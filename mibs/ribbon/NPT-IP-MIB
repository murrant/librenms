-- the NPT IP address table
  
 -- The NPT IP address table contains this NPT's IP addressing
 -- information.
 
NPT-IP-MIB  DEFINITIONS ::= BEGIN
    IMPORTS
    nptIP
             FROM NPT-ROOT-MIB
    MODULE-IDENTITY, OBJECT-TYPE, Counter32, Gauge32,
        Integer32, Unsigned32, IpAddress, mib-2, zeroDotZero
                     FROM SNMPv2-SMI
    DisplayString
            FROM RFC1213-MIB
    InetAddress, InetAddressType,
    InetAddressPrefixLength,
    InetVersion, InetZoneIndex         FROM INET-ADDRESS-MIB
    InterfaceIndex                     FROM IF-MIB
    IpAddressOriginTC, IpAddressStatusTC    FROM IP-MIB
    RowPointer, TimeStamp,
    RowStatus, StorageType    FROM SNMPv2-TC;

    nptip MODULE-IDENTITY
        LAST-UPDATED "202012020000Z"
        ORGANIZATION "ECI"
        CONTACT-INFO "Contact-info"
        DESCRIPTION  "Description"
        REVISION     "01Z"
        DESCRIPTION     ""
        ::=  {  nptIP  1  }

IpAddressOriginTC ::= TEXTUAL-CONVENTION
    STATUS     current
    DESCRIPTION
           "The origin of the address.

            manual(2) indicates that the address was manually configured
            to a specified address, e.g., by user configuration.

            dhcp(4) indicates an address that was assigned to this
            system by a DHCP server.

            linklayer(5) indicates an address created by IPv6 stateless
            auto-configuration.

            random(6) indicates an address chosen by the system at
            random, e.g., an IPv4 address within 169.254/16, or an RFC
            3041 privacy address."
    SYNTAX     INTEGER {
        other(1),
        manual(2),
        dhcp(4),
        linklayer(5),
        random(6)
    }

IpAddressStatusTC ::= TEXTUAL-CONVENTION
    STATUS     current
    DESCRIPTION
           "The status of an address.  Most of the states correspond to
            states from the IPv6 Stateless Address Autoconfiguration
            protocol.

            The preferred(1) state indicates that this is a valid
            address that can appear as the destination or source address
            of a packet.

            The deprecated(2) state indicates that this is a valid but
            deprecated address that should no longer be used as a source
            address in new communications, but packets addressed to such
            an address are processed as expected.

            The invalid(3) state indicates that this isn't a valid
            address and it shouldn't appear as the destination or source
            address of a packet.

            The inaccessible(4) state indicates that the address is not
            accessible because the interface to which this address is
            assigned is not operational.

            The unknown(5) state indicates that the status cannot be
            determined for some reason.

            The tentative(6) state indicates that the uniqueness of the
            address on the link is being verified.  Addresses in this
            state should not be used for general communication and
            should only be used to determine the uniqueness of the
            address.

            The duplicate(7) state indicates the address has been
            determined to be non-unique on the link and so must not be
            used.

            The optimistic(8) state indicates the address is available
            for use, subject to restrictions, while its uniqueness on
            a link is being verified.

            In the absence of other information, an IPv4 address is
            always preferred(1)."
    REFERENCE "RFC 2462"
    SYNTAX     INTEGER {
        preferred(1),
        deprecated(2),
        invalid(3),
        inaccessible(4),
        unknown(5),
        tentative(6),
        duplicate(7),
        optimistic(8)
    }


    -- Objects
    nptIPObjects OBJECT IDENTIFIER ::= { nptip 1 }
    
 nptIpAddrTable OBJECT-TYPE
     SYNTAX  SEQUENCE OF NptIpAddrEntry
     ACCESS  not-accessible
     STATUS  mandatory
     DESCRIPTION
             "The table of addressing information relevant to
             this entity's IP addresses."
     ::= { nptIPObjects 1 }
  
 nptIpAddrEntry OBJECT-TYPE
     SYNTAX  NptIpAddrEntry
     ACCESS  not-accessible
     STATUS  mandatory
     DESCRIPTION
             "The addressing information for one of this
             entity's IP addresses."
     INDEX   {  nptIpAdEntAddr  }
     ::= { nptIpAddrTable 1 }
  
 NptIpAddrEntry ::=
     SEQUENCE {
          nptIpAdEntAddr 
             IpAddress,
          nptIpAdEntIfIndex
             INTEGER,
         nptIpAdEntNetMask
             IpAddress,
         nptIpAdEntBcastAddr
             INTEGER,
         nptIpAdEntReasmMaxSize
             INTEGER(0..65535),
         nptIpAdEntSubNet
             DisplayString(SIZE (0..24))
     }
  
  nptIpAdEntAddr  OBJECT-TYPE
     SYNTAX  IpAddress
     ACCESS  read-only
     STATUS  mandatory
     DESCRIPTION
             "The IP address to which this entry's addressing
             information pertains."
     ::= { nptIpAddrEntry 1 }
  
  nptIpAdEntIfIndex OBJECT-TYPE
     SYNTAX  INTEGER
     ACCESS  read-only
     STATUS  mandatory
     DESCRIPTION
             "The index value which uniquely identifies the
             interface to which this entry is applicable.  The
             interface identified by a particular value of this
             index is the same interface as identified by the
             same value of ifIndex."
     ::= { nptIpAddrEntry 2 }
  
 nptIpAdEntNetMask OBJECT-TYPE
     SYNTAX  IpAddress
     ACCESS  read-only
     STATUS  mandatory
     DESCRIPTION
             "The subnet mask associated with the IP address of
             this entry.  The value of the mask is an IP
             address with all the network bits set to 1 and all
             the hosts bits set to 0."
     ::= { nptIpAddrEntry 3 }
  
 nptIpAdEntBcastAddr OBJECT-TYPE
     SYNTAX  INTEGER
     ACCESS  read-only
     STATUS  mandatory
     DESCRIPTION
             "The value of the least-significant bit in the IP
             broadcast address used for sending datagrams on
             the (logical) interface associated with the IP
             address of this entry.  For example, when the
             Internet standard all-ones broadcast address is
             used, the value will be 1.  This value applies to
             both the subnet and network broadcasts addresses
             used by the entity on this (logical) interface."
     ::= { nptIpAddrEntry 4 }
  
 nptIpAdEntReasmMaxSize OBJECT-TYPE
     SYNTAX  INTEGER (0..65535)
     ACCESS  read-only
     STATUS  mandatory
     DESCRIPTION
             "The size of the largest IP datagram which this
             entity can re-assemble from incoming IP fragmented
             datagrams received on this interface."
     ::= { nptIpAddrEntry 5 } 
 
nptIpAdEntSubNet OBJECT-TYPE
     SYNTAX  DisplayString (SIZE (0..24))
     ACCESS  read-only
     STATUS  mandatory
     DESCRIPTION
             "The subnet address associated with the IP address of
             this entry, with the format <ip>/<mask length>. For
             example, 1.2.3.0/24. "
     ::= { nptIpAddrEntry 6 }

nptIpAddressTable OBJECT-TYPE
    SYNTAX     SEQUENCE OF NptIpAddressEntry
    MAX-ACCESS not-accessible
    STATUS     current
    DESCRIPTION
           "This table contains addressing information relevant to the
            entity's interfaces.

            This table does not contain multicast address information.
            Tables for such information should be contained in multicast
            specific MIBs, such as RFC 3019.

            While this table is writable, the user will note that
            several objects, such as nptIpAddressOrigin, are not.  The
            intention in allowing a user to write to this table is to
            allow them to add or remove any entry that isn't
            permanent.  The user should be allowed to modify objects
            and entries when that would not cause inconsistencies
            within the table.  Allowing write access to objects, such
            as nptIpAddressOrigin, could allow a user to insert an entry
            and then label it incorrectly.

            Note well: When including IPv6 link-local addresses in this
            table, the entry must use an InetAddressType of 'ipv6z' in
            order to differentiate between the possible interfaces."
    ::= { nptIPObjects 2 }

nptIpAddressEntry OBJECT-TYPE
    SYNTAX     NptIpAddressEntry
    MAX-ACCESS not-accessible
    STATUS     current
    DESCRIPTION
           "An address mapping for a particular interface."
    INDEX { nptIpAddressAddrType, nptIpAddressAddr, nptIpAddressIfIndex }
    ::= { nptIpAddressTable 1 }

NptIpAddressEntry ::= SEQUENCE {
	nptIpAddressAddrType     InetAddressType,
        nptIpAddressAddr         InetAddress,
        nptIpAddressIfIndex      InterfaceIndex,
        nptIpAddressType         INTEGER,
        nptIpAddressPrefix       RowPointer,
        nptIpAddressOrigin       IpAddressOriginTC,
        nptIpAddressStatus       IpAddressStatusTC,
        nptIpAddressCreated      TimeStamp,
        nptIpAddressLastChanged  TimeStamp,
        nptIpAddressRowStatus    RowStatus,
        nptIpAddressStorageType  StorageType,
        nptIpAddressEntSubNet   DisplayString
}
    
nptIpAddressAddrType OBJECT-TYPE
    SYNTAX     InetAddressType
    MAX-ACCESS not-accessible
    STATUS     current
    DESCRIPTION
           "The address type of nptIpAddressAddr."
    ::= { nptIpAddressEntry 1 }

nptIpAddressAddr OBJECT-TYPE
    SYNTAX     InetAddress
    MAX-ACCESS not-accessible
    STATUS     current
    DESCRIPTION
           "The IP address to which this entry's addressing information
            pertains.  The address type of this object is specified in
            nptIpAddressAddrType.

            Implementors need to be aware that if the size of
            nptIpAddressAddr exceeds 116 octets, then OIDS of instances of
            columns in this row will have more than 128 sub-identifiers
            and cannot be accessed using SNMPv1, SNMPv2c, or SNMPv3."
    ::= { nptIpAddressEntry 2 }

nptIpAddressIfIndex OBJECT-TYPE
    SYNTAX     InterfaceIndex
    MAX-ACCESS read-create
    STATUS     current
    DESCRIPTION
           "The index value that uniquely identifies the interface to
            which this entry is applicable.  The interface identified by
            a particular value of this index is the same interface as
            identified by the same value of the IF-MIB's ifIndex."
    ::= { nptIpAddressEntry 3 }

nptIpAddressType OBJECT-TYPE
    SYNTAX     INTEGER {
                 unicast(1),
                 anycast(2),
                 broadcast(3)
    }
    MAX-ACCESS read-create
    STATUS     current
    DESCRIPTION
           "The type of address.  broadcast(3) is not a valid value for
            IPv6 addresses (RFC 3513)."
    DEFVAL { unicast }
    ::= { nptIpAddressEntry 4 }

nptIpAddressPrefix OBJECT-TYPE
    SYNTAX     RowPointer
    MAX-ACCESS read-only
    STATUS     current
    DESCRIPTION
           "A pointer to the row in the prefix table to which this
            address belongs.  May be { 0 0 } if there is no such row."
    DEFVAL { zeroDotZero }
    ::= { nptIpAddressEntry 5 }

nptIpAddressOrigin OBJECT-TYPE
    SYNTAX     IpAddressOriginTC
    MAX-ACCESS read-only
    STATUS     current
    DESCRIPTION
           "The origin of the address."
    ::= { nptIpAddressEntry 6 }

nptIpAddressStatus OBJECT-TYPE
    SYNTAX     IpAddressStatusTC
    MAX-ACCESS read-create
    STATUS     current
    DESCRIPTION
           "The status of the address, describing if the address can be
            used for communication.

            In the absence of other information, an IPv4 address is
            always preferred(1)."
    DEFVAL { preferred }
    ::= { nptIpAddressEntry 7 }

nptIpAddressCreated OBJECT-TYPE
    SYNTAX     TimeStamp
    MAX-ACCESS read-only
    STATUS     current
    DESCRIPTION
           "The value of sysUpTime at the time this entry was created.
            If this entry was created prior to the last re-
            initialization of the local network management subsystem,
            then this object contains a zero value."
    ::= { nptIpAddressEntry 8 }

nptIpAddressLastChanged OBJECT-TYPE
    SYNTAX     TimeStamp
    MAX-ACCESS read-only
    STATUS     current
    DESCRIPTION
           "The value of sysUpTime at the time this entry was last
            updated.  If this entry was updated prior to the last re-
            initialization of the local network management subsystem,
            then this object contains a zero value."
    ::= { nptIpAddressEntry 9 }

nptIpAddressRowStatus OBJECT-TYPE
    SYNTAX     RowStatus
    MAX-ACCESS read-create
    STATUS     current
    DESCRIPTION
           "The status of this conceptual row.

            The RowStatus TC requires that this DESCRIPTION clause
            states under which circumstances other objects in this row
            can be modified.  The value of this object has no effect on
            whether other objects in this conceptual row can be
            modified.

            A conceptual row can not be made active until the
            nptIpAddressIfIndex has been set to a valid index."
    ::= { nptIpAddressEntry 10 }

nptIpAddressStorageType OBJECT-TYPE
    SYNTAX     StorageType
    MAX-ACCESS read-create
    STATUS     current
    DESCRIPTION
           "The storage type for this conceptual row.  If this object
            has a value of 'permanent', then no other objects are
            required to be able to be modified."
    DEFVAL { volatile }
    ::= { nptIpAddressEntry 11 }
    
nptIpAddressEntSubNet OBJECT-TYPE
 SYNTAX  DisplayString (SIZE (0..43))
 ACCESS  read-only
 STATUS  mandatory
 DESCRIPTION
         "The subnet address associated with the IP address of
         this entry, with the format <ip>/<mask length>. For
         example, 1.2.3.0/24, or 1234:5678::1/64. "
 ::= { nptIpAddressEntry 12 }
 
END
