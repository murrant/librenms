-- File Name : NPT-STATISTICS-MIB
-- Date      : Tue Jul 05 09:15:57 CST 2011
-- Author    : AdventNet Agent Toolkit C Edition - MibEditor 6



NPT-STATISTICS-MIB	DEFINITIONS ::= BEGIN
	IMPORTS
		nptStatistics
			FROM NPT-ROOT-MIB
		RowStatus, DisplayString
			FROM SNMPv2-TC
		DisplayString
			FROM RFC1213-MIB
		MODULE-IDENTITY, OBJECT-TYPE, Integer32, Counter64, enterprises
			FROM SNMPv2-SMI;
	
	nptStatisticsModule	MODULE-IDENTITY
		LAST-UPDATED	"201105240945Z"
		ORGANIZATION	"Ribbon Communications Inc."
		CONTACT-INFO	"on.support@rbbn.com 
                         Ribbon Communications Inc.,China
                         Dongxin Tower, No.398 Wensan Road, 
                         Hangzhou, 310012 P.R.China"
		DESCRIPTION		"The MIB module for NPT IP/MPLS products."
		REVISION		"201105240945Z"
		DESCRIPTION		""
		::=  {  nptStatistics  1  }

	org	OBJECT IDENTIFIER
		::=  {  iso  3  }

	dod	OBJECT IDENTIFIER
		::=  {  org  6  }

	internet	OBJECT IDENTIFIER
		::=  {  dod  1  }

	private	OBJECT IDENTIFIER
		::=  {  internet  4  }

	enterprises	OBJECT IDENTIFIER
		::=  {  private  1  }

	nptProtocolIfGroup OBJECT IDENTIFIER
		::=  {  nptStatisticsModule  1  }
		
	nptInterfaceIfGroup OBJECT IDENTIFIER
		::=  {  nptStatisticsModule  2  }
		
	nptMPLSIfGroup OBJECT IDENTIFIER
		::=  {  nptStatisticsModule  3  }
		
	nptVPNIfGroup OBJECT IDENTIFIER
		::=  {  nptStatisticsModule  4  }
				
	nptSwitchIfGroup OBJECT IDENTIFIER
		::=  {  nptStatisticsModule  5  }
		
    nptPWIfGroup	OBJECT IDENTIFIER
		::=  {  nptStatisticsModule  7  }

    nptRoutingInstancesGroup	OBJECT IDENTIFIER
		::=  {  nptStatisticsModule  8  }

	nptSecurityGroup	OBJECT IDENTIFIER
		::=  {  nptStatisticsModule  9  }

	nptSmartSfpGroup	OBJECT IDENTIFIER
		::=  {  nptStatisticsModule  10  }

	nptOspf	OBJECT IDENTIFIER
		::=  {  nptProtocolIfGroup  1  }
		
	nptIsis	OBJECT IDENTIFIER
		::=  {  nptProtocolIfGroup  2  }
				
	nptBfd OBJECT IDENTIFIER
		::=  {  nptProtocolIfGroup  3  }
		
	nptLDI OBJECT IDENTIFIER
		::=  {  nptProtocolIfGroup  4  }

	nptMSTP OBJECT IDENTIFIER
		::=  {  nptProtocolIfGroup  5  }
		
	nptBundle OBJECT IDENTIFIER
		::=  {  nptProtocolIfGroup  6  }
		
	nptLP OBJECT IDENTIFIER
		::=  {  nptProtocolIfGroup  7  }
		
	nptLDP OBJECT IDENTIFIER
		::=  {  nptProtocolIfGroup  8  }
		
	nptPTP1588 OBJECT IDENTIFIER
		::=  {  nptProtocolIfGroup  9  }
				
	nptERPS OBJECT IDENTIFIER
		::=  {  nptProtocolIfGroup  10  }
		
	nptIGMP OBJECT IDENTIFIER
		::=  {  nptProtocolIfGroup  11  }
		
	nptDHCP OBJECT IDENTIFIER
		::=  {  nptProtocolIfGroup  12  }
		
	nptVRRP OBJECT IDENTIFIER
		::=  {  nptProtocolIfGroup  13  }
		
	nptDAI OBJECT IDENTIFIER
		::=  {  nptProtocolIfGroup  14  }
		
	nptPIM OBJECT IDENTIFIER
		::=  {  nptProtocolIfGroup  15  }
		
	nptBGP OBJECT IDENTIFIER
		::=  {  nptProtocolIfGroup  16  }
		
	nptMLD OBJECT IDENTIFIER
		::=  {  nptProtocolIfGroup  17  }
		
	nptDHCPV6 OBJECT IDENTIFIER
		::=  {  nptProtocolIfGroup  18  }
		
	nptOspfV3 OBJECT IDENTIFIER
		::=  {  nptProtocolIfGroup  19  }
		
	nptNdp OBJECT IDENTIFIER
		::=  {  nptProtocolIfGroup  20  }
		
	nptmthBfd OBJECT IDENTIFIER
		::=  {  nptProtocolIfGroup  21  }
        
	nptLLDP OBJECT IDENTIFIER
		::=  {  nptProtocolIfGroup  22  }
		
	nptPhysicalPort	OBJECT IDENTIFIER
		::=  {  nptInterfaceIfGroup  1  }
		
	nptIfTMDFSRV	OBJECT IDENTIFIER
		::=  {  nptInterfaceIfGroup  2  }
				
	nptIfTMFRR	OBJECT IDENTIFIER
		::=  {  nptInterfaceIfGroup  3  }
		
	nptIfRx	OBJECT IDENTIFIER
		::=  {  nptInterfaceIfGroup  4  }
		
	nptIfTx	OBJECT IDENTIFIER
		::=  {  nptInterfaceIfGroup  5  }
		
	nptLif	OBJECT IDENTIFIER
		::=  {  nptInterfaceIfGroup  8  }
		
		
	nptTunnelRx	OBJECT IDENTIFIER
		::=  {  nptMPLSIfGroup  1  }
		
	nptTunnelRxCoS	OBJECT IDENTIFIER
		::=  {  nptMPLSIfGroup  2  }
		
	nptTunnelTx	OBJECT IDENTIFIER
		::=  {  nptMPLSIfGroup  3  }
		
	nptTunnelTxCoS	OBJECT IDENTIFIER
		::=  {  nptMPLSIfGroup  4  }
		
	nptTunnelTMFB	OBJECT IDENTIFIER
		::=  {  nptMPLSIfGroup  5  }
		
	nptSrteTunnel	OBJECT IDENTIFIER
		::=  {  nptMPLSIfGroup  8  }
        
	nptBGPLU OBJECT IDENTIFIER
		::=  {  nptMPLSIfGroup  9  }
		
	nptSRBE	OBJECT IDENTIFIER
		::=  {  nptMPLSIfGroup  10  }

	nptVSIRx	OBJECT IDENTIFIER
		::=  {  nptVPNIfGroup  1  }
		
	nptVSITx	OBJECT IDENTIFIER
		::=  {  nptVPNIfGroup  2  }
		
	nptVSIRxCoS	OBJECT IDENTIFIER
		::=  {  nptVPNIfGroup  3  }
		
	nptVSITxCoS	OBJECT IDENTIFIER
		::=  {  nptVPNIfGroup  4  }
		
	nptSwitchRouter	OBJECT IDENTIFIER
		::=  {  nptSwitchIfGroup  1  }
		
	nptOspfInstance	OBJECT IDENTIFIER
		::=  {  nptOspf  1  }
		
	nptOspfLif	OBJECT IDENTIFIER
		::=  {  nptOspf  2  }
		
	nptIsisInstance OBJECT IDENTIFIER
		::=  {  nptIsis  1  }
		
	nptIsisLif	OBJECT IDENTIFIER
		::=  {  nptIsis  2  }
		
	nptBfdSwitch OBJECT IDENTIFIER
		::=  {  nptBfd  1  }
		
	nptBfdPseudowire OBJECT IDENTIFIER
		::=  {  nptBfd  2  }
		
	nptBfdSection OBJECT IDENTIFIER
		::=  {  nptBfd  3  }
		
	nptBfdSingleHopIP OBJECT IDENTIFIER
		::=  {  nptBfd  4  }
		
	nptBfdMPLSTPTunnel OBJECT IDENTIFIER
		::=  {  nptBfd  5  }
		
	nptLAG OBJECT IDENTIFIER
		::=  {  nptBundle  1  }
		
	nptLAGPort OBJECT IDENTIFIER
		::=  {  nptBundle  2  }
		
	nptMcLAG OBJECT IDENTIFIER
		::=  {  nptBundle  3  }
		
	nptLDPEntity OBJECT IDENTIFIER
		::=  {  nptLDP  1  }
		
	nptLDPSession OBJECT IDENTIFIER
		::=  {  nptLDP  2  }
		
	nptLDPTargetedEntity OBJECT IDENTIFIER
		::=  {  nptLDP  3  }
		
	nptLDPLSP OBJECT IDENTIFIER
		::=  {  nptLDP  4  }
		
	nptLDPSegment OBJECT IDENTIFIER
		::=  {  nptLDP  5  }
		
	nptPTP1588SlaveRx OBJECT IDENTIFIER
		::=  {  nptPTP1588  1  }
		
	nptPTP1588SlaveTx OBJECT IDENTIFIER
		::=  {  nptPTP1588  2  }
		
	nptPTP1588Master OBJECT IDENTIFIER
		::=  {  nptPTP1588  3  }
		
	nptPTP1588Slave OBJECT IDENTIFIER
		::=  {  nptPTP1588  4  }
		
	nptPTP1588Port OBJECT IDENTIFIER
		::=  {  nptPTP1588  5  }
		
	nptIGMPInterface OBJECT IDENTIFIER
		::=  {  nptIGMP  1  }
		
	nptIGMPProxyUpstream OBJECT IDENTIFIER
		::=  {  nptIGMP  2  }
		
	nptIGMPProxyDownstream OBJECT IDENTIFIER
		::=  {  nptIGMP  3  }
		
	nptDHCPRelayAgentClient OBJECT IDENTIFIER
		::=  {  nptDHCP  1  }
		
	nptDHCPRelayAgentServer OBJECT IDENTIFIER
		::=  {  nptDHCP  2  }
		
	nptDHCPPW OBJECT IDENTIFIER
		::=  {  nptDHCP  3  }
		
	nptDHCPInterface OBJECT IDENTIFIER
		::=  {  nptDHCP  4  }
		
	nptDAIPW OBJECT IDENTIFIER
		::=  {  nptDAI  1  }
		
	nptDAIInterface OBJECT IDENTIFIER
		::=  {  nptDAI  2  }
		
	nptPIMInstance OBJECT IDENTIFIER
		::=  {  nptPIM  1  }
		
	nptPIMLif OBJECT IDENTIFIER
		::=  {  nptPIM  2  }
		
	nptBgpNeighbor OBJECT IDENTIFIER
		::=  {  nptBGP  1  }
		
	nptMldInterface OBJECT IDENTIFIER
		::=  {  nptMLD  1  }
		
	nptDhcpv6RelayAgent OBJECT IDENTIFIER
		::=  {  nptDHCPV6  1  }
		
	nptDhcpv6PhtRelayAgent OBJECT IDENTIFIER
		::=  {  nptDHCPV6  2  }
		
	nptDhcpv6RelayAgentServer OBJECT IDENTIFIER
		::=  {  nptDHCPV6  3  }
		
	nptOspfV3Instance	OBJECT IDENTIFIER
		::=  {  nptOspfV3  1  }
		
	nptOspfV3Interface	OBJECT IDENTIFIER
		::=  {  nptOspfV3  2  }
		
	nptNdpProtocol	OBJECT IDENTIFIER
		::=  {  nptNdp  1  }
		
	nptNdpTracking	OBJECT IDENTIFIER
		::=  {  nptNdp  2  }
		
    nptmthBfdAuto	OBJECT IDENTIFIER
		::=  {  nptmthBfd  1  }
		
	nptmthBfdManual	OBJECT IDENTIFIER
		::=  {  nptmthBfd  2  }
        
	nptLLDPStatistics OBJECT IDENTIFIER
		::=  {  nptLLDP  1  }
		
	nptSwitchInstance OBJECT IDENTIFIER
		::=  {  nptPWIfGroup  6  }
		
	nptSwitchInstanceRx OBJECT IDENTIFIER
		::=  {  nptPWIfGroup  7  }
		
	nptSwitchInstanceTx OBJECT IDENTIFIER
		::=  {  nptPWIfGroup  8  }
		
	nptSwitchInstanceRxCoS OBJECT IDENTIFIER
		::=  {  nptPWIfGroup  9  }
		
	nptSwitchInstanceTxCoS OBJECT IDENTIFIER
		::=  {  nptPWIfGroup  10  }
		
	nptRoutingInstances	OBJECT IDENTIFIER
		::=  {  nptRoutingInstancesGroup  1  }
		
	nptRoutingInstancesRxCoS	OBJECT IDENTIFIER
		::=  {  nptRoutingInstancesGroup  2  }
		
	nptRoutingInstancesTxCoS	OBJECT IDENTIFIER
		::=  {  nptRoutingInstancesGroup  3  }
		
	nptSecurityMacsecStatisticsComPort	OBJECT IDENTIFIER
		::=  {  nptSecurityGroup  1  }
		
	nptSecurityMacsecStatisticsCtrlPort	OBJECT IDENTIFIER
		::=  {  nptSecurityGroup  2  }
		
	nptSecurityMacsecStatisticsEAPol	OBJECT IDENTIFIER
		::=  {  nptSecurityGroup  3  }
		
	nptSecurityMacsecStatisticsMACEntity	OBJECT IDENTIFIER
		::=  {  nptSecurityGroup  4  }
		
	nptSecurityMacsecStatisticsSecChan	OBJECT IDENTIFIER
		::=  {  nptSecurityGroup  5  }
		
	nptSecurityMacsecStatisticsUnctrlPort	OBJECT IDENTIFIER
		::=  {  nptSecurityGroup  6  }
		
	nptSecurityMkaStatisticsError	OBJECT IDENTIFIER
		::=  {  nptSecurityGroup  7  }
		
	nptSecurityMkaStatisticsGlobal	OBJECT IDENTIFIER
		::=  {  nptSecurityGroup  8  }

	nptSmartSfpEthPortStatistics	OBJECT IDENTIFIER
		::=  {  nptSmartSfpGroup  1  }
		
	nptSmartSfpStmPortStatistics	OBJECT IDENTIFIER
		::=  {  nptSmartSfpGroup  2  }
		
	nptSmartSfpE1PortStatistics	OBJECT IDENTIFIER
		::=  {  nptSmartSfpGroup  3  }
		
	nptSmartSfpCesStatistics	OBJECT IDENTIFIER
		::=  {  nptSmartSfpGroup  4  }

	nptOspfInstanceTable	OBJECT-TYPE
		SYNTAX		SEQUENCE  OF  NptOspfInstanceEntry
		MAX-ACCESS	not-accessible
		STATUS		current
		DESCRIPTION	"Description"
		::=  { nptOspfInstance  1 }

	nptOspfInstanceEntry	OBJECT-TYPE
		SYNTAX		NptOspfInstanceEntry
		MAX-ACCESS	not-accessible
		STATUS		current
		DESCRIPTION	"Row Description"
		INDEX		{  nptOspfInstanceIndex  }
		::=  { nptOspfInstanceTable 1 }

	NptOspfInstanceEntry  ::=  SEQUENCE {
	    nptOspfInstanceIndex  Integer32,
		nptOspfInstanceName  DisplayString,
		nptOspfInstanceDisContinuityTime  Counter64,
		nptOspfInstanceElapsed DisplayString,
	    nptOspfInstanceRxLengthErr  Counter64,
		nptOspfInstanceRxResourceErr  Counter64,
		nptOspfInstanceRxInvalidInterface  Counter64,
		nptOspfInstanceRxInvalidVritualLink  Counter64,
		nptOspfInstanceRxInvalidInstanceId  Counter64,
		nptOspfInstanceRxInvalidVersion  Counter64,
		nptOspfInstanceRxBadIpHeaderLength  Counter64,
		nptOspfInstanceRxBadSource  Counter64,
		nptOspfInstanceRxBadPacket  Counter64
		}


	nptOspfInstanceIndex	OBJECT-TYPE	
		SYNTAX			Integer32  ( -2147483648 .. 2147483647  ) 
		MAX-ACCESS		read-only
		STATUS			current
		DESCRIPTION		"Column Description"
		::=  {  nptOspfInstanceEntry  1  }
		
	nptOspfInstanceName	OBJECT-TYPE	
		SYNTAX			DisplayString 
		MAX-ACCESS		read-only
		STATUS			current
		DESCRIPTION		"instance name"
		::=  {  nptOspfInstanceEntry  2  }


	nptOspfInstanceDisContinuityTime	OBJECT-TYPE	
		SYNTAX			Counter64
		MAX-ACCESS		read-only
		STATUS			current
		DESCRIPTION		"DisContinuity Time"
		::=  {  nptOspfInstanceEntry  3  }
		
	nptOspfInstanceElapsed	OBJECT-TYPE	
		SYNTAX			DisplayString 
		MAX-ACCESS		read-only
		STATUS			current
		DESCRIPTION		"dd:hh:mm:ss"
		::=  {  nptOspfInstanceEntry  4  }


	nptOspfInstanceRxLengthErr	OBJECT-TYPE	
		SYNTAX			Counter64
		MAX-ACCESS		read-only
		STATUS			current
		DESCRIPTION		"Description"
		::=  {  nptOspfInstanceEntry  5  }


	nptOspfInstanceRxResourceErr	OBJECT-TYPE	
		SYNTAX			Counter64
		MAX-ACCESS		read-only
		STATUS			current
		DESCRIPTION		"Description"
		::=  {  nptOspfInstanceEntry  6  }


	nptOspfInstanceRxInvalidInterface	OBJECT-TYPE	
		SYNTAX			Counter64
		MAX-ACCESS		read-only
		STATUS			current
		DESCRIPTION		"Description"
		::=  {  nptOspfInstanceEntry  7  }


	nptOspfInstanceRxInvalidVritualLink	OBJECT-TYPE	
		SYNTAX			Counter64
		MAX-ACCESS		read-only
		STATUS			current
		DESCRIPTION		"Description"
		::=  {  nptOspfInstanceEntry  8  }


	nptOspfInstanceRxInvalidInstanceId	OBJECT-TYPE	
		SYNTAX			Counter64
		MAX-ACCESS		read-only
		STATUS			current
		DESCRIPTION		"Description"
		::=  {  nptOspfInstanceEntry  9  }


	nptOspfInstanceRxInvalidVersion	OBJECT-TYPE	
		SYNTAX			Counter64
		MAX-ACCESS		read-only
		STATUS			current
		DESCRIPTION		"Description"
		::=  {  nptOspfInstanceEntry  10  }


	nptOspfInstanceRxBadIpHeaderLength	OBJECT-TYPE	
		SYNTAX			Counter64
		MAX-ACCESS		read-only
		STATUS			current
		DESCRIPTION		"Description"
		::=  {  nptOspfInstanceEntry  11  }


	nptOspfInstanceRxBadSource	OBJECT-TYPE	
		SYNTAX			Counter64
		MAX-ACCESS		read-only
		STATUS			current
		DESCRIPTION		"Description"
		::=  {  nptOspfInstanceEntry  12  }


	nptOspfInstanceRxBadPacket	OBJECT-TYPE	
		SYNTAX			Counter64
		MAX-ACCESS		read-only
		STATUS			current
		DESCRIPTION		"Description"
		::=  {  nptOspfInstanceEntry  13  }
		
	nptOspfLifTable	OBJECT-TYPE
		SYNTAX		SEQUENCE  OF  NptOspfLifEntry
		MAX-ACCESS	not-accessible
		STATUS		current
		DESCRIPTION	"Description"
		::=  { nptOspfLif  1 }

	nptOspfLifEntry	OBJECT-TYPE
		SYNTAX		NptOspfLifEntry
		MAX-ACCESS	not-accessible
		STATUS		current
		DESCRIPTION	"Row Description"
		INDEX		{  nptOspfLifIndex  }
		::=  { nptOspfLifTable 1 }

	NptOspfLifEntry  ::=  SEQUENCE {
	    nptOspfLifIndex  Integer32,
		nptOspfLifInstanceName  DisplayString,
		nptOspfLifName  DisplayString,
		nptOspfLifDisContinuityTime  Counter64,
		nptOspfLifElapsed DisplayString,
	    nptOspfLifTxPktHello  Counter64,
		nptOspfLifTxPktDbD  Counter64,
		nptOspfLifTxPktLsReq  Counter64,
		nptOspfLifTxPktLsUpd  Counter64,
		nptOspfLifTxPktLsAck  Counter64,
		nptOspfLifTxPktFailed  Counter64,
		nptOspfLifTxByteHello  Counter64,
		nptOspfLifTxByteDbD  Counter64,
		nptOspfLifTxByteLsReq  Counter64,
		nptOspfLifTxByteLsUpd  Counter64,
		nptOspfLifTxByteLsAck  Counter64,
		nptOspfLifTxByteFailed  Counter64,
		nptOspfLifRxPktInvalid  Counter64,
		nptOspfLifRxPktHello  Counter64,
		nptOspfLifRxPktDbD  Counter64,
		nptOspfLifRxPktLsReq  Counter64,
		nptOspfLifRxPktLsUpd  Counter64,
		nptOspfLifRxPktLsAck  Counter64,
		nptOspfLifRxByteInvalid  Counter64,
		nptOspfLifRxByteHello  Counter64,
		nptOspfLifRxByteDbD  Counter64,
		nptOspfLifRxByteLsReq  Counter64,
		nptOspfLifRxByteLsUpd  Counter64,
		nptOspfLifRxByteLsAck  Counter64,
		nptOspfLifPktHeadErrLength  Counter64,
		nptOspfLifPktHeadErrCksum  Counter64,
		nptOspfLifPktHeadErrVersion  Counter64,
		nptOspfLifPktHeadErrBadSrc  Counter64,
		nptOspfLifPktHeadErrAreaMismatch  Counter64,
		nptOspfLifPktHeadErrSelfOrig  Counter64,
		nptOspfLifPktHeadErrDuplicateID  Counter64,
		nptOspfLifPktHeadErrHello  Counter64,
		nptOspfLifPktHeadErrMtuMismatch  Counter64,
		nptOspfLifPktHeadErrNbrIgnored  Counter64,
		nptOspfLifPktHeadErrAuthErrors  Counter64,
		nptOspfLifPktHeadErrWrongProto  Counter64,
		nptOspfLifPktHeadErrResourceErr  Counter64,
		nptOspfLifPktHeadErrVirtMaIfClash  Counter64,
		nptOspfLifPktHeadErrIfStandby  Counter64,
		nptOspfLifLsaErrUpdBadLen  Counter64,
		nptOspfLifLsaErrBadType  Counter64,
		nptOspfLifLsaErrBadLen  Counter64,
		nptOspfLifLsaErrBadData  Counter64,
		nptOspfLifLsaErrBadCksum  Counter64,
		nptOspfLifPktDropUnkNbmaNbr  Counter64,
		nptOspfLifPktDropUnkVirtNbr  Counter64,
		nptOspfLifPktDropAuthMismatch  Counter64,
		nptOspfLifPktDropAuthFailure  Counter64,
		nptOspfLifPktDropNetmaskMismatch  Counter64,
		nptOspfLifPktDropHelloMismatch  Counter64,
		nptOspfLifPktDropDeadMismatch  Counter64,
		nptOspfLifPktDropOptionsMismatch  Counter64,
		nptOspfLifPktDropNbrAdminDown  Counter64,
		nptOspfLifPktDropPktLocalAddr  Counter64,
		nptOspfLifPktDropBadPacket  Counter64
		}


	nptOspfLifIndex	OBJECT-TYPE	
		SYNTAX			Integer32  ( -2147483648 .. 2147483647  ) 
		MAX-ACCESS		read-only
		STATUS			current
		DESCRIPTION		"Column Description"
		::=  {  nptOspfLifEntry  1  }
		
	nptOspfLifInstanceName	OBJECT-TYPE	
		SYNTAX			DisplayString 
		MAX-ACCESS		read-only
		STATUS			current
		DESCRIPTION		"LifName"
		::=  {  nptOspfLifEntry  2  }
		
	nptOspfLifName	OBJECT-TYPE	
		SYNTAX			DisplayString 
		MAX-ACCESS		read-only
		STATUS			current
		DESCRIPTION		"LifName"
		::=  {  nptOspfLifEntry  3  }


	nptOspfLifDisContinuityTime	OBJECT-TYPE	
		SYNTAX			Counter64
		MAX-ACCESS		read-only
		STATUS			current
		DESCRIPTION		"DisContinuity Time"
		::=  {  nptOspfLifEntry  4  }

    nptOspfLifElapsed	OBJECT-TYPE	
		SYNTAX			DisplayString 
		MAX-ACCESS		read-only
		STATUS			current
		DESCRIPTION		"dd:hh:mm:ss"
		::=  {  nptOspfLifEntry  5  }


	nptOspfLifTxPktHello	OBJECT-TYPE	
		SYNTAX			Counter64
		MAX-ACCESS		read-only
		STATUS			current
		DESCRIPTION		"Description"
		::=  {  nptOspfLifEntry  6  }


	nptOspfLifTxPktDbD	OBJECT-TYPE	
		SYNTAX			Counter64
		MAX-ACCESS		read-only
		STATUS			current
		DESCRIPTION		"Description"
		::=  {  nptOspfLifEntry  7  }


	nptOspfLifTxPktLsReq	OBJECT-TYPE	
		SYNTAX			Counter64
		MAX-ACCESS		read-only
		STATUS			current
		DESCRIPTION		"Description"
		::=  {  nptOspfLifEntry  8  }


	nptOspfLifTxPktLsUpd	OBJECT-TYPE	
		SYNTAX			Counter64
		MAX-ACCESS		read-only
		STATUS			current
		DESCRIPTION		"Description"
		::=  {  nptOspfLifEntry  9  }


	nptOspfLifTxPktLsAck	OBJECT-TYPE	
		SYNTAX			Counter64
		MAX-ACCESS		read-only
		STATUS			current
		DESCRIPTION		"Description"
		::=  {  nptOspfLifEntry  10  }


	nptOspfLifTxPktFailed	OBJECT-TYPE	
		SYNTAX			Counter64
		MAX-ACCESS		read-only
		STATUS			current
		DESCRIPTION		"Description"
		::=  {  nptOspfLifEntry  11  }


	nptOspfLifTxByteHello	OBJECT-TYPE	
		SYNTAX			Counter64
		MAX-ACCESS		read-only
		STATUS			current
		DESCRIPTION		"Description"
		::=  {  nptOspfLifEntry  12  }


	nptOspfLifTxByteDbD	OBJECT-TYPE	
		SYNTAX			Counter64
		MAX-ACCESS		read-only
		STATUS			current
		DESCRIPTION		"Description"
		::=  {  nptOspfLifEntry  13  }


	nptOspfLifTxByteLsReq	OBJECT-TYPE	
		SYNTAX			Counter64
		MAX-ACCESS		read-only
		STATUS			current
		DESCRIPTION		"Description"
		::=  {  nptOspfLifEntry  14  }


	nptOspfLifTxByteLsUpd	OBJECT-TYPE	
		SYNTAX			Counter64
		MAX-ACCESS		read-only
		STATUS			current
		DESCRIPTION		"Description"
		::=  {  nptOspfLifEntry  15  }


	nptOspfLifTxByteLsAck	OBJECT-TYPE	
		SYNTAX			Counter64
		MAX-ACCESS		read-only
		STATUS			current
		DESCRIPTION		"Description"
		::=  {  nptOspfLifEntry  16  }


	nptOspfLifTxByteFailed	OBJECT-TYPE	
		SYNTAX			Counter64
		MAX-ACCESS		read-only
		STATUS			current
		DESCRIPTION		"Description"
		::=  {  nptOspfLifEntry  17  }


	nptOspfLifRxPktInvalid	OBJECT-TYPE	
		SYNTAX			Counter64
		MAX-ACCESS		read-only
		STATUS			current
		DESCRIPTION		"Description"
		::=  {  nptOspfLifEntry  18  }


	nptOspfLifRxPktHello	OBJECT-TYPE	
		SYNTAX			Counter64
		MAX-ACCESS		read-only
		STATUS			current
		DESCRIPTION		"Description"
		::=  {  nptOspfLifEntry  19  }


	nptOspfLifRxPktDbD	OBJECT-TYPE	
		SYNTAX			Counter64
		MAX-ACCESS		read-only
		STATUS			current
		DESCRIPTION		"Description"
		::=  {  nptOspfLifEntry  20  }


	nptOspfLifRxPktLsReq	OBJECT-TYPE	
		SYNTAX			Counter64
		MAX-ACCESS		read-only
		STATUS			current
		DESCRIPTION		"Description"
		::=  {  nptOspfLifEntry  21  }


	nptOspfLifRxPktLsUpd	OBJECT-TYPE	
		SYNTAX			Counter64
		MAX-ACCESS		read-only
		STATUS			current
		DESCRIPTION		"Description"
		::=  {  nptOspfLifEntry  22  }


	nptOspfLifRxPktLsAck	OBJECT-TYPE	
		SYNTAX			Counter64
		MAX-ACCESS		read-only
		STATUS			current
		DESCRIPTION		"Description"
		::=  {  nptOspfLifEntry  23  }
		
	nptOspfLifRxByteInvalid	OBJECT-TYPE	
		SYNTAX			Counter64
		MAX-ACCESS		read-only
		STATUS			current
		DESCRIPTION		"Description"
		::=  {  nptOspfLifEntry  24  }
		
	nptOspfLifRxByteHello	OBJECT-TYPE	
		SYNTAX			Counter64
		MAX-ACCESS		read-only
		STATUS			current
		DESCRIPTION		"Description"
		::=  {  nptOspfLifEntry  25  }
		
	nptOspfLifRxByteDbD	OBJECT-TYPE	
		SYNTAX			Counter64
		MAX-ACCESS		read-only
		STATUS			current
		DESCRIPTION		"Description"
		::=  {  nptOspfLifEntry  26  }
		
	nptOspfLifRxByteLsReq	OBJECT-TYPE	
		SYNTAX			Counter64
		MAX-ACCESS		read-only
		STATUS			current
		DESCRIPTION		"Description"
		::=  {  nptOspfLifEntry  27  }
		
	nptOspfLifRxByteLsUpd	OBJECT-TYPE	
		SYNTAX			Counter64
		MAX-ACCESS		read-only
		STATUS			current
		DESCRIPTION		"Description"
		::=  {  nptOspfLifEntry  28  }
		
	nptOspfLifRxByteLsAck	OBJECT-TYPE	
		SYNTAX			Counter64
		MAX-ACCESS		read-only
		STATUS			current
		DESCRIPTION		"Description"
		::=  {  nptOspfLifEntry  29  }
		
	nptOspfLifPktHeadErrLength	OBJECT-TYPE	
		SYNTAX			Counter64
		MAX-ACCESS		read-only
		STATUS			current
		DESCRIPTION		"Description"
		::=  {  nptOspfLifEntry  30  }
		
	nptOspfLifPktHeadErrCksum	OBJECT-TYPE	
		SYNTAX			Counter64
		MAX-ACCESS		read-only
		STATUS			current
		DESCRIPTION		"Description"
		::=  {  nptOspfLifEntry  31  }
		
	nptOspfLifPktHeadErrVersion	OBJECT-TYPE	
		SYNTAX			Counter64
		MAX-ACCESS		read-only
		STATUS			current
		DESCRIPTION		"Description"
		::=  {  nptOspfLifEntry  32  }
		
	nptOspfLifPktHeadErrBadSrc	OBJECT-TYPE	
		SYNTAX			Counter64
		MAX-ACCESS		read-only
		STATUS			current
		DESCRIPTION		"Description"
		::=  {  nptOspfLifEntry  33  }
		
	nptOspfLifPktHeadErrAreaMismatch	OBJECT-TYPE	
		SYNTAX			Counter64
		MAX-ACCESS		read-only
		STATUS			current
		DESCRIPTION		"Description"
		::=  {  nptOspfLifEntry  34  }
		
	nptOspfLifPktHeadErrSelfOrig	OBJECT-TYPE	
		SYNTAX			Counter64
		MAX-ACCESS		read-only
		STATUS			current
		DESCRIPTION		"Description"
		::=  {  nptOspfLifEntry  35  }
		
	nptOspfLifPktHeadErrDuplicateID	OBJECT-TYPE	
		SYNTAX			Counter64
		MAX-ACCESS		read-only
		STATUS			current
		DESCRIPTION		"Description"
		::=  {  nptOspfLifEntry  36  }
		
	nptOspfLifPktHeadErrHello	OBJECT-TYPE	
		SYNTAX			Counter64
		MAX-ACCESS		read-only
		STATUS			current
		DESCRIPTION		"Description"
		::=  {  nptOspfLifEntry  37  }
		
	nptOspfLifPktHeadErrMtuMismatch	OBJECT-TYPE	
		SYNTAX			Counter64
		MAX-ACCESS		read-only
		STATUS			current
		DESCRIPTION		"Description"
		::=  {  nptOspfLifEntry  38  }
		
	nptOspfLifPktHeadErrNbrIgnored	OBJECT-TYPE	
		SYNTAX			Counter64
		MAX-ACCESS		read-only
		STATUS			current
		DESCRIPTION		"Description"
		::=  {  nptOspfLifEntry  39  }
		
	nptOspfLifPktHeadErrAuthErrors	OBJECT-TYPE	
		SYNTAX			Counter64
		MAX-ACCESS		read-only
		STATUS			current
		DESCRIPTION		"Description"
		::=  {  nptOspfLifEntry  40  }
		
	nptOspfLifPktHeadErrWrongProto	OBJECT-TYPE	
		SYNTAX			Counter64
		MAX-ACCESS		read-only
		STATUS			current
		DESCRIPTION		"Description"
		::=  {  nptOspfLifEntry  41  }
		
	nptOspfLifPktHeadErrResourceErr	OBJECT-TYPE	
		SYNTAX			Counter64
		MAX-ACCESS		read-only
		STATUS			current
		DESCRIPTION		"Description"
		::=  {  nptOspfLifEntry  42  }
		
	nptOspfLifPktHeadErrVirtMaIfClash	OBJECT-TYPE	
		SYNTAX			Counter64
		MAX-ACCESS		read-only
		STATUS			current
		DESCRIPTION		"Description"
		::=  {  nptOspfLifEntry  43  }
		
	nptOspfLifPktHeadErrIfStandby	OBJECT-TYPE	
		SYNTAX			Counter64
		MAX-ACCESS		read-only
		STATUS			current
		DESCRIPTION		"Description"
		::=  {  nptOspfLifEntry  44  }

    nptOspfLifLsaErrUpdBadLen	OBJECT-TYPE	
		SYNTAX			Counter64
		MAX-ACCESS		read-only
		STATUS			current
		DESCRIPTION		"Description"
		::=  {  nptOspfLifEntry  45  }

    nptOspfLifLsaErrBadType	OBJECT-TYPE	
		SYNTAX			Counter64
		MAX-ACCESS		read-only
		STATUS			current
		DESCRIPTION		"Description"
		::=  {  nptOspfLifEntry  46  }

    nptOspfLifLsaErrBadLen	OBJECT-TYPE	
		SYNTAX			Counter64
		MAX-ACCESS		read-only
		STATUS			current
		DESCRIPTION		"Description"
		::=  {  nptOspfLifEntry  47  }

    nptOspfLifLsaErrBadData	OBJECT-TYPE	
		SYNTAX			Counter64
		MAX-ACCESS		read-only
		STATUS			current
		DESCRIPTION		"Description"
		::=  {  nptOspfLifEntry  48  }

    nptOspfLifLsaErrBadCksum	OBJECT-TYPE	
		SYNTAX			Counter64
		MAX-ACCESS		read-only
		STATUS			current
		DESCRIPTION		"Description"
		::=  {  nptOspfLifEntry  49  }

    nptOspfLifPktDropUnkNbmaNbr	OBJECT-TYPE	
		SYNTAX			Counter64
		MAX-ACCESS		read-only
		STATUS			current
		DESCRIPTION		"Description"
		::=  {  nptOspfLifEntry  50  }

    nptOspfLifPktDropUnkVirtNbr	OBJECT-TYPE	
		SYNTAX			Counter64
		MAX-ACCESS		read-only
		STATUS			current
		DESCRIPTION		"Description"
		::=  {  nptOspfLifEntry  51  }

    nptOspfLifPktDropAuthMismatch	OBJECT-TYPE	
		SYNTAX			Counter64
		MAX-ACCESS		read-only
		STATUS			current
		DESCRIPTION		"Description"
		::=  {  nptOspfLifEntry  52  }

    nptOspfLifPktDropAuthFailure	OBJECT-TYPE	
		SYNTAX			Counter64
		MAX-ACCESS		read-only
		STATUS			current
		DESCRIPTION		"Description"
		::=  {  nptOspfLifEntry  53  }

    nptOspfLifPktDropNetmaskMismatch	OBJECT-TYPE	
		SYNTAX			Counter64
		MAX-ACCESS		read-only
		STATUS			current
		DESCRIPTION		"Description"
		::=  {  nptOspfLifEntry  54  }

    nptOspfLifPktDropHelloMismatch	OBJECT-TYPE	
		SYNTAX			Counter64
		MAX-ACCESS		read-only
		STATUS			current
		DESCRIPTION		"Description"
		::=  {  nptOspfLifEntry  55  }

    nptOspfLifPktDropDeadMismatch	OBJECT-TYPE	
		SYNTAX			Counter64
		MAX-ACCESS		read-only
		STATUS			current
		DESCRIPTION		"Description"
		::=  {  nptOspfLifEntry  56  }

    nptOspfLifPktDropOptionsMismatch	OBJECT-TYPE	
		SYNTAX			Counter64
		MAX-ACCESS		read-only
		STATUS			current
		DESCRIPTION		"Description"
		::=  {  nptOspfLifEntry  57  }

    nptOspfLifPktDropNbrAdminDown	OBJECT-TYPE	
		SYNTAX			Counter64
		MAX-ACCESS		read-only
		STATUS			current
		DESCRIPTION		"Description"
		::=  {  nptOspfLifEntry  58  }

    nptOspfLifPktDropPktLocalAddr	OBJECT-TYPE	
		SYNTAX			Counter64
		MAX-ACCESS		read-only
		STATUS			current
		DESCRIPTION		"Description"
		::=  {  nptOspfLifEntry  59  }

    nptOspfLifPktDropBadPacket	OBJECT-TYPE	
		SYNTAX			Counter64
		MAX-ACCESS		read-only
		STATUS			current
		DESCRIPTION		"Description"
		::=  {  nptOspfLifEntry  60  }
		
	nptIsisInstanceTable	OBJECT-TYPE
		SYNTAX		SEQUENCE  OF  NptIsisInstanceEntry
		MAX-ACCESS	not-accessible
		STATUS		current
		DESCRIPTION	"Description"
		::=  { nptIsisInstance  1 }

	nptIsisInstanceEntry	OBJECT-TYPE
		SYNTAX		NptIsisInstanceEntry
		MAX-ACCESS	not-accessible
		STATUS		current
		DESCRIPTION	"Row Description"
		INDEX		{  nptIsisInstanceIndex  }
		::=  { nptIsisInstanceTable 1 }

	NptIsisInstanceEntry  ::=  SEQUENCE {
	    nptIsisInstanceIndex  Integer32,
		nptIsisInstanceName  DisplayString,
        nptIsisInstanceProtocol  Integer32,
		nptIsisInstanceLevel  Integer32,
		nptIsisInstanceLastUpTime  Integer32,
		nptIsisInstanceElapsed DisplayString,
	    nptIsisInstanceCorruptedLsps  Counter64,
		nptIsisInstanceAuthTypeFails  Counter64,
		nptIsisInstanceAuthFails  Counter64,
		nptIsisInstanceDatabaseOverload  Counter64,
		nptIsisInstanceManAddrDrop  Counter64,
		nptIsisInstanceMaxSequence  Counter64,
		nptIsisInstanceSeqNumSkipped  Counter64,
		nptIsisInstanceOwnLspPurge  Counter64,
		nptIsisInstanceIdLenMismatch  Counter64,
		nptIsisInstancePartitionChange  Counter64,
		nptIsisInstanceSpfRuns  Counter64,
		nptIsisInstanceLspErrors  Counter64,
		nptIsisInstancePsnpErrors  Counter64,
		nptIsisInstanceCsnpErrors  Counter64
		}


	nptIsisInstanceIndex	OBJECT-TYPE	
		SYNTAX			Integer32  ( -2147483648 .. 2147483647  ) 
		MAX-ACCESS		read-only
		STATUS			current
		DESCRIPTION		"Column Description"
		::=  {  nptIsisInstanceEntry  1  }
		
	nptIsisInstanceName	OBJECT-TYPE	
		SYNTAX			DisplayString 
		MAX-ACCESS		read-only
		STATUS			current
		DESCRIPTION		"instance name"
		::=  {  nptIsisInstanceEntry  2  }

	nptIsisInstanceProtocol	OBJECT-TYPE	
		SYNTAX			Integer32 
		MAX-ACCESS		read-only
		STATUS			current
		DESCRIPTION		"Protocol to show muti-instance"
		::=  {  nptIsisInstanceEntry  3  }
		
	nptIsisInstanceLevel	OBJECT-TYPE	
		SYNTAX			Integer32
		MAX-ACCESS		read-only
		STATUS			current
		DESCRIPTION		"Isis level"
		::=  {  nptIsisInstanceEntry  4  }
		
	nptIsisInstanceLastUpTime	OBJECT-TYPE	
		SYNTAX			Integer32 
		MAX-ACCESS		read-only
		STATUS			current
		DESCRIPTION		"last time"
		::=  {  nptIsisInstanceEntry  5  }


	nptIsisInstanceElapsed	OBJECT-TYPE	
		SYNTAX			DisplayString 
		MAX-ACCESS		read-only
		STATUS			current
		DESCRIPTION		"dd:hh:mm:ss"
		::=  {  nptIsisInstanceEntry  6  }


	nptIsisInstanceCorruptedLsps	OBJECT-TYPE	
		SYNTAX			Counter64
		MAX-ACCESS		read-only
		STATUS			current
		DESCRIPTION		"Description"
		::=  {  nptIsisInstanceEntry  7  }


	nptIsisInstanceAuthTypeFails	OBJECT-TYPE	
		SYNTAX			Counter64
		MAX-ACCESS		read-only
		STATUS			current
		DESCRIPTION		"Description"
		::=  {  nptIsisInstanceEntry  8  }


	nptIsisInstanceAuthFails	OBJECT-TYPE	
		SYNTAX			Counter64
		MAX-ACCESS		read-only
		STATUS			current
		DESCRIPTION		"Description"
		::=  {  nptIsisInstanceEntry  9  }


	nptIsisInstanceDatabaseOverload	OBJECT-TYPE	
		SYNTAX			Counter64
		MAX-ACCESS		read-only
		STATUS			current
		DESCRIPTION		"Description"
		::=  {  nptIsisInstanceEntry  10  }


	nptIsisInstanceManAddrDrop	OBJECT-TYPE	
		SYNTAX			Counter64
		MAX-ACCESS		read-only
		STATUS			current
		DESCRIPTION		"Description"
		::=  {  nptIsisInstanceEntry  11  }


	nptIsisInstanceMaxSequence	OBJECT-TYPE	
		SYNTAX			Counter64
		MAX-ACCESS		read-only
		STATUS			current
		DESCRIPTION		"Description"
		::=  {  nptIsisInstanceEntry  12  }


	nptIsisInstanceSeqNumSkipped	OBJECT-TYPE	
		SYNTAX			Counter64
		MAX-ACCESS		read-only
		STATUS			current
		DESCRIPTION		"Description"
		::=  {  nptIsisInstanceEntry  13  }


    nptIsisInstanceOwnLspPurge	OBJECT-TYPE	
		SYNTAX			Counter64
		MAX-ACCESS		read-only
		STATUS			current
		DESCRIPTION		"Description"
		::=  {  nptIsisInstanceEntry  14  }

    nptIsisInstanceIdLenMismatch	OBJECT-TYPE	
		SYNTAX			Counter64
		MAX-ACCESS		read-only
		STATUS			current
		DESCRIPTION		"Description"
		::=  {  nptIsisInstanceEntry  15  }

    nptIsisInstancePartitionChange	OBJECT-TYPE	
		SYNTAX			Counter64
		MAX-ACCESS		read-only
		STATUS			current
		DESCRIPTION		"Description"
		::=  {  nptIsisInstanceEntry  16  }

    nptIsisInstanceSpfRuns	OBJECT-TYPE	
		SYNTAX			Counter64
		MAX-ACCESS		read-only
		STATUS			current
		DESCRIPTION		"Description"
		::=  {  nptIsisInstanceEntry  17  }

    nptIsisInstanceLspErrors	OBJECT-TYPE	
		SYNTAX			Counter64
		MAX-ACCESS		read-only
		STATUS			current
		DESCRIPTION		"Description"
		::=  {  nptIsisInstanceEntry  18  }

    nptIsisInstancePsnpErrors	OBJECT-TYPE	
		SYNTAX			Counter64
		MAX-ACCESS		read-only
		STATUS			current
		DESCRIPTION		"Description"
		::=  {  nptIsisInstanceEntry  19  }

    nptIsisInstanceCsnpErrors	OBJECT-TYPE	
		SYNTAX			Counter64
		MAX-ACCESS		read-only
		STATUS			current
		DESCRIPTION		"Description"
		::=  {  nptIsisInstanceEntry  20  }
		
	nptIsisLifTable	OBJECT-TYPE
		SYNTAX		SEQUENCE  OF  NptIsisLifEntry
		MAX-ACCESS	not-accessible
		STATUS		current
		DESCRIPTION	"Description"
		::=  { nptIsisLif  1 }

	nptIsisLifEntry	OBJECT-TYPE
		SYNTAX		NptIsisLifEntry
		MAX-ACCESS	not-accessible
		STATUS		current
		DESCRIPTION	"Row Description"
		INDEX		{  nptIsisLifIndex  }
		::=  { nptIsisLifTable 1 }

	NptIsisLifEntry  ::=  SEQUENCE {
	    nptIsisLifIndex  Integer32,
        nptIsisinstancename  DisplayString,
        nptIsisLifProtocolInstance  Integer32,
		nptIsisLifName  DisplayString,
        nptIsisLifLevel Integer32,
		nptIsisLifType  DisplayString,
		nptIsisLifDiscTime  DisplayString,
		nptIsisLifElapsed DisplayString,
	    nptIsisLifAdjacencyChanges  Counter64,
		nptIsisLifAdjacencyNumber  Counter64,
		nptIsisLifInitFails  Counter64,
		nptIsisLifAdjacencyRejects  Counter64,
		nptIsisLifIdLenMismatch  Counter64,
		nptIsisLifMaxAreaAddrMismatch  Counter64,
		nptIsisLifAuthenticationTypeFails  Counter64,
		nptIsisLifAuthenticationFails  Counter64,
		nptIsisLifLanDisChanges  Counter64,
		nptIsisLifLspRcv  Counter64,
		nptIsisLifLspSnt  Counter64,
		nptIsisLifLspDisc  Counter64,
		nptIsisLifCsnpRcv  Counter64,
		nptIsisLifCsnpSnt  Counter64,
		nptIsisLifCsnpDisc  Counter64,
		nptIsisLifPsnpRcv  Counter64,
		nptIsisLifPsnpSnt  Counter64,
		nptIsisLifPsnpDisc  Counter64,
		nptIsisLifIihRcv  Counter64,
		nptIsisLifIihSnt  Counter64,
		nptIsisLifIihDisc  Counter64,
		nptIsisLifIshRcv  Counter64,
		nptIsisLifIshSnt  Counter64,
		nptIsisLifEshRcv  Counter64,
		nptIsisLifEshSnt  Counter64,
		nptIsisLifUnknwnRcv  Counter64,
		nptIsisLifUnknwnSnt  Counter64
		}


	nptIsisLifIndex	OBJECT-TYPE	
		SYNTAX			Integer32  ( -2147483648 .. 2147483647  ) 
		MAX-ACCESS		read-only
		STATUS			current
		DESCRIPTION		"Column Description"
		::=  {  nptIsisLifEntry  1  }
		
	nptIsisinstancename	OBJECT-TYPE	
		SYNTAX			DisplayString 
		MAX-ACCESS		read-only
		STATUS			current
		DESCRIPTION		"isis instance name"
		::=  {  nptIsisLifEntry  2  }

	nptIsisLifProtocolInstance	OBJECT-TYPE	
		SYNTAX			Integer32 
		MAX-ACCESS		read-only
		STATUS			current
		DESCRIPTION		"isis ProtocolInstance"
		::=  {  nptIsisLifEntry  3  }

	nptIsisLifName	OBJECT-TYPE	
		SYNTAX			DisplayString 
		MAX-ACCESS		read-only
		STATUS			current
		DESCRIPTION		"isis lif name"
		::=  {  nptIsisLifEntry  4  }
        
	nptIsisLifLevel	OBJECT-TYPE	
		SYNTAX			Integer32 
		MAX-ACCESS		read-only
		STATUS			current
		DESCRIPTION		"isis level"
		::=  {  nptIsisLifEntry  5  }
		
	nptIsisLifType	OBJECT-TYPE	
		SYNTAX			DisplayString 
		MAX-ACCESS		read-only
		STATUS			current
		DESCRIPTION		"lif type"
		::=  {  nptIsisLifEntry  6  }


	nptIsisLifDiscTime	OBJECT-TYPE	
		SYNTAX			DisplayString 
		MAX-ACCESS		read-only
		STATUS			current
		DESCRIPTION		"last uptime"
		::=  {  nptIsisLifEntry  7  }


	nptIsisLifElapsed	OBJECT-TYPE	
		SYNTAX			DisplayString 
		MAX-ACCESS		read-only
		STATUS			current
		DESCRIPTION		"dd:hh:mm:ss"
		::=  {  nptIsisLifEntry  8  }


	nptIsisLifAdjacencyChanges	OBJECT-TYPE	
		SYNTAX			Counter64
		MAX-ACCESS		read-only
		STATUS			current
		DESCRIPTION		"Description"
		::=  {  nptIsisLifEntry  9  }


	nptIsisLifAdjacencyNumber	OBJECT-TYPE	
		SYNTAX			Counter64
		MAX-ACCESS		read-only
		STATUS			current
		DESCRIPTION		"Description"
		::=  {  nptIsisLifEntry  10  }


	nptIsisLifInitFails	OBJECT-TYPE	
		SYNTAX			Counter64
		MAX-ACCESS		read-only
		STATUS			current
		DESCRIPTION		"Description"
		::=  {  nptIsisLifEntry  11  }


	nptIsisLifAdjacencyRejects	OBJECT-TYPE	
		SYNTAX			Counter64
		MAX-ACCESS		read-only
		STATUS			current
		DESCRIPTION		"Description"
		::=  {  nptIsisLifEntry  12  }
		
	nptIsisLifIdLenMismatch	OBJECT-TYPE	
		SYNTAX			Counter64
		MAX-ACCESS		read-only
		STATUS			current
		DESCRIPTION		"Description"
		::=  {  nptIsisLifEntry  13  }
		
		
	nptIsisLifMaxAreaAddrMismatch	OBJECT-TYPE	
		SYNTAX			Counter64
		MAX-ACCESS		read-only
		STATUS			current
		DESCRIPTION		"Description"
		::=  {  nptIsisLifEntry  14  }


	nptIsisLifAuthenticationTypeFails	OBJECT-TYPE	
		SYNTAX			Counter64
		MAX-ACCESS		read-only
		STATUS			current
		DESCRIPTION		"Description"
		::=  {  nptIsisLifEntry  15  }


    nptIsisLifAuthenticationFails	OBJECT-TYPE	
		SYNTAX			Counter64
		MAX-ACCESS		read-only
		STATUS			current
		DESCRIPTION		"Description"
		::=  {  nptIsisLifEntry  16  }

    nptIsisLifLanDisChanges	OBJECT-TYPE	
		SYNTAX			Counter64
		MAX-ACCESS		read-only
		STATUS			current
		DESCRIPTION		"Description"
		::=  {  nptIsisLifEntry  17  }

    nptIsisLifLspRcv	OBJECT-TYPE	
		SYNTAX			Counter64
		MAX-ACCESS		read-only
		STATUS			current
		DESCRIPTION		"Description"
		::=  {  nptIsisLifEntry  18  }

    nptIsisLifLspSnt	OBJECT-TYPE	
		SYNTAX			Counter64
		MAX-ACCESS		read-only
		STATUS			current
		DESCRIPTION		"Description"
		::=  {  nptIsisLifEntry  19  }

    nptIsisLifLspDisc	OBJECT-TYPE	
		SYNTAX			Counter64
		MAX-ACCESS		read-only
		STATUS			current
		DESCRIPTION		"Description"
		::=  {  nptIsisLifEntry  20  }

    nptIsisLifCsnpRcv	OBJECT-TYPE	
		SYNTAX			Counter64
		MAX-ACCESS		read-only
		STATUS			current
		DESCRIPTION		"Description"
		::=  {  nptIsisLifEntry  21  }

    nptIsisLifCsnpSnt	OBJECT-TYPE	
		SYNTAX			Counter64
		MAX-ACCESS		read-only
		STATUS			current
		DESCRIPTION		"Description"
		::=  {  nptIsisLifEntry  22  }

    nptIsisLifCsnpDisc	OBJECT-TYPE	
		SYNTAX			Counter64
		MAX-ACCESS		read-only
		STATUS			current
		DESCRIPTION		"Description"
		::=  {  nptIsisLifEntry  23  }

    nptIsisLifPsnpRcv	OBJECT-TYPE	
		SYNTAX			Counter64
		MAX-ACCESS		read-only
		STATUS			current
		DESCRIPTION		"Description"
		::=  {  nptIsisLifEntry  24  }

    nptIsisLifPsnpSnt	OBJECT-TYPE	
		SYNTAX			Counter64
		MAX-ACCESS		read-only
		STATUS			current
		DESCRIPTION		"Description"
		::=  {  nptIsisLifEntry  25  }

    nptIsisLifPsnpDisc	OBJECT-TYPE	
		SYNTAX			Counter64
		MAX-ACCESS		read-only
		STATUS			current
		DESCRIPTION		"Description"
		::=  {  nptIsisLifEntry  26  }

    nptIsisLifIihRcv	OBJECT-TYPE	
		SYNTAX			Counter64
		MAX-ACCESS		read-only
		STATUS			current
		DESCRIPTION		"Description"
		::=  {  nptIsisLifEntry  27  }

    nptIsisLifIihSnt	OBJECT-TYPE	
		SYNTAX			Counter64
		MAX-ACCESS		read-only
		STATUS			current
		DESCRIPTION		"Description"
		::=  {  nptIsisLifEntry  28  }

    nptIsisLifIihDisc	OBJECT-TYPE	
		SYNTAX			Counter64
		MAX-ACCESS		read-only
		STATUS			current
		DESCRIPTION		"Description"
		::=  {  nptIsisLifEntry  29  }

    nptIsisLifIshRcv	OBJECT-TYPE	
		SYNTAX			Counter64
		MAX-ACCESS		read-only
		STATUS			current
		DESCRIPTION		"Description"
		::=  {  nptIsisLifEntry  30  }

    nptIsisLifIshSnt	OBJECT-TYPE	
		SYNTAX			Counter64
		MAX-ACCESS		read-only
		STATUS			current
		DESCRIPTION		"Description"
		::=  {  nptIsisLifEntry  31  }

    nptIsisLifEshRcv	OBJECT-TYPE	
		SYNTAX			Counter64
		MAX-ACCESS		read-only
		STATUS			current
		DESCRIPTION		"Description"
		::=  {  nptIsisLifEntry  32  }

    nptIsisLifEshSnt	OBJECT-TYPE	
		SYNTAX			Counter64
		MAX-ACCESS		read-only
		STATUS			current
		DESCRIPTION		"Description"
		::=  {  nptIsisLifEntry  33  }

    nptIsisLifUnknwnRcv	OBJECT-TYPE	
		SYNTAX			Counter64
		MAX-ACCESS		read-only
		STATUS			current
		DESCRIPTION		"Description"
		::=  {  nptIsisLifEntry  34  }

    nptIsisLifUnknwnSnt	OBJECT-TYPE	
		SYNTAX			Counter64
		MAX-ACCESS		read-only
		STATUS			current
		DESCRIPTION		"Description"
		::=  {  nptIsisLifEntry  35  }
		
	nptBfdSwitchTable	OBJECT-TYPE
		SYNTAX		SEQUENCE  OF  NptBfdSwitchEntry
		MAX-ACCESS	not-accessible
		STATUS		current
		DESCRIPTION	"Description"
		::=  { nptBfdSwitch  1 }

	nptBfdSwitchEntry	OBJECT-TYPE
		SYNTAX		NptBfdSwitchEntry
		MAX-ACCESS	not-accessible
		STATUS		current
		DESCRIPTION	"Row Description"
		INDEX		{  nptBfdSwitchIndex  }
		::=  { nptBfdSwitchTable 1 }

	NptBfdSwitchEntry  ::=  SEQUENCE {
	    nptBfdSwitchIndex  Integer32,
		nptBfdSwitchDisContinuityTime  DisplayString,
		nptBfdSwitchElapsed DisplayString,
		nptBfdSwitchUnknownControlPackets Counter64
		}


	nptBfdSwitchIndex	OBJECT-TYPE	
		SYNTAX			Integer32  ( -2147483648 .. 2147483647  ) 
		MAX-ACCESS		read-only
		STATUS			current
		DESCRIPTION		"Column Description"
		::=  {  nptBfdSwitchEntry  1  }
		
	nptBfdSwitchDisContinuityTime	OBJECT-TYPE	
		SYNTAX			DisplayString
		MAX-ACCESS		read-only
		STATUS			current
		DESCRIPTION		"DisContinuity Time"
		::=  {  nptBfdSwitchEntry  2  }
		
	nptBfdSwitchElapsed	OBJECT-TYPE	
		SYNTAX			DisplayString 
		MAX-ACCESS		read-only
		STATUS			current
		DESCRIPTION		"dd:hh:mm:ss"
		::=  {  nptBfdSwitchEntry  3  }


	nptBfdSwitchUnknownControlPackets	OBJECT-TYPE	
		SYNTAX			Counter64
		MAX-ACCESS		read-only
		STATUS			current
		DESCRIPTION		"Unknown Control Packets"
		::=  {  nptBfdSwitchEntry  4  }
		
	nptBfdPseudowireTable	OBJECT-TYPE
		SYNTAX		SEQUENCE  OF  NptBfdPseudowireEntry
		MAX-ACCESS	not-accessible
		STATUS		current
		DESCRIPTION	"Description"
		::=  { nptBfdPseudowire  1 }

	nptBfdPseudowireEntry	OBJECT-TYPE
		SYNTAX		NptBfdPseudowireEntry
		MAX-ACCESS	not-accessible
		STATUS		current
		DESCRIPTION	"Row Description"
		INDEX		{  nptBfdPseudowireIndex  }
		::=  { nptBfdPseudowireTable 1 }

	NptBfdPseudowireEntry  ::=  SEQUENCE {
	    nptBfdPseudowireIndex  Integer32,
        nptBfdPseudowireInstanceName  DisplayString,
        nptBfdPseudowirePeerAddress  DisplayString,
        nptBfdPseudowirePeerRole  DisplayString,
		nptBfdPseudowireDisContinuityTime  DisplayString,
		nptBfdPseudowireElapsed DisplayString,
		nptBfdPseudowireRxPackets Counter64,
		nptBfdPseudowireTxPackets Counter64,
		nptBfdPseudowireRxInvalidPackets Counter64
		}


	nptBfdPseudowireIndex	OBJECT-TYPE	
		SYNTAX			Integer32  ( -2147483648 .. 2147483647  ) 
		MAX-ACCESS		read-only
		STATUS			current
		DESCRIPTION		"Column Description"
		::=  {  nptBfdPseudowireEntry  1  }
		
	nptBfdPseudowireInstanceName	OBJECT-TYPE	
		SYNTAX			DisplayString 
		MAX-ACCESS		read-only
		STATUS			current
		DESCRIPTION		"instance name"
		::=  {  nptBfdPseudowireEntry  2  }


	nptBfdPseudowirePeerAddress	OBJECT-TYPE	
		SYNTAX			DisplayString 
		MAX-ACCESS		read-only
		STATUS			current
		DESCRIPTION		"Peer Address"
		::=  {  nptBfdPseudowireEntry  3  }

    nptBfdPseudowirePeerRole	OBJECT-TYPE	
		SYNTAX			DisplayString
		MAX-ACCESS		read-only
		STATUS			current
		DESCRIPTION		"Primary|Secondary"
		::=  {  nptBfdPseudowireEntry  4  }

    nptBfdPseudowireDisContinuityTime	OBJECT-TYPE	
		SYNTAX			DisplayString
		MAX-ACCESS		read-only
		STATUS			current
		DESCRIPTION		"DisContinuity Time"
		::=  {  nptBfdPseudowireEntry  5  }
		
		
	nptBfdPseudowireElapsed	OBJECT-TYPE	
		SYNTAX			DisplayString 
		MAX-ACCESS		read-only
		STATUS			current
		DESCRIPTION		"dd:hh:mm:ss"
		::=  {  nptBfdPseudowireEntry  6  }


    nptBfdPseudowireRxPackets	OBJECT-TYPE	
		SYNTAX			Counter64
		MAX-ACCESS		read-only
		STATUS			current
		DESCRIPTION		"Description"
		::=  {  nptBfdPseudowireEntry  7  }

    nptBfdPseudowireTxPackets	OBJECT-TYPE	
		SYNTAX			Counter64
		MAX-ACCESS		read-only
		STATUS			current
		DESCRIPTION		"Description"
		::=  {  nptBfdPseudowireEntry  8  }

    nptBfdPseudowireRxInvalidPackets	OBJECT-TYPE	
		SYNTAX			Counter64
		MAX-ACCESS		read-only
		STATUS			current
		DESCRIPTION		"Description"
		::=  {  nptBfdPseudowireEntry  9  }
		
	nptBfdSectionTable	OBJECT-TYPE
		SYNTAX		SEQUENCE  OF  NptBfdSectionEntry
		MAX-ACCESS	not-accessible
		STATUS		current
		DESCRIPTION	"Description"
		::=  { nptBfdSection  1 }

	nptBfdSectionEntry	OBJECT-TYPE
		SYNTAX		NptBfdSectionEntry
		MAX-ACCESS	not-accessible
		STATUS		current
		DESCRIPTION	"Row Description"
		INDEX		{  nptBfdSectionIndex  }
		::=  { nptBfdSectionTable 1 }

	NptBfdSectionEntry  ::=  SEQUENCE {
	    nptBfdSectionIndex  Integer32,
        nptBfdSectionInterface  DisplayString,
		nptBfdSectionDisContinuityTime  DisplayString,
		nptBfdSectionElapsed DisplayString,
		nptBfdSectionRxPackets Counter64,
		nptBfdSectionTxPackets Counter64,
		nptBfdSectionRxInvalidPackets Counter64
		}


	nptBfdSectionIndex	OBJECT-TYPE	
		SYNTAX			Integer32  ( -2147483648 .. 2147483647  ) 
		MAX-ACCESS		read-only
		STATUS			current
		DESCRIPTION		"Column Description"
		::=  {  nptBfdSectionEntry  1  }
		
	nptBfdSectionInterface	OBJECT-TYPE	
		SYNTAX			DisplayString 
		MAX-ACCESS		read-only
		STATUS			current
		DESCRIPTION		"interface name"
		::=  {  nptBfdSectionEntry  2  }


    nptBfdSectionDisContinuityTime	OBJECT-TYPE	
		SYNTAX			DisplayString
		MAX-ACCESS		read-only
		STATUS			current
		DESCRIPTION		"DisContinuity Time"
		::=  {  nptBfdSectionEntry  3  }

    nptBfdSectionElapsed	OBJECT-TYPE	
		SYNTAX			DisplayString 
		MAX-ACCESS		read-only
		STATUS			current
		DESCRIPTION		"dd:hh:mm:ss"
		::=  {  nptBfdSectionEntry  4  }


    nptBfdSectionRxPackets	OBJECT-TYPE	
		SYNTAX			Counter64
		MAX-ACCESS		read-only
		STATUS			current
		DESCRIPTION		"Description"
		::=  {  nptBfdSectionEntry  5  }

    nptBfdSectionTxPackets	OBJECT-TYPE	
		SYNTAX			Counter64
		MAX-ACCESS		read-only
		STATUS			current
		DESCRIPTION		"Description"
		::=  {  nptBfdSectionEntry  6  }

    nptBfdSectionRxInvalidPackets	OBJECT-TYPE	
		SYNTAX			Counter64
		MAX-ACCESS		read-only
		STATUS			current
		DESCRIPTION		"Description"
		::=  {  nptBfdSectionEntry  7  }
		
	nptBfdSingleHopIPTable	OBJECT-TYPE
		SYNTAX		SEQUENCE  OF  NptBfdSingleHopIPEntry
		MAX-ACCESS	not-accessible
		STATUS		current
		DESCRIPTION	"Description"
		::=  { nptBfdSingleHopIP  1 }

	nptBfdSingleHopIPEntry	OBJECT-TYPE
		SYNTAX		NptBfdSingleHopIPEntry
		MAX-ACCESS	not-accessible
		STATUS		current
		DESCRIPTION	"Row Description"
		INDEX		{  nptBfdSingleHopIPIndex  }
		::=  { nptBfdSingleHopIPTable 1 }

	NptBfdSingleHopIPEntry  ::=  SEQUENCE {
	    nptBfdSingleHopIPIndex  Integer32,
		nptBfdSingleHopIPSessions  DisplayString,
        nptBfdSingleHopIPInterface  DisplayString,
        nptBfdSingleHopIPPeerAddress  DisplayString,
		nptBfdSingleHopIPDisContinuityTime  DisplayString,
		nptBfdSingleHopIPElapsed DisplayString,
		nptBfdSingleHopIPRxPackets Counter64,
		nptBfdSingleHopIPTxPackets Counter64,
		nptBfdSingleHopIPRxInvalidPackets Counter64
		}


	nptBfdSingleHopIPIndex	OBJECT-TYPE	
		SYNTAX			Integer32  ( -2147483648 .. 2147483647  ) 
		MAX-ACCESS		read-only
		STATUS			current
		DESCRIPTION		"Column Description"
		::=  {  nptBfdSingleHopIPEntry  1  }
		
	nptBfdSingleHopIPSessions	OBJECT-TYPE	
		SYNTAX			DisplayString 
		MAX-ACCESS		read-only
		STATUS			current
		DESCRIPTION		"Auto|Manual"
		::=  {  nptBfdSingleHopIPEntry  2  }
		
	nptBfdSingleHopIPInterface	OBJECT-TYPE	
		SYNTAX			DisplayString 
		MAX-ACCESS		read-only
		STATUS			current
		DESCRIPTION		"interface name"
		::=  {  nptBfdSingleHopIPEntry  3  }

    nptBfdSingleHopIPPeerAddress	OBJECT-TYPE	
		SYNTAX			DisplayString 
		MAX-ACCESS		read-only
		STATUS			current
		DESCRIPTION		"Peer Address"
		::=  {  nptBfdSingleHopIPEntry  4  }


    nptBfdSingleHopIPDisContinuityTime	OBJECT-TYPE	
		SYNTAX			DisplayString
		MAX-ACCESS		read-only
		STATUS			current
		DESCRIPTION		"DisContinuity Time"
		::=  {  nptBfdSingleHopIPEntry  5  }

    nptBfdSingleHopIPElapsed	OBJECT-TYPE	
		SYNTAX			DisplayString 
		MAX-ACCESS		read-only
		STATUS			current
		DESCRIPTION		"dd:hh:mm:ss"
		::=  {  nptBfdSingleHopIPEntry  6  }


    nptBfdSingleHopIPRxPackets	OBJECT-TYPE	
		SYNTAX			Counter64
		MAX-ACCESS		read-only
		STATUS			current
		DESCRIPTION		"Description"
		::=  {  nptBfdSingleHopIPEntry  7  }

    nptBfdSingleHopIPTxPackets	OBJECT-TYPE	
		SYNTAX			Counter64
		MAX-ACCESS		read-only
		STATUS			current
		DESCRIPTION		"Description"
		::=  {  nptBfdSingleHopIPEntry  8  }

    nptBfdSingleHopIPRxInvalidPackets	OBJECT-TYPE	
		SYNTAX			Counter64
		MAX-ACCESS		read-only
		STATUS			current
		DESCRIPTION		"Description"
		::=  {  nptBfdSingleHopIPEntry  9  }
		
	nptBfdMPLSTPTunnelTable	OBJECT-TYPE
		SYNTAX		SEQUENCE  OF  NptBfdMPLSTPTunnelEntry
		MAX-ACCESS	not-accessible
		STATUS		current
		DESCRIPTION	"Description"
		::=  { nptBfdMPLSTPTunnel  1 }

	nptBfdMPLSTPTunnelEntry	OBJECT-TYPE
		SYNTAX		NptBfdMPLSTPTunnelEntry
		MAX-ACCESS	not-accessible
		STATUS		current
		DESCRIPTION	"Row Description"
		INDEX		{  nptBfdMPLSTPTunnelIndex  }
		::=  { nptBfdMPLSTPTunnelTable 1 }

	NptBfdMPLSTPTunnelEntry  ::=  SEQUENCE {
	    nptBfdMPLSTPTunnelIndex  Integer32,
        nptBfdMPLSTPTunnelName  DisplayString,
        nptBfdMPLSTPTunnelLspRole  DisplayString,
		nptBfdMPLSTPTunnelDisContinuityTime  DisplayString,
		nptBfdMPLSTPTunnelElapsed DisplayString,
		nptBfdMPLSTPTunnelRxPackets Counter64,
		nptBfdMPLSTPTunnelTxPackets Counter64,
		nptBfdMPLSTPTunnelRxInvalidPackets Counter64
		}


	nptBfdMPLSTPTunnelIndex	OBJECT-TYPE	
		SYNTAX			Integer32  ( -2147483648 .. 2147483647  ) 
		MAX-ACCESS		read-only
		STATUS			current
		DESCRIPTION		"Column Description"
		::=  {  nptBfdMPLSTPTunnelEntry  1  }
		
	nptBfdMPLSTPTunnelName	OBJECT-TYPE	
		SYNTAX			DisplayString 
		MAX-ACCESS		read-only
		STATUS			current
		DESCRIPTION		"tunnel name"
		::=  {  nptBfdMPLSTPTunnelEntry  2  }

    nptBfdMPLSTPTunnelLspRole	OBJECT-TYPE	
		SYNTAX			DisplayString 
		MAX-ACCESS		read-only
		STATUS			current
		DESCRIPTION		"Working|Protection"
		::=  {  nptBfdMPLSTPTunnelEntry  3  }


    nptBfdMPLSTPTunnelDisContinuityTime	OBJECT-TYPE	
		SYNTAX			DisplayString
		MAX-ACCESS		read-only
		STATUS			current
		DESCRIPTION		"DisContinuity Time"
		::=  {  nptBfdMPLSTPTunnelEntry  4  }

    nptBfdMPLSTPTunnelElapsed	OBJECT-TYPE	
		SYNTAX			DisplayString 
		MAX-ACCESS		read-only
		STATUS			current
		DESCRIPTION		"dd:hh:mm:ss"
		::=  {  nptBfdMPLSTPTunnelEntry  5  }


    nptBfdMPLSTPTunnelRxPackets	OBJECT-TYPE	
		SYNTAX			Counter64
		MAX-ACCESS		read-only
		STATUS			current
		DESCRIPTION		"Description"
		::=  {  nptBfdMPLSTPTunnelEntry  6  }

    nptBfdMPLSTPTunnelTxPackets	OBJECT-TYPE	
		SYNTAX			Counter64
		MAX-ACCESS		read-only
		STATUS			current
		DESCRIPTION		"Description"
		::=  {  nptBfdMPLSTPTunnelEntry  7  }

    nptBfdMPLSTPTunnelRxInvalidPackets	OBJECT-TYPE	
		SYNTAX			Counter64
		MAX-ACCESS		read-only
		STATUS			current
		DESCRIPTION		"Description"
		::=  {  nptBfdMPLSTPTunnelEntry  8  }
		
	nptLDITable	OBJECT-TYPE
		SYNTAX		SEQUENCE  OF  NptLDIEntry
		MAX-ACCESS	not-accessible
		STATUS		current
		DESCRIPTION	"Description"
		::=  { nptLDI  1 }

	nptLDIEntry	OBJECT-TYPE
		SYNTAX		NptLDIEntry
		MAX-ACCESS	not-accessible
		STATUS		current
		DESCRIPTION	"Row Description"
		INDEX		{  nptLDIIndex  }
		::=  { nptLDITable 1 }

	NptLDIEntry  ::=  SEQUENCE {
	    nptLDIIndex  Integer32,
        nptLDIName  DisplayString,
        nptLDILspRole  Integer32,
		nptLDIRxPackets Counter64,
		nptLDITxPackets Counter64,
		nptLDIRxInvalidPackets Counter64
		}


	nptLDIIndex	OBJECT-TYPE	
		SYNTAX			Integer32  ( -2147483648 .. 2147483647  ) 
		MAX-ACCESS		read-only
		STATUS			current
		DESCRIPTION		"Column Description"
		::=  {  nptLDIEntry  1  }
		
	nptLDIName	OBJECT-TYPE	
		SYNTAX			DisplayString 
		MAX-ACCESS		read-only
		STATUS			current
		DESCRIPTION		"tunnel name"
		::=  {  nptLDIEntry  2  }

    nptLDILspRole	OBJECT-TYPE	
		SYNTAX			Integer32 
		MAX-ACCESS		read-only
		STATUS			current
		DESCRIPTION		"Primary|Secondary"
		::=  {  nptLDIEntry  3  }


    nptLDIRxPackets	OBJECT-TYPE	
		SYNTAX			Counter64
		MAX-ACCESS		read-only
		STATUS			current
		DESCRIPTION		"Description"
		::=  {  nptLDIEntry  4  }

    nptLDITxPackets	OBJECT-TYPE	
		SYNTAX			Counter64
		MAX-ACCESS		read-only
		STATUS			current
		DESCRIPTION		"Description"
		::=  {  nptLDIEntry  5  }

    nptLDIRxInvalidPackets	OBJECT-TYPE	
		SYNTAX			Counter64
		MAX-ACCESS		read-only
		STATUS			current
		DESCRIPTION		"Description"
		::=  {  nptLDIEntry  6  }
		
	nptMSTPTable	OBJECT-TYPE
		SYNTAX		SEQUENCE  OF  NptMSTPEntry
		MAX-ACCESS	not-accessible
		STATUS		current
		DESCRIPTION	"Description"
		::=  { nptMSTP  1 }

	nptMSTPEntry	OBJECT-TYPE
		SYNTAX		NptMSTPEntry
		MAX-ACCESS	not-accessible
		STATUS		current
		DESCRIPTION	"Row Description"
		INDEX		{  nptMSTPIndex  }
		::=  { nptMSTPTable 1 }

	NptMSTPEntry  ::=  SEQUENCE {
	    nptMSTPIndex  Integer32,
        nptMSTPInterface  DisplayString,
		nptMSTPDisContinuityTime  DisplayString,
		nptMSTPElapsed DisplayString,
		nptMSTPRXConfigBPDU Counter64,
		nptMSTPRXRSTPBPDU Counter64,
		nptMSTPRXTCNBPDU Counter64,
		nptMSTPTXBPDU Counter64
		}


	nptMSTPIndex	OBJECT-TYPE	
		SYNTAX			Integer32  ( -2147483648 .. 2147483647  ) 
		MAX-ACCESS		read-only
		STATUS			current
		DESCRIPTION		"Column Description"
		::=  {  nptMSTPEntry  1  }
		
	nptMSTPInterface	OBJECT-TYPE	
		SYNTAX			DisplayString 
		MAX-ACCESS		read-only
		STATUS			current
		DESCRIPTION		"interface name"
		::=  {  nptMSTPEntry  2  }


    nptMSTPDisContinuityTime	OBJECT-TYPE	
		SYNTAX			DisplayString
		MAX-ACCESS		read-only
		STATUS			current
		DESCRIPTION		"DisContinuity Time"
		::=  {  nptMSTPEntry  3  }

    nptMSTPElapsed	OBJECT-TYPE	
		SYNTAX			DisplayString 
		MAX-ACCESS		read-only
		STATUS			current
		DESCRIPTION		"dd:hh:mm:ss"
		::=  {  nptMSTPEntry  4  }


    nptMSTPRXConfigBPDU	OBJECT-TYPE	
		SYNTAX			Counter64
		MAX-ACCESS		read-only
		STATUS			current
		DESCRIPTION		"Description"
		::=  {  nptMSTPEntry  5  }

    nptMSTPRXRSTPBPDU	OBJECT-TYPE	
		SYNTAX			Counter64
		MAX-ACCESS		read-only
		STATUS			current
		DESCRIPTION		"Description"
		::=  {  nptMSTPEntry  6  }

    nptMSTPRXTCNBPDU	OBJECT-TYPE	
		SYNTAX			Counter64
		MAX-ACCESS		read-only
		STATUS			current
		DESCRIPTION		"Description"
		::=  {  nptMSTPEntry  7  }

    nptMSTPTXBPDU	OBJECT-TYPE	
		SYNTAX			Counter64
		MAX-ACCESS		read-only
		STATUS			current
		DESCRIPTION		"Description"
		::=  {  nptMSTPEntry  8  }
		
	nptLAGTable	OBJECT-TYPE
		SYNTAX		SEQUENCE  OF  NptLAGEntry
		MAX-ACCESS	not-accessible
		STATUS		current
		DESCRIPTION	"Description"
		::=  { nptLAG  1 }

	nptLAGEntry	OBJECT-TYPE
		SYNTAX		NptLAGEntry
		MAX-ACCESS	not-accessible
		STATUS		current
		DESCRIPTION	"Row Description"
		INDEX		{  nptLAGIndex  }
		::=  { nptLAGTable 1 }

	NptLAGEntry  ::=  SEQUENCE {
	    nptLAGIndex  Integer32,
        nptLAGBundleName  DisplayString,
		nptLAGDisContinuityTime  DisplayString,
		nptLAGElapsed DisplayString,
		nptLAGRxOctets Counter64,
		nptLAGRxPkts Counter64,
		nptLAGRxBroadcastPkts Counter64,
		nptLAGRxMulticastPkts Counter64,
		nptLAGTxOctets Counter64,
		nptLAGTxPkts Counter64,
		nptLAGRxErrorPkts Counter64,
		nptLAGRxPkts64 Counter64,
		nptLAGRxPkts65To127 Counter64,
		nptLAGRxPkts128To255 Counter64,
		nptLAGRxPkts256To511 Counter64,
		nptLAGRxPkts512To1023 Counter64,
		nptLAGRxPktsOver1024 Counter64,
		nptLAGRxPausePkts Counter64,
		nptLAGRxCrcAlignErrorPkts Counter64,
		nptLAGRxUndersizePkts Counter64,
		nptLAGRxOversizePkts Counter64,
		nptLAGRxFragments Counter64,
		nptLAGRxJabberPkts Counter64,
		nptLAGCollisionErrors Counter64
		}


	nptLAGIndex	OBJECT-TYPE	
		SYNTAX			Integer32  ( -2147483648 .. 2147483647  ) 
		MAX-ACCESS		read-only
		STATUS			current
		DESCRIPTION		"Column Description"
		::=  {  nptLAGEntry  1  }
		
	nptLAGBundleName	OBJECT-TYPE	
		SYNTAX			DisplayString 
		MAX-ACCESS		read-only
		STATUS			current
		DESCRIPTION		"bundle name"
		::=  {  nptLAGEntry  2  }


    nptLAGDisContinuityTime	OBJECT-TYPE	
		SYNTAX			DisplayString
		MAX-ACCESS		read-only
		STATUS			current
		DESCRIPTION		"DisContinuity Time"
		::=  {  nptLAGEntry  3  }

    nptLAGElapsed	OBJECT-TYPE	
		SYNTAX			DisplayString 
		MAX-ACCESS		read-only
		STATUS			current
		DESCRIPTION		"dd:hh:mm:ss"
		::=  {  nptLAGEntry  4  }


    nptLAGRxOctets	OBJECT-TYPE	
		SYNTAX			Counter64
		MAX-ACCESS		read-only
		STATUS			current
		DESCRIPTION		"Description"
		::=  {  nptLAGEntry  5  }

    nptLAGRxPkts	OBJECT-TYPE	
		SYNTAX			Counter64
		MAX-ACCESS		read-only
		STATUS			current
		DESCRIPTION		"Description"
		::=  {  nptLAGEntry  6  }

    nptLAGRxBroadcastPkts	OBJECT-TYPE	
		SYNTAX			Counter64
		MAX-ACCESS		read-only
		STATUS			current
		DESCRIPTION		"Description"
		::=  {  nptLAGEntry  7  }

    nptLAGRxMulticastPkts	OBJECT-TYPE	
		SYNTAX			Counter64
		MAX-ACCESS		read-only
		STATUS			current
		DESCRIPTION		"Description"
		::=  {  nptLAGEntry  8  }

    nptLAGTxOctets	OBJECT-TYPE	
		SYNTAX			Counter64
		MAX-ACCESS		read-only
		STATUS			current
		DESCRIPTION		"Description"
		::=  {  nptLAGEntry  9  }

    nptLAGTxPkts	OBJECT-TYPE	
		SYNTAX			Counter64
		MAX-ACCESS		read-only
		STATUS			current
		DESCRIPTION		"Description"
		::=  {  nptLAGEntry  10  }

    nptLAGRxErrorPkts	OBJECT-TYPE	
		SYNTAX			Counter64
		MAX-ACCESS		read-only
		STATUS			current
		DESCRIPTION		"Description"
		::=  {  nptLAGEntry  11  }

    nptLAGRxPkts64	OBJECT-TYPE	
		SYNTAX			Counter64
		MAX-ACCESS		read-only
		STATUS			current
		DESCRIPTION		"Description"
		::=  {  nptLAGEntry  12  }

    nptLAGRxPkts65To127	OBJECT-TYPE	
		SYNTAX			Counter64
		MAX-ACCESS		read-only
		STATUS			current
		DESCRIPTION		"Description"
		::=  {  nptLAGEntry  13  }

    nptLAGRxPkts128To255	OBJECT-TYPE	
		SYNTAX			Counter64
		MAX-ACCESS		read-only
		STATUS			current
		DESCRIPTION		"Description"
		::=  {  nptLAGEntry  14  }

    nptLAGRxPkts256To511	OBJECT-TYPE	
		SYNTAX			Counter64
		MAX-ACCESS		read-only
		STATUS			current
		DESCRIPTION		"Description"
		::=  {  nptLAGEntry  15  }

    nptLAGRxPkts512To1023	OBJECT-TYPE	
		SYNTAX			Counter64
		MAX-ACCESS		read-only
		STATUS			current
		DESCRIPTION		"Description"
		::=  {  nptLAGEntry  16  }

    nptLAGRxPktsOver1024	OBJECT-TYPE	
		SYNTAX			Counter64
		MAX-ACCESS		read-only
		STATUS			current
		DESCRIPTION		"Description"
		::=  {  nptLAGEntry  17  }

    nptLAGRxPausePkts	OBJECT-TYPE	
		SYNTAX			Counter64
		MAX-ACCESS		read-only
		STATUS			current
		DESCRIPTION		"Description"
		::=  {  nptLAGEntry  18  }


    nptLAGRxCrcAlignErrorPkts	OBJECT-TYPE	
		SYNTAX			Counter64
		MAX-ACCESS		read-only
		STATUS			current
		DESCRIPTION		"Description"
		::=  {  nptLAGEntry  19  }

    nptLAGRxUndersizePkts	OBJECT-TYPE	
		SYNTAX			Counter64
		MAX-ACCESS		read-only
		STATUS			current
		DESCRIPTION		"Description"
		::=  {  nptLAGEntry  20  }

    nptLAGRxOversizePkts	OBJECT-TYPE	
		SYNTAX			Counter64
		MAX-ACCESS		read-only
		STATUS			current
		DESCRIPTION		"Description"
		::=  {  nptLAGEntry  21  }

    nptLAGRxFragments	OBJECT-TYPE	
		SYNTAX			Counter64
		MAX-ACCESS		read-only
		STATUS			current
		DESCRIPTION		"Description"
		::=  {  nptLAGEntry  22  }

    nptLAGRxJabberPkts	OBJECT-TYPE	
		SYNTAX			Counter64
		MAX-ACCESS		read-only
		STATUS			current
		DESCRIPTION		"Description"
		::=  {  nptLAGEntry  23  }

    nptLAGCollisionErrors	OBJECT-TYPE	
		SYNTAX			Counter64
		MAX-ACCESS		read-only
		STATUS			current
		DESCRIPTION		"Description"
		::=  {  nptLAGEntry  24  }
		
	nptLAGPortTable	OBJECT-TYPE
		SYNTAX		SEQUENCE  OF  NptLAGPortEntry
		MAX-ACCESS	not-accessible
		STATUS		current
		DESCRIPTION	"Description"
		::=  { nptLAGPort  1 }

	nptLAGPortEntry	OBJECT-TYPE
		SYNTAX		NptLAGPortEntry
		MAX-ACCESS	not-accessible
		STATUS		current
		DESCRIPTION	"Row Description"
		INDEX		{  nptLAGPortIndex  }
		::=  { nptLAGPortTable 1 }

	NptLAGPortEntry  ::=  SEQUENCE {
	    nptLAGPortIndex  Integer32,
        nptLAGPortBundleName  DisplayString,
        nptLAGPortIfName  DisplayString,
		nptLAGPortDisContinuityTime  DisplayString,
		nptLAGPortElapsed DisplayString,
		nptLAGPortStatsID Counter64,
		nptLAGPortLACPDUsRx Counter64,
		nptLAGPortMarkerPDUsRx Counter64,
		nptLAGPortMarkerResponsePDUsRx Counter64,
		nptLAGPortUnknownRx Counter64,
		nptLAGPortIllegalRx Counter64,
		nptLAGPortLACPDUsTx Counter64,
		nptLAGPortMarkerPDUsTx Counter64,
		nptLAGPortMarkerResponsePDUsTx Counter64
		}


	nptLAGPortIndex	OBJECT-TYPE	
		SYNTAX			Integer32  ( -2147483648 .. 2147483647  ) 
		MAX-ACCESS		read-only
		STATUS			current
		DESCRIPTION		"Column Description"
		::=  {  nptLAGPortEntry  1  }
		
	nptLAGPortBundleName	OBJECT-TYPE	
		SYNTAX			DisplayString 
		MAX-ACCESS		read-only
		STATUS			current
		DESCRIPTION		"bundle name"
		::=  {  nptLAGPortEntry  2  }

    nptLAGPortIfName	OBJECT-TYPE	
		SYNTAX			DisplayString 
		MAX-ACCESS		read-only
		STATUS			current
		DESCRIPTION		"if name"
		::=  {  nptLAGPortEntry  3  }


    nptLAGPortDisContinuityTime	OBJECT-TYPE	
		SYNTAX			DisplayString
		MAX-ACCESS		read-only
		STATUS			current
		DESCRIPTION		"DisContinuity Time"
		::=  {  nptLAGPortEntry  4  }

    nptLAGPortElapsed	OBJECT-TYPE	
		SYNTAX			DisplayString 
		MAX-ACCESS		read-only
		STATUS			current
		DESCRIPTION		"dd:hh:mm:ss"
		::=  {  nptLAGPortEntry  5  }


    nptLAGPortStatsID	OBJECT-TYPE	
		SYNTAX			Counter64
		MAX-ACCESS		read-only
		STATUS			current
		DESCRIPTION		"Description"
		::=  {  nptLAGPortEntry  6  }

    nptLAGPortLACPDUsRx	OBJECT-TYPE	
		SYNTAX			Counter64
		MAX-ACCESS		read-only
		STATUS			current
		DESCRIPTION		"Description"
		::=  {  nptLAGPortEntry  7  }

    nptLAGPortMarkerPDUsRx	OBJECT-TYPE	
		SYNTAX			Counter64
		MAX-ACCESS		read-only
		STATUS			current
		DESCRIPTION		"Description"
		::=  {  nptLAGPortEntry  8  }

    nptLAGPortMarkerResponsePDUsRx	OBJECT-TYPE	
		SYNTAX			Counter64
		MAX-ACCESS		read-only
		STATUS			current
		DESCRIPTION		"Description"
		::=  {  nptLAGPortEntry  9  }

    nptLAGPortUnknownRx	OBJECT-TYPE	
		SYNTAX			Counter64
		MAX-ACCESS		read-only
		STATUS			current
		DESCRIPTION		"Description"
		::=  {  nptLAGPortEntry  10  }

    nptLAGPortIllegalRx	OBJECT-TYPE	
		SYNTAX			Counter64
		MAX-ACCESS		read-only
		STATUS			current
		DESCRIPTION		"Description"
		::=  {  nptLAGPortEntry  11  }

    nptLAGPortLACPDUsTx	OBJECT-TYPE	
		SYNTAX			Counter64
		MAX-ACCESS		read-only
		STATUS			current
		DESCRIPTION		"Description"
		::=  {  nptLAGPortEntry  12  }

    nptLAGPortMarkerPDUsTx	OBJECT-TYPE	
		SYNTAX			Counter64
		MAX-ACCESS		read-only
		STATUS			current
		DESCRIPTION		"Description"
		::=  {  nptLAGPortEntry  13  }

    nptLAGPortMarkerResponsePDUsTx	OBJECT-TYPE	
		SYNTAX			Counter64
		MAX-ACCESS		read-only
		STATUS			current
		DESCRIPTION		"Description"
		::=  {  nptLAGPortEntry  14  }
		
	nptMcLAGTable	OBJECT-TYPE
		SYNTAX		SEQUENCE  OF  NptMcLAGEntry
		MAX-ACCESS	not-accessible
		STATUS		current
		DESCRIPTION	"Description"
		::=  { nptMcLAG  1 }

	nptMcLAGEntry	OBJECT-TYPE
		SYNTAX		NptMcLAGEntry
		MAX-ACCESS	not-accessible
		STATUS		current
		DESCRIPTION	"Row Description"
		INDEX		{  nptMcLAGIndex  }
		::=  { nptMcLAGTable 1 }

	NptMcLAGEntry  ::=  SEQUENCE {
	    nptMcLAGIndex  Integer32,
        nptMcLAGBundleName  DisplayString,
		nptMcLAGDisContinuityTime  DisplayString,
		nptMcLAGElapsed DisplayString,
		nptMcLAGFramesTx Counter64,
		nptMcLAGFramesRx Counter64,
		nptMcLAGInvalidFramesRx Counter64
		}


	nptMcLAGIndex	OBJECT-TYPE	
		SYNTAX			Integer32  ( -2147483648 .. 2147483647  ) 
		MAX-ACCESS		read-only
		STATUS			current
		DESCRIPTION		"Column Description"
		::=  {  nptMcLAGEntry  1  }
		
	nptMcLAGBundleName	OBJECT-TYPE	
		SYNTAX			DisplayString 
		MAX-ACCESS		read-only
		STATUS			current
		DESCRIPTION		"bundle name"
		::=  {  nptMcLAGEntry  2  }


    nptMcLAGDisContinuityTime	OBJECT-TYPE	
		SYNTAX			DisplayString
		MAX-ACCESS		read-only
		STATUS			current
		DESCRIPTION		"DisContinuity Time"
		::=  {  nptMcLAGEntry  3  }

    nptMcLAGElapsed	OBJECT-TYPE	
		SYNTAX			DisplayString 
		MAX-ACCESS		read-only
		STATUS			current
		DESCRIPTION		"dd:hh:mm:ss"
		::=  {  nptMcLAGEntry  4  }


    nptMcLAGFramesTx	OBJECT-TYPE	
		SYNTAX			Counter64
		MAX-ACCESS		read-only
		STATUS			current
		DESCRIPTION		"Description"
		::=  {  nptMcLAGEntry  5  }

    nptMcLAGFramesRx	OBJECT-TYPE	
		SYNTAX			Counter64
		MAX-ACCESS		read-only
		STATUS			current
		DESCRIPTION		"Description"
		::=  {  nptMcLAGEntry  6  }

    nptMcLAGInvalidFramesRx	OBJECT-TYPE	
		SYNTAX			Counter64
		MAX-ACCESS		read-only
		STATUS			current
		DESCRIPTION		"Description"
		::=  {  nptMcLAGEntry  7  }
		
		
	nptLPTable	OBJECT-TYPE
		SYNTAX		SEQUENCE  OF  NptLPEntry
		MAX-ACCESS	not-accessible
		STATUS		current
		DESCRIPTION	"Description"
		::=  { nptLP  1 }

	nptLPEntry	OBJECT-TYPE
		SYNTAX		NptLPEntry
		MAX-ACCESS	not-accessible
		STATUS		current
		DESCRIPTION	"Row Description"
		INDEX		{  nptLPIndex  }
		::=  { nptLPTable 1 }

	NptLPEntry  ::=  SEQUENCE {
	    nptLPIndex  Integer32,
        nptLPTunnelName  DisplayString,
		nptLPTxPSCpackets Counter64,
		nptLPRxPSCpackets Counter64,
		nptLPRxInvalidPSCPackets Counter64
		}


	nptLPIndex	OBJECT-TYPE	
		SYNTAX			Integer32  ( -2147483648 .. 2147483647  ) 
		MAX-ACCESS		read-only
		STATUS			current
		DESCRIPTION		"Column Description"
		::=  {  nptLPEntry  1  }

    nptLPTunnelName	OBJECT-TYPE	
		SYNTAX			DisplayString 
		MAX-ACCESS		read-only
		STATUS			current
		DESCRIPTION		"Tunnel Name"
		::=  {  nptLPEntry  2  }


    nptLPTxPSCpackets	OBJECT-TYPE	
		SYNTAX			Counter64
		MAX-ACCESS		read-only
		STATUS			current
		DESCRIPTION		"Description"
		::=  {  nptLPEntry  3  }

    nptLPRxPSCpackets	OBJECT-TYPE	
		SYNTAX			Counter64
		MAX-ACCESS		read-only
		STATUS			current
		DESCRIPTION		"Description"
		::=  {  nptLPEntry  4  }

    nptLPRxInvalidPSCPackets	OBJECT-TYPE	
		SYNTAX			Counter64
		MAX-ACCESS		read-only
		STATUS			current
		DESCRIPTION		"Description"
		::=  {  nptLPEntry  5  }
		
	nptLDPEntityTable	OBJECT-TYPE
		SYNTAX		SEQUENCE  OF  NptLDPEntityEntry
		MAX-ACCESS	not-accessible
		STATUS		current
		DESCRIPTION	"Description"
		::=  { nptLDPEntity  1 }

	nptLDPEntityEntry	OBJECT-TYPE
		SYNTAX		NptLDPEntityEntry
		MAX-ACCESS	not-accessible
		STATUS		current
		DESCRIPTION	"Row Description"
		INDEX		{  nptLDPEntityIndex  }
		::=  { nptLDPEntityTable 1 }

	NptLDPEntityEntry  ::=  SEQUENCE {
	    nptLDPEntityIndex  Integer32,
		nptLDPEntityDisContinuityTime  DisplayString,
		nptLDPEntityElapsed DisplayString,
		nptLDPEntityRxHello Integer32,
		nptLDPEntityTxHello Integer32,
		nptLDPEntityRxInitialization Integer32,
		nptLDPEntityTxInitialization Integer32,
		nptLDPEntityRxKeepalive Integer32,
		nptLDPEntityTxKeepalive Integer32,
		nptLDPEntityRxNotification Integer32,
		nptLDPEntityTxNotification Integer32,
		nptLDPEntityRxAddress Integer32,
		nptLDPEntityTxAddress Integer32,
		nptLDPEntityRxAddressWithdraw Integer32,
		nptLDPEntityTxAddressWithdraw Integer32,
		nptLDPEntityRxLabelMapping Integer32,
		nptLDPEntityTxLabelMapping Integer32,
		nptLDPEntityRxLabelRequest Integer32,
		nptLDPEntityTxLabelRequest Integer32,
		nptLDPEntityRxLabelWithdraw Integer32,
		nptLDPEntityTxLabelWithdraw Integer32,
		nptLDPEntityRxLabelRelease Integer32,
		nptLDPEntityTxLabelRelease Integer32,
		nptLDPEntityRxLabelAbort Integer32,
		nptLDPEntityTxLabelAbort Integer32,
		nptLDPEntityRxAllUDP Integer32,
		nptLDPEntityTxAllUDP Integer32,
		nptLDPEntityRxAllTCP Integer32,
		nptLDPEntityTxAllTCP Integer32,
		nptLDPEntitySessionInitFailed Integer32,
		nptLDPEntityNoHello Integer32,
		nptLDPEntityAdvertismentMode Integer32,
		nptLDPEntityMaxPduLength Integer32,
		nptLDPEntityLabelRange Integer32,
		nptLDPEntityBadLdpId Integer32,
		nptLDPEntityBadPduLength Integer32,
		nptLDPEntityBadMessageLen Integer32,
		nptLDPEntityBadTlvLen Integer32,
		nptLDPEntityMalformedTlvValue Integer32,
		nptLDPEntityRxShutdownNotif Integer32,
		nptLDPEntityTxShutdownNotif Integer32,
		nptLDPEntityKeepAliveTimerExp Integer32
		}


	nptLDPEntityIndex	OBJECT-TYPE	
		SYNTAX			Integer32  ( -2147483648 .. 2147483647  ) 
		MAX-ACCESS		read-only
		STATUS			current
		DESCRIPTION		"Column Description"
		::=  {  nptLDPEntityEntry  1  }


    nptLDPEntityDisContinuityTime	OBJECT-TYPE	
		SYNTAX			DisplayString
		MAX-ACCESS		read-only
		STATUS			current
		DESCRIPTION		"DisContinuity Time"
		::=  {  nptLDPEntityEntry  2  }

    nptLDPEntityElapsed	OBJECT-TYPE	
		SYNTAX			DisplayString 
		MAX-ACCESS		read-only
		STATUS			current
		DESCRIPTION		"dd:hh:mm:ss"
		::=  {  nptLDPEntityEntry  3  }


    nptLDPEntityRxHello	OBJECT-TYPE	
		SYNTAX			Integer32
		MAX-ACCESS		read-only
		STATUS			current
		DESCRIPTION		"Description"
		::=  {  nptLDPEntityEntry  4  }

    nptLDPEntityTxHello	OBJECT-TYPE	
		SYNTAX			Integer32
		MAX-ACCESS		read-only
		STATUS			current
		DESCRIPTION		"Description"
		::=  {  nptLDPEntityEntry  5  }

    nptLDPEntityRxInitialization	OBJECT-TYPE	
		SYNTAX			Integer32
		MAX-ACCESS		read-only
		STATUS			current
		DESCRIPTION		"Description"
		::=  {  nptLDPEntityEntry  6  }

    nptLDPEntityTxInitialization	OBJECT-TYPE	
		SYNTAX			Integer32
		MAX-ACCESS		read-only
		STATUS			current
		DESCRIPTION		"Description"
		::=  {  nptLDPEntityEntry  7  }

    nptLDPEntityRxKeepalive	OBJECT-TYPE	
		SYNTAX			Integer32
		MAX-ACCESS		read-only
		STATUS			current
		DESCRIPTION		"Description"
		::=  {  nptLDPEntityEntry  8  }

    nptLDPEntityTxKeepalive	OBJECT-TYPE	
		SYNTAX			Integer32
		MAX-ACCESS		read-only
		STATUS			current
		DESCRIPTION		"Description"
		::=  {  nptLDPEntityEntry  9  }

    nptLDPEntityRxNotification	OBJECT-TYPE	
		SYNTAX			Integer32
		MAX-ACCESS		read-only
		STATUS			current
		DESCRIPTION		"Description"
		::=  {  nptLDPEntityEntry  10  }

    nptLDPEntityTxNotification	OBJECT-TYPE	
		SYNTAX			Integer32
		MAX-ACCESS		read-only
		STATUS			current
		DESCRIPTION		"Description"
		::=  {  nptLDPEntityEntry  11  }

    nptLDPEntityRxAddress	OBJECT-TYPE	
		SYNTAX			Integer32
		MAX-ACCESS		read-only
		STATUS			current
		DESCRIPTION		"Description"
		::=  {  nptLDPEntityEntry  12  }

    nptLDPEntityTxAddress	OBJECT-TYPE	
		SYNTAX			Integer32
		MAX-ACCESS		read-only
		STATUS			current
		DESCRIPTION		"Description"
		::=  {  nptLDPEntityEntry  13  }

    nptLDPEntityRxAddressWithdraw	OBJECT-TYPE	
		SYNTAX			Integer32
		MAX-ACCESS		read-only
		STATUS			current
		DESCRIPTION		"Description"
		::=  {  nptLDPEntityEntry  14  }

    nptLDPEntityTxAddressWithdraw	OBJECT-TYPE	
		SYNTAX			Integer32
		MAX-ACCESS		read-only
		STATUS			current
		DESCRIPTION		"Description"
		::=  {  nptLDPEntityEntry  15  }

    nptLDPEntityRxLabelMapping	OBJECT-TYPE	
		SYNTAX			Integer32
		MAX-ACCESS		read-only
		STATUS			current
		DESCRIPTION		"Description"
		::=  {  nptLDPEntityEntry  16  }

    nptLDPEntityTxLabelMapping	OBJECT-TYPE	
		SYNTAX			Integer32
		MAX-ACCESS		read-only
		STATUS			current
		DESCRIPTION		"Description"
		::=  {  nptLDPEntityEntry  17  }

    nptLDPEntityRxLabelRequest	OBJECT-TYPE	
		SYNTAX			Integer32
		MAX-ACCESS		read-only
		STATUS			current
		DESCRIPTION		"Description"
		::=  {  nptLDPEntityEntry  18  }

    nptLDPEntityTxLabelRequest	OBJECT-TYPE	
		SYNTAX			Integer32
		MAX-ACCESS		read-only
		STATUS			current
		DESCRIPTION		"Description"
		::=  {  nptLDPEntityEntry  19  }

    nptLDPEntityRxLabelWithdraw	OBJECT-TYPE	
		SYNTAX			Integer32
		MAX-ACCESS		read-only
		STATUS			current
		DESCRIPTION		"Description"
		::=  {  nptLDPEntityEntry  20  }

    nptLDPEntityTxLabelWithdraw	OBJECT-TYPE	
		SYNTAX			Integer32
		MAX-ACCESS		read-only
		STATUS			current
		DESCRIPTION		"Description"
		::=  {  nptLDPEntityEntry  21  }

    nptLDPEntityRxLabelRelease	OBJECT-TYPE	
		SYNTAX			Integer32
		MAX-ACCESS		read-only
		STATUS			current
		DESCRIPTION		"Description"
		::=  {  nptLDPEntityEntry  22  }

    nptLDPEntityTxLabelRelease	OBJECT-TYPE	
		SYNTAX			Integer32
		MAX-ACCESS		read-only
		STATUS			current
		DESCRIPTION		"Description"
		::=  {  nptLDPEntityEntry  23  }

    nptLDPEntityRxLabelAbort	OBJECT-TYPE	
		SYNTAX			Integer32
		MAX-ACCESS		read-only
		STATUS			current
		DESCRIPTION		"Description"
		::=  {  nptLDPEntityEntry  24  }

    nptLDPEntityTxLabelAbort	OBJECT-TYPE	
		SYNTAX			Integer32
		MAX-ACCESS		read-only
		STATUS			current
		DESCRIPTION		"Description"
		::=  {  nptLDPEntityEntry  25  }

    nptLDPEntityRxAllUDP	OBJECT-TYPE	
		SYNTAX			Integer32
		MAX-ACCESS		read-only
		STATUS			current
		DESCRIPTION		"Description"
		::=  {  nptLDPEntityEntry  26  }

    nptLDPEntityTxAllUDP	OBJECT-TYPE	
		SYNTAX			Integer32
		MAX-ACCESS		read-only
		STATUS			current
		DESCRIPTION		"Description"
		::=  {  nptLDPEntityEntry  27  }

    nptLDPEntityRxAllTCP	OBJECT-TYPE	
		SYNTAX			Integer32
		MAX-ACCESS		read-only
		STATUS			current
		DESCRIPTION		"Description"
		::=  {  nptLDPEntityEntry  28  }

    nptLDPEntityTxAllTCP	OBJECT-TYPE	
		SYNTAX			Integer32
		MAX-ACCESS		read-only
		STATUS			current
		DESCRIPTION		"Description"
		::=  {  nptLDPEntityEntry  29  }

    nptLDPEntitySessionInitFailed	OBJECT-TYPE	
		SYNTAX			Integer32
		MAX-ACCESS		read-only
		STATUS			current
		DESCRIPTION		"Description"
		::=  {  nptLDPEntityEntry  30  }

    nptLDPEntityNoHello	OBJECT-TYPE	
		SYNTAX			Integer32
		MAX-ACCESS		read-only
		STATUS			current
		DESCRIPTION		"Description"
		::=  {  nptLDPEntityEntry  31  }

    nptLDPEntityAdvertismentMode	OBJECT-TYPE	
		SYNTAX			Integer32
		MAX-ACCESS		read-only
		STATUS			current
		DESCRIPTION		"Description"
		::=  {  nptLDPEntityEntry  32  }

    nptLDPEntityMaxPduLength	OBJECT-TYPE	
		SYNTAX			Integer32
		MAX-ACCESS		read-only
		STATUS			current
		DESCRIPTION		"Description"
		::=  {  nptLDPEntityEntry  33  }

    nptLDPEntityLabelRange	OBJECT-TYPE	
		SYNTAX			Integer32
		MAX-ACCESS		read-only
		STATUS			current
		DESCRIPTION		"Description"
		::=  {  nptLDPEntityEntry  34  }

    nptLDPEntityBadLdpId	OBJECT-TYPE	
		SYNTAX			Integer32
		MAX-ACCESS		read-only
		STATUS			current
		DESCRIPTION		"Description"
		::=  {  nptLDPEntityEntry  35  }

    nptLDPEntityBadPduLength	OBJECT-TYPE	
		SYNTAX			Integer32
		MAX-ACCESS		read-only
		STATUS			current
		DESCRIPTION		"Description"
		::=  {  nptLDPEntityEntry  36  }

    nptLDPEntityBadMessageLen	OBJECT-TYPE	
		SYNTAX			Integer32
		MAX-ACCESS		read-only
		STATUS			current
		DESCRIPTION		"Description"
		::=  {  nptLDPEntityEntry  37  }

    nptLDPEntityBadTlvLen	OBJECT-TYPE	
		SYNTAX			Integer32
		MAX-ACCESS		read-only
		STATUS			current
		DESCRIPTION		"Description"
		::=  {  nptLDPEntityEntry  38  }

    nptLDPEntityMalformedTlvValue	OBJECT-TYPE	
		SYNTAX			Integer32
		MAX-ACCESS		read-only
		STATUS			current
		DESCRIPTION		"Description"
		::=  {  nptLDPEntityEntry  39  }

    nptLDPEntityRxShutdownNotif	OBJECT-TYPE	
		SYNTAX			Integer32
		MAX-ACCESS		read-only
		STATUS			current
		DESCRIPTION		"Description"
		::=  {  nptLDPEntityEntry  40  }

    nptLDPEntityTxShutdownNotif	OBJECT-TYPE	
		SYNTAX			Integer32
		MAX-ACCESS		read-only
		STATUS			current
		DESCRIPTION		"Description"
		::=  {  nptLDPEntityEntry  41  }

    nptLDPEntityKeepAliveTimerExp	OBJECT-TYPE	
		SYNTAX			Integer32
		MAX-ACCESS		read-only
		STATUS			current
		DESCRIPTION		"Description"
		::=  {  nptLDPEntityEntry  42  }
		
	nptLDPSessionTable	OBJECT-TYPE
		SYNTAX		SEQUENCE  OF  NptLDPSessionEntry
		MAX-ACCESS	not-accessible
		STATUS		current
		DESCRIPTION	"Description"
		::=  { nptLDPSession  1 }

	nptLDPSessionEntry	OBJECT-TYPE
		SYNTAX		NptLDPSessionEntry
		MAX-ACCESS	not-accessible
		STATUS		current
		DESCRIPTION	"Row Description"
		INDEX		{  nptLDPSessionIndex  }
		::=  { nptLDPSessionTable 1 }

	NptLDPSessionEntry  ::=  SEQUENCE {
	    nptLDPSessionIndex  Integer32,
        nptLDPSessionPeerId DisplayString,
		nptLDPSessionDisContinuityTime  DisplayString,
		nptLDPSessionRxKeepalive Integer32,
		nptLDPSessionTxKeepalive Integer32,
		nptLDPSessionRxNotification Integer32,
		nptLDPSessionTxNotification Integer32,
		nptLDPSessionRxAddress Integer32,
		nptLDPSessionTxAddress Integer32,
		nptLDPSessionRxAddressWithdraw Integer32,
		nptLDPSessionTxAddressWithdraw Integer32,
		nptLDPSessionRxLabelMapping Integer32,
		nptLDPSessionTxLabelMapping Integer32,
		nptLDPSessionRxLabelRequest Integer32,
		nptLDPSessionTxLabelRequest Integer32,
		nptLDPSessionRxLabelWithdraw Integer32,
		nptLDPSessionTxLabelWithdraw Integer32,
		nptLDPSessionRxLabelRelease Integer32,
		nptLDPSessionTxLabelRelease Integer32,
		nptLDPSessionRxLabelAbort Integer32,
		nptLDPSessionTxLabelAbort Integer32,
		nptLDPSessionRxAllTCP Integer32,
		nptLDPSessionTxAllTCP Integer32,
		nptLDPSessionUnknownMsgType Integer32,
		nptLDPSessionUnknownTlv Integer32,
		nptLDPSessionDropDangerousPackets Integer32
		}


	nptLDPSessionIndex	OBJECT-TYPE	
		SYNTAX			Integer32  ( -2147483648 .. 2147483647  ) 
		MAX-ACCESS		read-only
		STATUS			current
		DESCRIPTION		"Column Description"
		::=  {  nptLDPSessionEntry  1  }

    nptLDPSessionPeerId	OBJECT-TYPE	
		SYNTAX			DisplayString 
		MAX-ACCESS		read-only
		STATUS			current
		DESCRIPTION		"Peer Id"
		::=  {  nptLDPSessionEntry  2  }


    nptLDPSessionDisContinuityTime	OBJECT-TYPE	
		SYNTAX			DisplayString
		MAX-ACCESS		read-only
		STATUS			current
		DESCRIPTION		"DisContinuity Time"
		::=  {  nptLDPSessionEntry  3  }

    nptLDPSessionRxKeepalive	OBJECT-TYPE	
		SYNTAX			Integer32
		MAX-ACCESS		read-only
		STATUS			current
		DESCRIPTION		"Description"
		::=  {  nptLDPSessionEntry  5  }

    nptLDPSessionTxKeepalive	OBJECT-TYPE	
		SYNTAX			Integer32
		MAX-ACCESS		read-only
		STATUS			current
		DESCRIPTION		"Description"
		::=  {  nptLDPSessionEntry  6  }

    nptLDPSessionRxNotification	OBJECT-TYPE	
		SYNTAX			Integer32
		MAX-ACCESS		read-only
		STATUS			current
		DESCRIPTION		"Description"
		::=  {  nptLDPSessionEntry  7  }

    nptLDPSessionTxNotification	OBJECT-TYPE	
		SYNTAX			Integer32
		MAX-ACCESS		read-only
		STATUS			current
		DESCRIPTION		"Description"
		::=  {  nptLDPSessionEntry  8  }

    nptLDPSessionRxAddress	OBJECT-TYPE	
		SYNTAX			Integer32
		MAX-ACCESS		read-only
		STATUS			current
		DESCRIPTION		"Description"
		::=  {  nptLDPSessionEntry  9  }

    nptLDPSessionTxAddress	OBJECT-TYPE	
		SYNTAX			Integer32
		MAX-ACCESS		read-only
		STATUS			current
		DESCRIPTION		"Description"
		::=  {  nptLDPSessionEntry  10  }

    nptLDPSessionRxAddressWithdraw	OBJECT-TYPE	
		SYNTAX			Integer32
		MAX-ACCESS		read-only
		STATUS			current
		DESCRIPTION		"Description"
		::=  {  nptLDPSessionEntry  11  }

    nptLDPSessionTxAddressWithdraw	OBJECT-TYPE	
		SYNTAX			Integer32
		MAX-ACCESS		read-only
		STATUS			current
		DESCRIPTION		"Description"
		::=  {  nptLDPSessionEntry  12  }

    nptLDPSessionRxLabelMapping	OBJECT-TYPE	
		SYNTAX			Integer32
		MAX-ACCESS		read-only
		STATUS			current
		DESCRIPTION		"Description"
		::=  {  nptLDPSessionEntry  13  }

    nptLDPSessionTxLabelMapping	OBJECT-TYPE	
		SYNTAX			Integer32
		MAX-ACCESS		read-only
		STATUS			current
		DESCRIPTION		"Description"
		::=  {  nptLDPSessionEntry  14  }

    nptLDPSessionRxLabelRequest	OBJECT-TYPE	
		SYNTAX			Integer32
		MAX-ACCESS		read-only
		STATUS			current
		DESCRIPTION		"Description"
		::=  {  nptLDPSessionEntry  15  }

    nptLDPSessionTxLabelRequest	OBJECT-TYPE	
		SYNTAX			Integer32
		MAX-ACCESS		read-only
		STATUS			current
		DESCRIPTION		"Description"
		::=  {  nptLDPSessionEntry  16  }

    nptLDPSessionRxLabelWithdraw	OBJECT-TYPE	
		SYNTAX			Integer32
		MAX-ACCESS		read-only
		STATUS			current
		DESCRIPTION		"Description"
		::=  {  nptLDPSessionEntry  17  }

    nptLDPSessionTxLabelWithdraw	OBJECT-TYPE	
		SYNTAX			Integer32
		MAX-ACCESS		read-only
		STATUS			current
		DESCRIPTION		"Description"
		::=  {  nptLDPSessionEntry  18  }

    nptLDPSessionRxLabelRelease	OBJECT-TYPE	
		SYNTAX			Integer32
		MAX-ACCESS		read-only
		STATUS			current
		DESCRIPTION		"Description"
		::=  {  nptLDPSessionEntry  19  }

    nptLDPSessionTxLabelRelease	OBJECT-TYPE	
		SYNTAX			Integer32
		MAX-ACCESS		read-only
		STATUS			current
		DESCRIPTION		"Description"
		::=  {  nptLDPSessionEntry  20  }

    nptLDPSessionRxLabelAbort	OBJECT-TYPE	
		SYNTAX			Integer32
		MAX-ACCESS		read-only
		STATUS			current
		DESCRIPTION		"Description"
		::=  {  nptLDPSessionEntry  21  }

    nptLDPSessionTxLabelAbort	OBJECT-TYPE	
		SYNTAX			Integer32
		MAX-ACCESS		read-only
		STATUS			current
		DESCRIPTION		"Description"
		::=  {  nptLDPSessionEntry  22  }

    nptLDPSessionRxAllTCP	OBJECT-TYPE	
		SYNTAX			Integer32
		MAX-ACCESS		read-only
		STATUS			current
		DESCRIPTION		"Description"
		::=  {  nptLDPSessionEntry  23  }

    nptLDPSessionTxAllTCP	OBJECT-TYPE	
		SYNTAX			Integer32
		MAX-ACCESS		read-only
		STATUS			current
		DESCRIPTION		"Description"
		::=  {  nptLDPSessionEntry  24  }


    nptLDPSessionUnknownMsgType	OBJECT-TYPE	
		SYNTAX			Integer32
		MAX-ACCESS		read-only
		STATUS			current
		DESCRIPTION		"Description"
		::=  {  nptLDPSessionEntry  25  }

    nptLDPSessionUnknownTlv	OBJECT-TYPE	
		SYNTAX			Integer32
		MAX-ACCESS		read-only
		STATUS			current
		DESCRIPTION		"Description"
		::=  {  nptLDPSessionEntry  26  }

    nptLDPSessionDropDangerousPackets	OBJECT-TYPE	
		SYNTAX			Integer32
		MAX-ACCESS		read-only
		STATUS			current
		DESCRIPTION		"Description"
		::=  {  nptLDPSessionEntry  27  }
		
	nptLDPTargetedEntityTable	OBJECT-TYPE
		SYNTAX		SEQUENCE  OF  NptLDPTargetedEntityEntry
		MAX-ACCESS	not-accessible
		STATUS		current
		DESCRIPTION	"Description"
		::=  { nptLDPTargetedEntity  1 }

	nptLDPTargetedEntityEntry	OBJECT-TYPE
		SYNTAX		NptLDPTargetedEntityEntry
		MAX-ACCESS	not-accessible
		STATUS		current
		DESCRIPTION	"Row Description"
		INDEX		{  nptLDPTargetedEntityIndex  }
		::=  { nptLDPTargetedEntityTable 1 }

	NptLDPTargetedEntityEntry  ::=  SEQUENCE {
	    nptLDPTargetedEntityIndex  Integer32,
		nptLDPTargetedEntityPeerID DisplayString,
		nptLDPTargetedEntityDisContinuityTime  DisplayString,
		nptLDPTargetedEntityElapsed DisplayString,
		nptLDPTargetedEntityRxHello Integer32,
		nptLDPTargetedEntityTxHello Integer32,
		nptLDPTargetedEntityRxInitialization Integer32,
		nptLDPTargetedEntityTxInitialization Integer32,
		nptLDPTargetedEntityRxKeepalive Integer32,
		nptLDPTargetedEntityTxKeepalive Integer32,
		nptLDPTargetedEntityRxNotification Integer32,
		nptLDPTargetedEntityTxNotification Integer32,
		nptLDPTargetedEntityRxAddress Integer32,
		nptLDPTargetedEntityTxAddress Integer32,
		nptLDPTargetedEntityRxAddressWithdraw Integer32,
		nptLDPTargetedEntityTxAddressWithdraw Integer32,
		nptLDPTargetedEntityRxLabelMapping Integer32,
		nptLDPTargetedEntityTxLabelMapping Integer32,
		nptLDPTargetedEntityRxLabelRequest Integer32,
		nptLDPTargetedEntityTxLabelRequest Integer32,
		nptLDPTargetedEntityRxLabelWithdraw Integer32,
		nptLDPTargetedEntityTxLabelWithdraw Integer32,
		nptLDPTargetedEntityRxLabelRelease Integer32,
		nptLDPTargetedEntityTxLabelRelease Integer32,
		nptLDPTargetedEntityRxLabelAbort Integer32,
		nptLDPTargetedEntityTxLabelAbort Integer32,
		nptLDPTargetedEntityRxAllUDP Integer32,
		nptLDPTargetedEntityTxAllUDP Integer32,
		nptLDPTargetedEntityRxAllTCP Integer32,
		nptLDPTargetedEntityTxAllTCP Integer32,
		nptLDPTargetedEntitySessionInitFailed Integer32,
		nptLDPTargetedEntityNoHello Integer32,
		nptLDPTargetedEntityAdvertismentMode Integer32,
		nptLDPTargetedEntityMaxPduLength Integer32,
		nptLDPTargetedEntityLabelRange Integer32,
		nptLDPTargetedEntityBadLdpId Integer32,
		nptLDPTargetedEntityBadPduLength Integer32,
		nptLDPTargetedEntityBadMessageLen Integer32,
		nptLDPTargetedEntityBadTlvLen Integer32,
		nptLDPTargetedEntityMalformedTlvValue Integer32,
		nptLDPTargetedEntityRxShutdownNotif Integer32,
		nptLDPTargetedEntityTxShutdownNotif Integer32,
		nptLDPTargetedEntityKeepAliveTimerExp Integer32
		}


	nptLDPTargetedEntityIndex	OBJECT-TYPE	
		SYNTAX			Integer32  ( -2147483648 .. 2147483647  ) 
		MAX-ACCESS		read-only
		STATUS			current
		DESCRIPTION		"Column Description"
		::=  {  nptLDPTargetedEntityEntry  1  }
		
	nptLDPTargetedEntityPeerID	OBJECT-TYPE	
		SYNTAX			DisplayString 
		MAX-ACCESS		read-only
		STATUS			current
		DESCRIPTION		"Peer ID"
		::=  {  nptLDPTargetedEntityEntry  2  }


    nptLDPTargetedEntityDisContinuityTime	OBJECT-TYPE	
		SYNTAX			DisplayString
		MAX-ACCESS		read-only
		STATUS			current
		DESCRIPTION		"DisContinuity Time"
		::=  {  nptLDPTargetedEntityEntry  3  }

    nptLDPTargetedEntityElapsed	OBJECT-TYPE	
		SYNTAX			DisplayString 
		MAX-ACCESS		read-only
		STATUS			current
		DESCRIPTION		"dd:hh:mm:ss"
		::=  {  nptLDPTargetedEntityEntry  4  }


    nptLDPTargetedEntityRxHello	OBJECT-TYPE	
		SYNTAX			Integer32
		MAX-ACCESS		read-only
		STATUS			current
		DESCRIPTION		"Description"
		::=  {  nptLDPTargetedEntityEntry  5  }

    nptLDPTargetedEntityTxHello	OBJECT-TYPE	
		SYNTAX			Integer32
		MAX-ACCESS		read-only
		STATUS			current
		DESCRIPTION		"Description"
		::=  {  nptLDPTargetedEntityEntry  6  }

    nptLDPTargetedEntityRxInitialization	OBJECT-TYPE	
		SYNTAX			Integer32
		MAX-ACCESS		read-only
		STATUS			current
		DESCRIPTION		"Description"
		::=  {  nptLDPTargetedEntityEntry  7  }

    nptLDPTargetedEntityTxInitialization	OBJECT-TYPE	
		SYNTAX			Integer32
		MAX-ACCESS		read-only
		STATUS			current
		DESCRIPTION		"Description"
		::=  {  nptLDPTargetedEntityEntry  8  }

    nptLDPTargetedEntityRxKeepalive	OBJECT-TYPE	
		SYNTAX			Integer32
		MAX-ACCESS		read-only
		STATUS			current
		DESCRIPTION		"Description"
		::=  {  nptLDPTargetedEntityEntry  9  }

    nptLDPTargetedEntityTxKeepalive	OBJECT-TYPE	
		SYNTAX			Integer32
		MAX-ACCESS		read-only
		STATUS			current
		DESCRIPTION		"Description"
		::=  {  nptLDPTargetedEntityEntry  10  }

    nptLDPTargetedEntityRxNotification	OBJECT-TYPE	
		SYNTAX			Integer32
		MAX-ACCESS		read-only
		STATUS			current
		DESCRIPTION		"Description"
		::=  {  nptLDPTargetedEntityEntry  11  }

    nptLDPTargetedEntityTxNotification	OBJECT-TYPE	
		SYNTAX			Integer32
		MAX-ACCESS		read-only
		STATUS			current
		DESCRIPTION		"Description"
		::=  {  nptLDPTargetedEntityEntry  12  }

    nptLDPTargetedEntityRxAddress	OBJECT-TYPE	
		SYNTAX			Integer32
		MAX-ACCESS		read-only
		STATUS			current
		DESCRIPTION		"Description"
		::=  {  nptLDPTargetedEntityEntry  13  }

    nptLDPTargetedEntityTxAddress	OBJECT-TYPE	
		SYNTAX			Integer32
		MAX-ACCESS		read-only
		STATUS			current
		DESCRIPTION		"Description"
		::=  {  nptLDPTargetedEntityEntry  14  }

    nptLDPTargetedEntityRxAddressWithdraw	OBJECT-TYPE	
		SYNTAX			Integer32
		MAX-ACCESS		read-only
		STATUS			current
		DESCRIPTION		"Description"
		::=  {  nptLDPTargetedEntityEntry  15  }

    nptLDPTargetedEntityTxAddressWithdraw	OBJECT-TYPE	
		SYNTAX			Integer32
		MAX-ACCESS		read-only
		STATUS			current
		DESCRIPTION		"Description"
		::=  {  nptLDPTargetedEntityEntry  16  }

    nptLDPTargetedEntityRxLabelMapping	OBJECT-TYPE	
		SYNTAX			Integer32
		MAX-ACCESS		read-only
		STATUS			current
		DESCRIPTION		"Description"
		::=  {  nptLDPTargetedEntityEntry  17  }

    nptLDPTargetedEntityTxLabelMapping	OBJECT-TYPE	
		SYNTAX			Integer32
		MAX-ACCESS		read-only
		STATUS			current
		DESCRIPTION		"Description"
		::=  {  nptLDPTargetedEntityEntry  18  }

    nptLDPTargetedEntityRxLabelRequest	OBJECT-TYPE	
		SYNTAX			Integer32
		MAX-ACCESS		read-only
		STATUS			current
		DESCRIPTION		"Description"
		::=  {  nptLDPTargetedEntityEntry  19  }

    nptLDPTargetedEntityTxLabelRequest	OBJECT-TYPE	
		SYNTAX			Integer32
		MAX-ACCESS		read-only
		STATUS			current
		DESCRIPTION		"Description"
		::=  {  nptLDPTargetedEntityEntry  20  }

    nptLDPTargetedEntityRxLabelWithdraw	OBJECT-TYPE	
		SYNTAX			Integer32
		MAX-ACCESS		read-only
		STATUS			current
		DESCRIPTION		"Description"
		::=  {  nptLDPTargetedEntityEntry  21  }

    nptLDPTargetedEntityTxLabelWithdraw	OBJECT-TYPE	
		SYNTAX			Integer32
		MAX-ACCESS		read-only
		STATUS			current
		DESCRIPTION		"Description"
		::=  {  nptLDPTargetedEntityEntry  22  }

    nptLDPTargetedEntityRxLabelRelease	OBJECT-TYPE	
		SYNTAX			Integer32
		MAX-ACCESS		read-only
		STATUS			current
		DESCRIPTION		"Description"
		::=  {  nptLDPTargetedEntityEntry  23  }

    nptLDPTargetedEntityTxLabelRelease	OBJECT-TYPE	
		SYNTAX			Integer32
		MAX-ACCESS		read-only
		STATUS			current
		DESCRIPTION		"Description"
		::=  {  nptLDPTargetedEntityEntry  24  }

    nptLDPTargetedEntityRxLabelAbort	OBJECT-TYPE	
		SYNTAX			Integer32
		MAX-ACCESS		read-only
		STATUS			current
		DESCRIPTION		"Description"
		::=  {  nptLDPTargetedEntityEntry  25  }

    nptLDPTargetedEntityTxLabelAbort	OBJECT-TYPE	
		SYNTAX			Integer32
		MAX-ACCESS		read-only
		STATUS			current
		DESCRIPTION		"Description"
		::=  {  nptLDPTargetedEntityEntry  26  }

    nptLDPTargetedEntityRxAllUDP	OBJECT-TYPE	
		SYNTAX			Integer32
		MAX-ACCESS		read-only
		STATUS			current
		DESCRIPTION		"Description"
		::=  {  nptLDPTargetedEntityEntry  27  }

    nptLDPTargetedEntityTxAllUDP	OBJECT-TYPE	
		SYNTAX			Integer32
		MAX-ACCESS		read-only
		STATUS			current
		DESCRIPTION		"Description"
		::=  {  nptLDPTargetedEntityEntry  28  }

    nptLDPTargetedEntityRxAllTCP	OBJECT-TYPE	
		SYNTAX			Integer32
		MAX-ACCESS		read-only
		STATUS			current
		DESCRIPTION		"Description"
		::=  {  nptLDPTargetedEntityEntry  29  }

    nptLDPTargetedEntityTxAllTCP	OBJECT-TYPE	
		SYNTAX			Integer32
		MAX-ACCESS		read-only
		STATUS			current
		DESCRIPTION		"Description"
		::=  {  nptLDPTargetedEntityEntry  30  }

    nptLDPTargetedEntitySessionInitFailed	OBJECT-TYPE	
		SYNTAX			Integer32
		MAX-ACCESS		read-only
		STATUS			current
		DESCRIPTION		"Description"
		::=  {  nptLDPTargetedEntityEntry  31  }

    nptLDPTargetedEntityNoHello	OBJECT-TYPE	
		SYNTAX			Integer32
		MAX-ACCESS		read-only
		STATUS			current
		DESCRIPTION		"Description"
		::=  {  nptLDPTargetedEntityEntry  32  }

    nptLDPTargetedEntityAdvertismentMode	OBJECT-TYPE	
		SYNTAX			Integer32
		MAX-ACCESS		read-only
		STATUS			current
		DESCRIPTION		"Description"
		::=  {  nptLDPTargetedEntityEntry  33  }

    nptLDPTargetedEntityMaxPduLength	OBJECT-TYPE	
		SYNTAX			Integer32
		MAX-ACCESS		read-only
		STATUS			current
		DESCRIPTION		"Description"
		::=  {  nptLDPTargetedEntityEntry  34  }

    nptLDPTargetedEntityLabelRange	OBJECT-TYPE	
		SYNTAX			Integer32
		MAX-ACCESS		read-only
		STATUS			current
		DESCRIPTION		"Description"
		::=  {  nptLDPTargetedEntityEntry  35  }

    nptLDPTargetedEntityBadLdpId	OBJECT-TYPE	
		SYNTAX			Integer32
		MAX-ACCESS		read-only
		STATUS			current
		DESCRIPTION		"Description"
		::=  {  nptLDPTargetedEntityEntry  36  }

    nptLDPTargetedEntityBadPduLength	OBJECT-TYPE	
		SYNTAX			Integer32
		MAX-ACCESS		read-only
		STATUS			current
		DESCRIPTION		"Description"
		::=  {  nptLDPTargetedEntityEntry  37  }

    nptLDPTargetedEntityBadMessageLen	OBJECT-TYPE	
		SYNTAX			Integer32
		MAX-ACCESS		read-only
		STATUS			current
		DESCRIPTION		"Description"
		::=  {  nptLDPTargetedEntityEntry  38  }

    nptLDPTargetedEntityBadTlvLen	OBJECT-TYPE	
		SYNTAX			Integer32
		MAX-ACCESS		read-only
		STATUS			current
		DESCRIPTION		"Description"
		::=  {  nptLDPTargetedEntityEntry  39  }

    nptLDPTargetedEntityMalformedTlvValue	OBJECT-TYPE	
		SYNTAX			Integer32
		MAX-ACCESS		read-only
		STATUS			current
		DESCRIPTION		"Description"
		::=  {  nptLDPTargetedEntityEntry  40  }

    nptLDPTargetedEntityRxShutdownNotif	OBJECT-TYPE	
		SYNTAX			Integer32
		MAX-ACCESS		read-only
		STATUS			current
		DESCRIPTION		"Description"
		::=  {  nptLDPTargetedEntityEntry  41  }

    nptLDPTargetedEntityTxShutdownNotif	OBJECT-TYPE	
		SYNTAX			Integer32
		MAX-ACCESS		read-only
		STATUS			current
		DESCRIPTION		"Description"
		::=  {  nptLDPTargetedEntityEntry  42  }

    nptLDPTargetedEntityKeepAliveTimerExp	OBJECT-TYPE	
		SYNTAX			Integer32
		MAX-ACCESS		read-only
		STATUS			current
		DESCRIPTION		"Description"
		::=  {  nptLDPTargetedEntityEntry  43  }
		
	nptLDPLSPTable	OBJECT-TYPE
		SYNTAX		SEQUENCE  OF  NptLDPLSPEntry
		MAX-ACCESS	not-accessible
		STATUS		current
		DESCRIPTION	"Description"
		::=  { nptLDPLSP  1 }
		
	nptLDPLSPEntry	OBJECT-TYPE
		SYNTAX		NptLDPLSPEntry
		MAX-ACCESS	not-accessible
		STATUS		current
		DESCRIPTION	"Row Description"
		INDEX		{  nptLDPLSPIndex  }
		::=  { nptLDPLSPTable 1 }

	NptLDPLSPEntry  ::=  SEQUENCE {
	    nptLDPLSPIndex  Integer32,
        nptLDPLSPFEC  DisplayString,
        nptLDPLSPType  DisplayString,
        nptLDPLSPDisContinuityTime  DisplayString,
        nptLDPLSPElapsed DisplayString,
		nptLDPLSPOctetsPassG Counter64,
		nptLDPLSPOctetsPassY Counter64,
		nptLDPLSPOctetsPassSum Counter64,
		nptLDPLSPOctetsDiscardGY Counter64,
		nptLDPLSPOctetsDiscardR Counter64,
		nptLDPLSPOctetsDiscardSum Counter64,
		nptLDPLSPPacketsPassG Counter64,
		nptLDPLSPPacketsPassY Counter64,
		nptLDPLSPPacketsPassSum Counter64,
		nptLDPLSPPacketsDiscardGY Counter64,
		nptLDPLSPPacketsDiscardR Counter64,
		nptLDPLSPPacketsDiscardSum Counter64
		}


	nptLDPLSPIndex	OBJECT-TYPE	
		SYNTAX			Integer32  ( -2147483648 .. 2147483647  ) 
		MAX-ACCESS		read-only
		STATUS			current
		DESCRIPTION		"Column Description"
		::=  {  nptLDPLSPEntry  1  }

    nptLDPLSPFEC	OBJECT-TYPE	
		SYNTAX			DisplayString 
		MAX-ACCESS		read-only
		STATUS			current
		DESCRIPTION		"Router-Id"
		::=  {  nptLDPLSPEntry  2  }

    nptLDPLSPType	OBJECT-TYPE	
		SYNTAX			DisplayString 
		MAX-ACCESS		read-only
		STATUS			current
		DESCRIPTION		"Transit|Ingress"
		::=  {  nptLDPLSPEntry  3  }

    nptLDPLSPDisContinuityTime	OBJECT-TYPE	
		SYNTAX			DisplayString
		MAX-ACCESS		read-only
		STATUS			current
		DESCRIPTION		"DisContinuity Time"
		::=  {  nptLDPLSPEntry  4  }

    nptLDPLSPElapsed	OBJECT-TYPE	
		SYNTAX			DisplayString 
		MAX-ACCESS		read-only
		STATUS			current
		DESCRIPTION		"dd:hh:mm:ss"
		::=  {  nptLDPLSPEntry  5  }

    nptLDPLSPOctetsPassG	OBJECT-TYPE	
		SYNTAX			Counter64
		MAX-ACCESS		read-only
		STATUS			current
		DESCRIPTION		"Description"
		::=  {  nptLDPLSPEntry  6  }

    nptLDPLSPOctetsPassY	OBJECT-TYPE	
		SYNTAX			Counter64
		MAX-ACCESS		read-only
		STATUS			current
		DESCRIPTION		"Description"
		::=  {  nptLDPLSPEntry  7  }

    nptLDPLSPOctetsPassSum	OBJECT-TYPE	
		SYNTAX			Counter64
		MAX-ACCESS		read-only
		STATUS			current
		DESCRIPTION		"Description"
		::=  {  nptLDPLSPEntry  8  }

    nptLDPLSPOctetsDiscardGY	OBJECT-TYPE	
		SYNTAX			Counter64
		MAX-ACCESS		read-only
		STATUS			current
		DESCRIPTION		"Description"
		::=  {  nptLDPLSPEntry  9  }

    nptLDPLSPOctetsDiscardR	OBJECT-TYPE	
		SYNTAX			Counter64
		MAX-ACCESS		read-only
		STATUS			current
		DESCRIPTION		"Description"
		::=  {  nptLDPLSPEntry  10  }

    nptLDPLSPOctetsDiscardSum	OBJECT-TYPE	
		SYNTAX			Counter64
		MAX-ACCESS		read-only
		STATUS			current
		DESCRIPTION		"Description"
		::=  {  nptLDPLSPEntry  11  }

    nptLDPLSPPacketsPassG	OBJECT-TYPE	
		SYNTAX			Counter64
		MAX-ACCESS		read-only
		STATUS			current
		DESCRIPTION		"Description"
		::=  {  nptLDPLSPEntry  12  }

    nptLDPLSPPacketsPassY	OBJECT-TYPE	
		SYNTAX			Counter64
		MAX-ACCESS		read-only
		STATUS			current
		DESCRIPTION		"Description"
		::=  {  nptLDPLSPEntry  13  }

    nptLDPLSPPacketsPassSum	OBJECT-TYPE	
		SYNTAX			Counter64
		MAX-ACCESS		read-only
		STATUS			current
		DESCRIPTION		"Description"
		::=  {  nptLDPLSPEntry  14  }

    nptLDPLSPPacketsDiscardGY	OBJECT-TYPE	
		SYNTAX			Counter64
		MAX-ACCESS		read-only
		STATUS			current
		DESCRIPTION		"Description"
		::=  {  nptLDPLSPEntry  15  }

    nptLDPLSPPacketsDiscardR	OBJECT-TYPE	
		SYNTAX			Counter64
		MAX-ACCESS		read-only
		STATUS			current
		DESCRIPTION		"Description"
		::=  {  nptLDPLSPEntry  16  }

    nptLDPLSPPacketsDiscardSum	OBJECT-TYPE	
		SYNTAX			Counter64
		MAX-ACCESS		read-only
		STATUS			current
		DESCRIPTION		"Description"
		::=  {  nptLDPLSPEntry  17  }

		
	nptPTP1588SlaveRxTable	OBJECT-TYPE
		SYNTAX		SEQUENCE  OF  NptPTP1588SlaveRxEntry
		MAX-ACCESS	not-accessible
		STATUS		current
		DESCRIPTION	"Description"
		::=  { nptPTP1588SlaveRx  1 }

	nptPTP1588SlaveRxEntry	OBJECT-TYPE
		SYNTAX		NptPTP1588SlaveRxEntry
		MAX-ACCESS	not-accessible
		STATUS		current
		DESCRIPTION	"Row Description"
		INDEX		{  nptPTP1588SlaveRxIndex  }
		::=  { nptPTP1588SlaveRxTable 1 }

	NptPTP1588SlaveRxEntry  ::=  SEQUENCE {
	    nptPTP1588SlaveRxIndex  Integer32,
		nptPTP1588SlaveRxDisContinuityTime  Integer32,
		nptPTP1588SlaveRxElapsedTime  DisplayString,
		nptPTP1588SlaveRxPDMin Integer32,
		nptPTP1588SlaveRxPDMax Integer32,
		nptPTP1588SlaveRxPDStartTime Integer32,
		nptPTP1588SlaveRxPDElapsedTime Integer32,
		nptPTP1588SlaveRxPDValidPkts Integer32,
		nptPTP1588SlaveRxPDVBIN1 DisplayString,
		nptPTP1588SlaveRxPDVBIN2 DisplayString,
		nptPTP1588SlaveRxPDVBIN3 DisplayString,
		nptPTP1588SlaveRxPDVBIN4 DisplayString,
		nptPTP1588SlaveRxPDVBIN5 DisplayString,
		nptPTP1588SlaveRxPDVBIN6 DisplayString,
		nptPTP1588SlaveRxPDVBIN7 DisplayString,
		nptPTP1588SlaveRxPDVBIN8 DisplayString,
		nptPTP1588SlaveRxPDVBIN9 DisplayString,
		nptPTP1588SlaveRxPDVBIN10 DisplayString,
		nptPTP1588SlaveRxPDVBIN11 DisplayString,
		nptPTP1588SlaveRxPDVBIN12 DisplayString,
		nptPTP1588SlaveRxPDVBIN13 DisplayString,
		nptPTP1588SlaveRxPDVBIN14 DisplayString,
		nptPTP1588SlaveRxPDVBIN15 DisplayString,
		nptPTP1588SlaveRxPDVBIN16 DisplayString,
		nptPTP1588SlaveRxPDVBIN17 DisplayString,
		nptPTP1588SlaveRxPDVBIN18 DisplayString,
		nptPTP1588SlaveRxPDVBIN19 DisplayString,
		nptPTP1588SlaveRxPDVBIN20 DisplayString,
		nptPTP1588SlaveRxPDVBIN21 DisplayString,
		nptPTP1588SlaveRxPDVBIN22 DisplayString,
		nptPTP1588SlaveRxPDVBIN23 DisplayString,
		nptPTP1588SlaveRxPDVBIN24 DisplayString,
		nptPTP1588SlaveRxPDVBIN25 DisplayString
		}


	nptPTP1588SlaveRxIndex	OBJECT-TYPE	
		SYNTAX			Integer32  ( -2147483648 .. 2147483647  ) 
		MAX-ACCESS		read-only
		STATUS			current
		DESCRIPTION		"Column Description"
		::=  {  nptPTP1588SlaveRxEntry  1  }


    nptPTP1588SlaveRxDisContinuityTime	OBJECT-TYPE	
		SYNTAX			Integer32
		MAX-ACCESS		read-only
		STATUS			current
		DESCRIPTION		"DisContinuity Time"
		::=  {  nptPTP1588SlaveRxEntry  2  }
		
	nptPTP1588SlaveRxElapsedTime	OBJECT-TYPE	
		SYNTAX			DisplayString
		MAX-ACCESS		read-only
		STATUS			current
		DESCRIPTION		"Elapsed Time"
		::=  {  nptPTP1588SlaveRxEntry  3  }

    nptPTP1588SlaveRxPDMin	OBJECT-TYPE	
		SYNTAX			Integer32 
		MAX-ACCESS		read-only
		STATUS			current
		DESCRIPTION		"Description"
		::=  {  nptPTP1588SlaveRxEntry  4  }


    nptPTP1588SlaveRxPDMax	OBJECT-TYPE	
		SYNTAX			Integer32
		MAX-ACCESS		read-only
		STATUS			current
		DESCRIPTION		"Description"
		::=  {  nptPTP1588SlaveRxEntry  5  }

    nptPTP1588SlaveRxPDStartTime	OBJECT-TYPE	
		SYNTAX			Integer32
		MAX-ACCESS		read-only
		STATUS			current
		DESCRIPTION		"Description"
		::=  {  nptPTP1588SlaveRxEntry  6  }

    nptPTP1588SlaveRxPDElapsedTime	OBJECT-TYPE	
		SYNTAX			Integer32
		MAX-ACCESS		read-only
		STATUS			current
		DESCRIPTION		"Description"
		::=  {  nptPTP1588SlaveRxEntry  7  }

    nptPTP1588SlaveRxPDValidPkts	OBJECT-TYPE	
		SYNTAX			Integer32
		MAX-ACCESS		read-only
		STATUS			current
		DESCRIPTION		"Description"
		::=  {  nptPTP1588SlaveRxEntry  8  }

    nptPTP1588SlaveRxPDVBIN1	OBJECT-TYPE	
		SYNTAX			DisplayString
		MAX-ACCESS		read-only
		STATUS			current
		DESCRIPTION		"PDV BIN (-0.0005 : 0.0005) "
		::=  {  nptPTP1588SlaveRxEntry  9  }

    nptPTP1588SlaveRxPDVBIN2	OBJECT-TYPE	
		SYNTAX			DisplayString
		MAX-ACCESS		read-only
		STATUS			current
		DESCRIPTION		"PDV BIN(0.0005:0.005)"
		::=  {  nptPTP1588SlaveRxEntry  10  }

    nptPTP1588SlaveRxPDVBIN3	OBJECT-TYPE	
		SYNTAX			DisplayString
		MAX-ACCESS		read-only
		STATUS			current
		DESCRIPTION		"PDV BIN(0.005:0.010)"
		::=  {  nptPTP1588SlaveRxEntry  11  }

    nptPTP1588SlaveRxPDVBIN4	OBJECT-TYPE	
		SYNTAX			DisplayString
		MAX-ACCESS		read-only
		STATUS			current
		DESCRIPTION		"PDV BIN(0.01:0.05)"
		::=  {  nptPTP1588SlaveRxEntry  12  }

    nptPTP1588SlaveRxPDVBIN5	OBJECT-TYPE	
		SYNTAX			DisplayString
		MAX-ACCESS		read-only
		STATUS			current
		DESCRIPTION		"PDV BIN(0.05:0.10)"
		::=  {  nptPTP1588SlaveRxEntry  13  }

    nptPTP1588SlaveRxPDVBIN6	OBJECT-TYPE	
		SYNTAX			DisplayString
		MAX-ACCESS		read-only
		STATUS			current
		DESCRIPTION		"PDV BIN(0.10:0.15)"
		::=  {  nptPTP1588SlaveRxEntry  14  }

    nptPTP1588SlaveRxPDVBIN7	OBJECT-TYPE	
		SYNTAX			DisplayString
		MAX-ACCESS		read-only
		STATUS			current
		DESCRIPTION		"PDV BIN(0.15:0.20)"
		::=  {  nptPTP1588SlaveRxEntry  15  }

    nptPTP1588SlaveRxPDVBIN8	OBJECT-TYPE	
		SYNTAX			DisplayString
		MAX-ACCESS		read-only
		STATUS			current
		DESCRIPTION		"PDV BIN(0.2:0.3)"
		::=  {  nptPTP1588SlaveRxEntry  16  }

    nptPTP1588SlaveRxPDVBIN9	OBJECT-TYPE	
		SYNTAX			DisplayString
		MAX-ACCESS		read-only
		STATUS			current
		DESCRIPTION		"PDV BIN(0.3:0.4)"
		::=  {  nptPTP1588SlaveRxEntry  17  }

    nptPTP1588SlaveRxPDVBIN10	OBJECT-TYPE	
		SYNTAX			DisplayString
		MAX-ACCESS		read-only
		STATUS			current
		DESCRIPTION		"PDV BIN(0.4:0.5)"
		::=  {  nptPTP1588SlaveRxEntry  18  }

    nptPTP1588SlaveRxPDVBIN11	OBJECT-TYPE	
		SYNTAX			DisplayString
		MAX-ACCESS		read-only
		STATUS			current
		DESCRIPTION		"PDV BIN(0.5:0.6)"
		::=  {  nptPTP1588SlaveRxEntry  19  }

    nptPTP1588SlaveRxPDVBIN12	OBJECT-TYPE	
		SYNTAX			DisplayString
		MAX-ACCESS		read-only
		STATUS			current
		DESCRIPTION		"PDV BIN(0.6:0.7)"
		::=  {  nptPTP1588SlaveRxEntry  20  }

    nptPTP1588SlaveRxPDVBIN13	OBJECT-TYPE	
		SYNTAX			DisplayString
		MAX-ACCESS		read-only
		STATUS			current
		DESCRIPTION		"PDV BIN(0.7:0.8)"
		::=  {  nptPTP1588SlaveRxEntry  21  }

    nptPTP1588SlaveRxPDVBIN14	OBJECT-TYPE	
		SYNTAX			DisplayString
		MAX-ACCESS		read-only
		STATUS			current
		DESCRIPTION		"PDV BIN(0.8:0.9)"
		::=  {  nptPTP1588SlaveRxEntry  22  }

    nptPTP1588SlaveRxPDVBIN15	OBJECT-TYPE	
		SYNTAX			DisplayString
		MAX-ACCESS		read-only
		STATUS			current
		DESCRIPTION		"PDV BIN(0.9:1.0)"
		::=  {  nptPTP1588SlaveRxEntry  23  }

    nptPTP1588SlaveRxPDVBIN16	OBJECT-TYPE	
		SYNTAX			DisplayString
		MAX-ACCESS		read-only
		STATUS			current
		DESCRIPTION		"PDV BIN(1.0:2.0)"
		::=  {  nptPTP1588SlaveRxEntry  24  }

    nptPTP1588SlaveRxPDVBIN17	OBJECT-TYPE	
		SYNTAX			DisplayString
		MAX-ACCESS		read-only
		STATUS			current
		DESCRIPTION		"PDV BIN(2.0:3.0)"
		::=  {  nptPTP1588SlaveRxEntry  25  }

    nptPTP1588SlaveRxPDVBIN18	OBJECT-TYPE	
		SYNTAX			DisplayString
		MAX-ACCESS		read-only
		STATUS			current
		DESCRIPTION		"PDV BIN(3.0:4.0)"
		::=  {  nptPTP1588SlaveRxEntry  26  }

    nptPTP1588SlaveRxPDVBIN19	OBJECT-TYPE	
		SYNTAX			DisplayString
		MAX-ACCESS		read-only
		STATUS			current
		DESCRIPTION		"PDV BIN(4.0:5.0)"
		::=  {  nptPTP1588SlaveRxEntry  27  }

    nptPTP1588SlaveRxPDVBIN20	OBJECT-TYPE	
		SYNTAX			DisplayString
		MAX-ACCESS		read-only
		STATUS			current
		DESCRIPTION		"PDV BIN(5.0:6.0)"
		::=  {  nptPTP1588SlaveRxEntry  28  }

    nptPTP1588SlaveRxPDVBIN21	OBJECT-TYPE	
		SYNTAX			DisplayString
		MAX-ACCESS		read-only
		STATUS			current
		DESCRIPTION		"PDV BIN(6.0:7.0)"
		::=  {  nptPTP1588SlaveRxEntry  29  }

    nptPTP1588SlaveRxPDVBIN22	OBJECT-TYPE	
		SYNTAX			DisplayString
		MAX-ACCESS		read-only
		STATUS			current
		DESCRIPTION		"PDV BIN(7.0:8.0)"
		::=  {  nptPTP1588SlaveRxEntry  30  }

    nptPTP1588SlaveRxPDVBIN23	OBJECT-TYPE	
		SYNTAX			DisplayString
		MAX-ACCESS		read-only
		STATUS			current
		DESCRIPTION		"PDV BIN(8.0:9.0)"
		::=  {  nptPTP1588SlaveRxEntry  31  }

    nptPTP1588SlaveRxPDVBIN24	OBJECT-TYPE	
		SYNTAX			DisplayString
		MAX-ACCESS		read-only
		STATUS			current
		DESCRIPTION		"PDV BIN(9.0:10.0)"
		::=  {  nptPTP1588SlaveRxEntry  32  }

    nptPTP1588SlaveRxPDVBIN25	OBJECT-TYPE	
		SYNTAX			DisplayString
		MAX-ACCESS		read-only
		STATUS			current
		DESCRIPTION		"PDV BIN(10.0:100)"
		::=  {  nptPTP1588SlaveRxEntry  33  }
		
		
	nptPTP1588SlaveTxTable	OBJECT-TYPE
		SYNTAX		SEQUENCE  OF  NptPTP1588SlaveTxEntry
		MAX-ACCESS	not-accessible
		STATUS		current
		DESCRIPTION	"Description"
		::=  { nptPTP1588SlaveTx  1 }

	nptPTP1588SlaveTxEntry	OBJECT-TYPE
		SYNTAX		NptPTP1588SlaveTxEntry
		MAX-ACCESS	not-accessible
		STATUS		current
		DESCRIPTION	"Row Description"
		INDEX		{  nptPTP1588SlaveTxIndex  }
		::=  { nptPTP1588SlaveTxTable 1 }

	NptPTP1588SlaveTxEntry  ::=  SEQUENCE {
	    nptPTP1588SlaveTxIndex  Integer32,
		nptPTP1588SlaveTxDisContinuityTime  Integer32,
		nptPTP1588SlaveTxElapsedTime  DisplayString,
		nptPTP1588SlaveTxPDMin Integer32,
		nptPTP1588SlaveTxPDMax Integer32,
		nptPTP1588SlaveTxPDStartTime Integer32,
		nptPTP1588SlaveTxPDElapsedTime Integer32,
		nptPTP1588SlaveTxPDValidPkts Integer32,
		nptPTP1588SlaveTxPDVBIN1 DisplayString,
		nptPTP1588SlaveTxPDVBIN2 DisplayString,
		nptPTP1588SlaveTxPDVBIN3 DisplayString,
		nptPTP1588SlaveTxPDVBIN4 DisplayString,
		nptPTP1588SlaveTxPDVBIN5 DisplayString,
		nptPTP1588SlaveTxPDVBIN6 DisplayString,
		nptPTP1588SlaveTxPDVBIN7 DisplayString,
		nptPTP1588SlaveTxPDVBIN8 DisplayString,
		nptPTP1588SlaveTxPDVBIN9 DisplayString,
		nptPTP1588SlaveTxPDVBIN10 DisplayString,
		nptPTP1588SlaveTxPDVBIN11 DisplayString,
		nptPTP1588SlaveTxPDVBIN12 DisplayString,
		nptPTP1588SlaveTxPDVBIN13 DisplayString,
		nptPTP1588SlaveTxPDVBIN14 DisplayString,
		nptPTP1588SlaveTxPDVBIN15 DisplayString,
		nptPTP1588SlaveTxPDVBIN16 DisplayString,
		nptPTP1588SlaveTxPDVBIN17 DisplayString,
		nptPTP1588SlaveTxPDVBIN18 DisplayString,
		nptPTP1588SlaveTxPDVBIN19 DisplayString,
		nptPTP1588SlaveTxPDVBIN20 DisplayString,
		nptPTP1588SlaveTxPDVBIN21 DisplayString,
		nptPTP1588SlaveTxPDVBIN22 DisplayString,
		nptPTP1588SlaveTxPDVBIN23 DisplayString,
		nptPTP1588SlaveTxPDVBIN24 DisplayString,
		nptPTP1588SlaveTxPDVBIN25 DisplayString
		}


	nptPTP1588SlaveTxIndex	OBJECT-TYPE	
		SYNTAX			Integer32  ( -2147483648 .. 2147483647  ) 
		MAX-ACCESS		read-only
		STATUS			current
		DESCRIPTION		"Column Description"
		::=  {  nptPTP1588SlaveTxEntry  1  }


    nptPTP1588SlaveTxDisContinuityTime	OBJECT-TYPE	
		SYNTAX			Integer32
		MAX-ACCESS		read-only
		STATUS			current
		DESCRIPTION		"DisContinuity Time"
		::=  {  nptPTP1588SlaveTxEntry  2  }
		
	nptPTP1588SlaveTxElapsedTime	OBJECT-TYPE	
		SYNTAX			DisplayString
		MAX-ACCESS		read-only
		STATUS			current
		DESCRIPTION		"Elapsed Time"
		::=  {  nptPTP1588SlaveTxEntry  3  }

    nptPTP1588SlaveTxPDMin	OBJECT-TYPE	
		SYNTAX			Integer32 
		MAX-ACCESS		read-only
		STATUS			current
		DESCRIPTION		"Description"
		::=  {  nptPTP1588SlaveTxEntry  4  }


    nptPTP1588SlaveTxPDMax	OBJECT-TYPE	
		SYNTAX			Integer32
		MAX-ACCESS		read-only
		STATUS			current
		DESCRIPTION		"Description"
		::=  {  nptPTP1588SlaveTxEntry  5  }

    nptPTP1588SlaveTxPDStartTime	OBJECT-TYPE	
		SYNTAX			Integer32
		MAX-ACCESS		read-only
		STATUS			current
		DESCRIPTION		"Description"
		::=  {  nptPTP1588SlaveTxEntry  6  }

    nptPTP1588SlaveTxPDElapsedTime	OBJECT-TYPE	
		SYNTAX			Integer32
		MAX-ACCESS		read-only
		STATUS			current
		DESCRIPTION		"Description"
		::=  {  nptPTP1588SlaveTxEntry  7  }

    nptPTP1588SlaveTxPDValidPkts	OBJECT-TYPE	
		SYNTAX			Integer32
		MAX-ACCESS		read-only
		STATUS			current
		DESCRIPTION		"Description"
		::=  {  nptPTP1588SlaveTxEntry  8  }

    nptPTP1588SlaveTxPDVBIN1	OBJECT-TYPE	
		SYNTAX			DisplayString
		MAX-ACCESS		read-only
		STATUS			current
		DESCRIPTION		"PDV BIN (-0.0005 : 0.0005) "
		::=  {  nptPTP1588SlaveTxEntry  9  }

    nptPTP1588SlaveTxPDVBIN2	OBJECT-TYPE	
		SYNTAX			DisplayString
		MAX-ACCESS		read-only
		STATUS			current
		DESCRIPTION		"PDV BIN(0.0005:0.005)"
		::=  {  nptPTP1588SlaveTxEntry  10  }

    nptPTP1588SlaveTxPDVBIN3	OBJECT-TYPE	
		SYNTAX			DisplayString
		MAX-ACCESS		read-only
		STATUS			current
		DESCRIPTION		"PDV BIN(0.005:0.010)"
		::=  {  nptPTP1588SlaveTxEntry  11  }

    nptPTP1588SlaveTxPDVBIN4	OBJECT-TYPE	
		SYNTAX			DisplayString
		MAX-ACCESS		read-only
		STATUS			current
		DESCRIPTION		"PDV BIN(0.01:0.05)"
		::=  {  nptPTP1588SlaveTxEntry  12  }

    nptPTP1588SlaveTxPDVBIN5	OBJECT-TYPE	
		SYNTAX			DisplayString
		MAX-ACCESS		read-only
		STATUS			current
		DESCRIPTION		"PDV BIN(0.05:0.10)"
		::=  {  nptPTP1588SlaveTxEntry  13  }

    nptPTP1588SlaveTxPDVBIN6	OBJECT-TYPE	
		SYNTAX			DisplayString
		MAX-ACCESS		read-only
		STATUS			current
		DESCRIPTION		"PDV BIN(0.10:0.15)"
		::=  {  nptPTP1588SlaveTxEntry  14  }

    nptPTP1588SlaveTxPDVBIN7	OBJECT-TYPE	
		SYNTAX			DisplayString
		MAX-ACCESS		read-only
		STATUS			current
		DESCRIPTION		"PDV BIN(0.15:0.20)"
		::=  {  nptPTP1588SlaveTxEntry  15  }

    nptPTP1588SlaveTxPDVBIN8	OBJECT-TYPE	
		SYNTAX			DisplayString
		MAX-ACCESS		read-only
		STATUS			current
		DESCRIPTION		"PDV BIN(0.2:0.3)"
		::=  {  nptPTP1588SlaveTxEntry  16  }

    nptPTP1588SlaveTxPDVBIN9	OBJECT-TYPE	
		SYNTAX			DisplayString
		MAX-ACCESS		read-only
		STATUS			current
		DESCRIPTION		"PDV BIN(0.3:0.4)"
		::=  {  nptPTP1588SlaveTxEntry  17  }

    nptPTP1588SlaveTxPDVBIN10	OBJECT-TYPE	
		SYNTAX			DisplayString
		MAX-ACCESS		read-only
		STATUS			current
		DESCRIPTION		"PDV BIN(0.4:0.5)"
		::=  {  nptPTP1588SlaveTxEntry  18  }

    nptPTP1588SlaveTxPDVBIN11	OBJECT-TYPE	
		SYNTAX			DisplayString
		MAX-ACCESS		read-only
		STATUS			current
		DESCRIPTION		"PDV BIN(0.5:0.6)"
		::=  {  nptPTP1588SlaveTxEntry  19  }

    nptPTP1588SlaveTxPDVBIN12	OBJECT-TYPE	
		SYNTAX			DisplayString
		MAX-ACCESS		read-only
		STATUS			current
		DESCRIPTION		"PDV BIN(0.6:0.7)"
		::=  {  nptPTP1588SlaveTxEntry  20  }

    nptPTP1588SlaveTxPDVBIN13	OBJECT-TYPE	
		SYNTAX			DisplayString
		MAX-ACCESS		read-only
		STATUS			current
		DESCRIPTION		"PDV BIN(0.7:0.8)"
		::=  {  nptPTP1588SlaveTxEntry  21  }

    nptPTP1588SlaveTxPDVBIN14	OBJECT-TYPE	
		SYNTAX			DisplayString
		MAX-ACCESS		read-only
		STATUS			current
		DESCRIPTION		"PDV BIN(0.8:0.9)"
		::=  {  nptPTP1588SlaveTxEntry  22  }

    nptPTP1588SlaveTxPDVBIN15	OBJECT-TYPE	
		SYNTAX			DisplayString
		MAX-ACCESS		read-only
		STATUS			current
		DESCRIPTION		"PDV BIN(0.9:1.0)"
		::=  {  nptPTP1588SlaveTxEntry  23  }

    nptPTP1588SlaveTxPDVBIN16	OBJECT-TYPE	
		SYNTAX			DisplayString
		MAX-ACCESS		read-only
		STATUS			current
		DESCRIPTION		"PDV BIN(1.0:2.0)"
		::=  {  nptPTP1588SlaveTxEntry  24  }

    nptPTP1588SlaveTxPDVBIN17	OBJECT-TYPE	
		SYNTAX			DisplayString
		MAX-ACCESS		read-only
		STATUS			current
		DESCRIPTION		"PDV BIN(2.0:3.0)"
		::=  {  nptPTP1588SlaveTxEntry  25  }

    nptPTP1588SlaveTxPDVBIN18	OBJECT-TYPE	
		SYNTAX			DisplayString
		MAX-ACCESS		read-only
		STATUS			current
		DESCRIPTION		"PDV BIN(3.0:4.0)"
		::=  {  nptPTP1588SlaveTxEntry  26  }

    nptPTP1588SlaveTxPDVBIN19	OBJECT-TYPE	
		SYNTAX			DisplayString
		MAX-ACCESS		read-only
		STATUS			current
		DESCRIPTION		"PDV BIN(4.0:5.0)"
		::=  {  nptPTP1588SlaveTxEntry  27  }

    nptPTP1588SlaveTxPDVBIN20	OBJECT-TYPE	
		SYNTAX			DisplayString
		MAX-ACCESS		read-only
		STATUS			current
		DESCRIPTION		"PDV BIN(5.0:6.0)"
		::=  {  nptPTP1588SlaveTxEntry  28  }

    nptPTP1588SlaveTxPDVBIN21	OBJECT-TYPE	
		SYNTAX			DisplayString
		MAX-ACCESS		read-only
		STATUS			current
		DESCRIPTION		"PDV BIN(6.0:7.0)"
		::=  {  nptPTP1588SlaveTxEntry  29  }

    nptPTP1588SlaveTxPDVBIN22	OBJECT-TYPE	
		SYNTAX			DisplayString
		MAX-ACCESS		read-only
		STATUS			current
		DESCRIPTION		"PDV BIN(7.0:8.0)"
		::=  {  nptPTP1588SlaveTxEntry  30  }

    nptPTP1588SlaveTxPDVBIN23	OBJECT-TYPE	
		SYNTAX			DisplayString
		MAX-ACCESS		read-only
		STATUS			current
		DESCRIPTION		"PDV BIN(8.0:9.0)"
		::=  {  nptPTP1588SlaveTxEntry  31  }

    nptPTP1588SlaveTxPDVBIN24	OBJECT-TYPE	
		SYNTAX			DisplayString
		MAX-ACCESS		read-only
		STATUS			current
		DESCRIPTION		"PDV BIN(9.0:10.0)"
		::=  {  nptPTP1588SlaveTxEntry  32  }

    nptPTP1588SlaveTxPDVBIN25	OBJECT-TYPE	
		SYNTAX			DisplayString
		MAX-ACCESS		read-only
		STATUS			current
		DESCRIPTION		"PDV BIN(10.0:100)"
		::=  {  nptPTP1588SlaveTxEntry  33  }
		
	nptPTP1588MasterTable	OBJECT-TYPE
		SYNTAX		SEQUENCE  OF  NptPTP1588MasterEntry
		MAX-ACCESS	not-accessible
		STATUS		current
		DESCRIPTION	"Description"
		::=  { nptPTP1588Master  1 }

	nptPTP1588MasterEntry	OBJECT-TYPE
		SYNTAX		NptPTP1588MasterEntry
		MAX-ACCESS	not-accessible
		STATUS		current
		DESCRIPTION	"Row Description"
		INDEX		{  nptPTP1588MasterIndex  }
		::=  { nptPTP1588MasterTable 1 }

	NptPTP1588MasterEntry  ::=  SEQUENCE {
	    nptPTP1588MasterIndex  Integer32,
        nptPTP1588MasterSlaveIP  DisplayString,
        nptPTP1588MasterSlaveMAC  DisplayString,
		nptPTP1588MasterDisContinuityTime  Integer32,
		nptPTP1588MasterElapsedTime  DisplayString,
		nptPTP1588MasterTxAnnoucePkts Counter64,
		nptPTP1588MasterTxSyncPkts Counter64,
		nptPTP1588MasterTxFollowupPkts Counter64,
		nptPTP1588MasterRxDelayReqPkts Counter64,
		nptPTP1588MasterMissingDelayReqPkts Counter64,
		nptPTP1588MasterMissorderDelayReqPkts Counter64,
		nptPTP1588MasterTxDelayRespPkts Counter64
		}


	nptPTP1588MasterIndex	OBJECT-TYPE	
		SYNTAX			Integer32  ( -2147483648 .. 2147483647  ) 
		MAX-ACCESS		read-only
		STATUS			current
		DESCRIPTION		"Column Description"
		::=  {  nptPTP1588MasterEntry  1  }


    nptPTP1588MasterSlaveIP	OBJECT-TYPE	
		SYNTAX			DisplayString 
		MAX-ACCESS		read-only
		STATUS			current
		DESCRIPTION		"Slave IP"
		::=  {  nptPTP1588MasterEntry  2  }

    nptPTP1588MasterSlaveMAC	OBJECT-TYPE	
		SYNTAX			DisplayString 
		MAX-ACCESS		read-only
		STATUS			current
		DESCRIPTION		"Slave MAC"
		::=  {  nptPTP1588MasterEntry  3  }

    nptPTP1588MasterDisContinuityTime	OBJECT-TYPE	
		SYNTAX			Integer32
		MAX-ACCESS		read-only
		STATUS			current
		DESCRIPTION		"DisContinuity Time"
		::=  {  nptPTP1588MasterEntry  4  }
		
	nptPTP1588MasterElapsedTime	OBJECT-TYPE	
		SYNTAX			DisplayString
		MAX-ACCESS		read-only
		STATUS			current
		DESCRIPTION		"Elapsed Time"
		::=  {  nptPTP1588MasterEntry  5  }


    nptPTP1588MasterTxAnnoucePkts	OBJECT-TYPE	
		SYNTAX			Counter64
		MAX-ACCESS		read-only
		STATUS			current
		DESCRIPTION		"Description"
		::=  {  nptPTP1588MasterEntry  6  }

    nptPTP1588MasterTxSyncPkts	OBJECT-TYPE	
		SYNTAX			Counter64
		MAX-ACCESS		read-only
		STATUS			current
		DESCRIPTION		"Description"
		::=  {  nptPTP1588MasterEntry  7  }

    nptPTP1588MasterTxFollowupPkts	OBJECT-TYPE	
		SYNTAX			Counter64
		MAX-ACCESS		read-only
		STATUS			current
		DESCRIPTION		"Description"
		::=  {  nptPTP1588MasterEntry  8  }

    nptPTP1588MasterRxDelayReqPkts	OBJECT-TYPE	
		SYNTAX			Counter64
		MAX-ACCESS		read-only
		STATUS			current
		DESCRIPTION		"Description"
		::=  {  nptPTP1588MasterEntry  9  }

    nptPTP1588MasterMissingDelayReqPkts	OBJECT-TYPE	
		SYNTAX			Counter64
		MAX-ACCESS		read-only
		STATUS			current
		DESCRIPTION		"Description"
		::=  {  nptPTP1588MasterEntry  10  }

    nptPTP1588MasterMissorderDelayReqPkts	OBJECT-TYPE	
		SYNTAX			Counter64
		MAX-ACCESS		read-only
		STATUS			current
		DESCRIPTION		"Description"
		::=  {  nptPTP1588MasterEntry  11  }

    nptPTP1588MasterTxDelayRespPkts	OBJECT-TYPE	
		SYNTAX			Counter64
		MAX-ACCESS		read-only
		STATUS			current
		DESCRIPTION		"Description"
		::=  {  nptPTP1588MasterEntry  12  }
		
	nptPTP1588SlaveTable	OBJECT-TYPE
		SYNTAX		SEQUENCE  OF  NptPTP1588SlaveEntry
		MAX-ACCESS	not-accessible
		STATUS		current
		DESCRIPTION	"Description"
		::=  { nptPTP1588Slave  1 }

	nptPTP1588SlaveEntry	OBJECT-TYPE
		SYNTAX		NptPTP1588SlaveEntry
		MAX-ACCESS	not-accessible
		STATUS		current
		DESCRIPTION	"Row Description"
		INDEX		{  nptPTP1588SlaveIndex  }
		::=  { nptPTP1588SlaveTable 1 }

	NptPTP1588SlaveEntry  ::=  SEQUENCE {
	    nptPTP1588SlaveIndex  Integer32,
		nptPTP1588SlaveDisContinuityTime  Integer32,
		nptPTP1588SlaveElapsedTime  DisplayString,
		nptPTP1588SlaveRxAnnoucePkts Counter64,
		nptPTP1588SlaveDropAnnoucePkts Counter64,
		nptPTP1588SlaveRxSyncPkts Counter64,
		nptPTP1588SlaveDropSyncPkts Counter64,
		nptPTP1588SlaveMissingSyncPkts Counter64,
		nptPTP1588SlaveMissorderSyncPkts Counter64,
		nptPTP1588SlaveRxFollowupPkts Counter64,
		nptPTP1588SlaveDropFollowupPkts Counter64,
		nptPTP1588SlaveMissingFollowupPkts Counter64,
		nptPTP1588SlaveTxDelayReqPkts Counter64,
		nptPTP1588SlaveRxDelayRespPkts Counter64,
		nptPTP1588SlaveDropDelayRespPkts Counter64,
		nptPTP1588SlaveMissingDelayRespPkts Counter64,
		nptPTP1588SlaveMissorderDelayRespPkts Counter64
		}


	nptPTP1588SlaveIndex	OBJECT-TYPE	
		SYNTAX			Integer32  ( -2147483648 .. 2147483647  ) 
		MAX-ACCESS		read-only
		STATUS			current
		DESCRIPTION		"Column Description"
		::=  {  nptPTP1588SlaveEntry  1  }

    nptPTP1588SlaveDisContinuityTime	OBJECT-TYPE	
		SYNTAX			Integer32
		MAX-ACCESS		read-only
		STATUS			current
		DESCRIPTION		"DisContinuity Time"
		::=  {  nptPTP1588SlaveEntry  2  }
		
	nptPTP1588SlaveElapsedTime	OBJECT-TYPE	
		SYNTAX			DisplayString
		MAX-ACCESS		read-only
		STATUS			current
		DESCRIPTION		"Elapsed Time"
		::=  {  nptPTP1588SlaveEntry  3  }


    nptPTP1588SlaveRxAnnoucePkts	OBJECT-TYPE	
		SYNTAX			Counter64
		MAX-ACCESS		read-only
		STATUS			current
		DESCRIPTION		"Description"
		::=  {  nptPTP1588SlaveEntry  4  }

    nptPTP1588SlaveDropAnnoucePkts	OBJECT-TYPE	
		SYNTAX			Counter64
		MAX-ACCESS		read-only
		STATUS			current
		DESCRIPTION		"Description"
		::=  {  nptPTP1588SlaveEntry  5  }

    nptPTP1588SlaveRxSyncPkts	OBJECT-TYPE	
		SYNTAX			Counter64
		MAX-ACCESS		read-only
		STATUS			current
		DESCRIPTION		"Description"
		::=  {  nptPTP1588SlaveEntry  6  }

    nptPTP1588SlaveDropSyncPkts	OBJECT-TYPE	
		SYNTAX			Counter64
		MAX-ACCESS		read-only
		STATUS			current
		DESCRIPTION		"Description"
		::=  {  nptPTP1588SlaveEntry  7  }

    nptPTP1588SlaveMissingSyncPkts	OBJECT-TYPE	
		SYNTAX			Counter64
		MAX-ACCESS		read-only
		STATUS			current
		DESCRIPTION		"Description"
		::=  {  nptPTP1588SlaveEntry  8  }

    nptPTP1588SlaveMissorderSyncPkts	OBJECT-TYPE	
		SYNTAX			Counter64
		MAX-ACCESS		read-only
		STATUS			current
		DESCRIPTION		"Description"
		::=  {  nptPTP1588SlaveEntry  9  }

    nptPTP1588SlaveRxFollowupPkts	OBJECT-TYPE	
		SYNTAX			Counter64
		MAX-ACCESS		read-only
		STATUS			current
		DESCRIPTION		"Description"
		::=  {  nptPTP1588SlaveEntry  10  }

    nptPTP1588SlaveDropFollowupPkts	OBJECT-TYPE	
		SYNTAX			Counter64
		MAX-ACCESS		read-only
		STATUS			current
		DESCRIPTION		"Description"
		::=  {  nptPTP1588SlaveEntry  11  }

    nptPTP1588SlaveMissingFollowupPkts	OBJECT-TYPE	
		SYNTAX			Counter64
		MAX-ACCESS		read-only
		STATUS			current
		DESCRIPTION		"Description"
		::=  {  nptPTP1588SlaveEntry  12  }

    nptPTP1588SlaveTxDelayReqPkts	OBJECT-TYPE	
		SYNTAX			Counter64
		MAX-ACCESS		read-only
		STATUS			current
		DESCRIPTION		"Description"
		::=  {  nptPTP1588SlaveEntry  13  }

    nptPTP1588SlaveRxDelayRespPkts	OBJECT-TYPE	
		SYNTAX			Counter64
		MAX-ACCESS		read-only
		STATUS			current
		DESCRIPTION		"Description"
		::=  {  nptPTP1588SlaveEntry  14  }

    nptPTP1588SlaveDropDelayRespPkts	OBJECT-TYPE	
		SYNTAX			Counter64
		MAX-ACCESS		read-only
		STATUS			current
		DESCRIPTION		"Description"
		::=  {  nptPTP1588SlaveEntry  15  }

    nptPTP1588SlaveMissingDelayRespPkts	OBJECT-TYPE	
		SYNTAX			Counter64
		MAX-ACCESS		read-only
		STATUS			current
		DESCRIPTION		"Description"
		::=  {  nptPTP1588SlaveEntry  16  }

    nptPTP1588SlaveMissorderDelayRespPkts	OBJECT-TYPE	
		SYNTAX			Counter64
		MAX-ACCESS		read-only
		STATUS			current
		DESCRIPTION		"Description"
		::=  {  nptPTP1588SlaveEntry  17  }
		
		
	nptPTP1588PortTable	OBJECT-TYPE
		SYNTAX		SEQUENCE  OF  NptPTP1588PortEntry
		MAX-ACCESS	not-accessible
		STATUS		current
		DESCRIPTION	"Description"
		::=  { nptPTP1588Port  1 }

	nptPTP1588PortEntry	OBJECT-TYPE
		SYNTAX		NptPTP1588PortEntry
		MAX-ACCESS	not-accessible
		STATUS		current
		DESCRIPTION	"Row Description"
		INDEX		{  nptPTP1588PortIndex  }
		::=  { nptPTP1588PortTable 1 }

	NptPTP1588PortEntry  ::=  SEQUENCE {
	    nptPTP1588PortIndex  Integer32,
        nptPTP1588PortName  DisplayString,
		nptPTP1588PortDisContinuityTime  Integer32,
		nptPTP1588PortElapsedTime  DisplayString,
		nptPTP1588PortTxAnnoucePkts Counter64,
		nptPTP1588PortRxAnnoucePkts Counter64,
		nptPTP1588PortDropAnnoucePkts Counter64,
        nptPTP1588PortLostAnnoucePkts Counter64,
		nptPTP1588PortTxSyncPkts Counter64,
		nptPTP1588PortRxSyncPkts Counter64,
		nptPTP1588PortDropSyncPkts Counter64,
        nptPTP1588PortLostSyncPkts Counter64,
		nptPTP1588PortTxFollowupPkts Counter64,
		nptPTP1588PortRxFollowupPkts Counter64,
		nptPTP1588PortDropFollowupPkts Counter64,
        nptPTP1588PortLostFollowupPkts Counter64,
		nptPTP1588PortTxDelayReqPkts Counter64,
		nptPTP1588PortRxDelayReqPkts Counter64,
		nptPTP1588PortDropDelayReqPkts Counter64,
        nptPTP1588PortLostDelayReqPkts Counter64,
		nptPTP1588PortTxDelayRespPkts Counter64,
		nptPTP1588PortRxDelayRespPkts Counter64,
		nptPTP1588PortDropDelayRespPkts Counter64,
        nptPTP1588PortLostDelayRespPkts Counter64,
		nptPTP1588PortTxSignalPkts Counter64,
		nptPTP1588PortRxSignalPkts Counter64,
		nptPTP1588PortDroppedSignalPkts Counter64,
        nptPTP1588PortLostSignalPkts Counter64,
		nptPTP1588PortTxManagementPkts Counter64,
		nptPTP1588PortRxManagementPkts Counter64,
		nptPTP1588PortDroppedManagementPkts Counter64,
        nptPTP1588PortLostManagementPkts Counter64
		}


	nptPTP1588PortIndex	OBJECT-TYPE	
		SYNTAX			Integer32  ( -2147483648 .. 2147483647  ) 
		MAX-ACCESS		read-only
		STATUS			current
		DESCRIPTION		"Column Description"
		::=  {  nptPTP1588PortEntry  1  }

    nptPTP1588PortName	OBJECT-TYPE	
		SYNTAX			DisplayString 
		MAX-ACCESS		read-only
		STATUS			current
		DESCRIPTION		"port IP"
		::=  {  nptPTP1588PortEntry  2  }

    nptPTP1588PortDisContinuityTime	OBJECT-TYPE	
		SYNTAX			Integer32
		MAX-ACCESS		read-only
		STATUS			current
		DESCRIPTION		"DisContinuity Time"
		::=  {  nptPTP1588PortEntry  3  }
		
	nptPTP1588PortElapsedTime	OBJECT-TYPE	
		SYNTAX			DisplayString
		MAX-ACCESS		read-only
		STATUS			current
		DESCRIPTION		"DisContinuity Time"
		::=  {  nptPTP1588PortEntry  4  }


    nptPTP1588PortTxAnnoucePkts	OBJECT-TYPE	
		SYNTAX			Counter64
		MAX-ACCESS		read-only
		STATUS			current
		DESCRIPTION		"Description"
		::=  {  nptPTP1588PortEntry  5  }

    nptPTP1588PortRxAnnoucePkts	OBJECT-TYPE	
		SYNTAX			Counter64
		MAX-ACCESS		read-only
		STATUS			current
		DESCRIPTION		"Description"
		::=  {  nptPTP1588PortEntry  6  }

    nptPTP1588PortDropAnnoucePkts	OBJECT-TYPE	
		SYNTAX			Counter64
		MAX-ACCESS		read-only
		STATUS			current
		DESCRIPTION		"Description"
		::=  {  nptPTP1588PortEntry  7  }
        
    nptPTP1588PortLostAnnoucePkts	OBJECT-TYPE	
		SYNTAX			Counter64
		MAX-ACCESS		read-only
		STATUS			current
		DESCRIPTION		"Description"
		::=  {  nptPTP1588PortEntry  8  }

    nptPTP1588PortTxSyncPkts	OBJECT-TYPE	
		SYNTAX			Counter64
		MAX-ACCESS		read-only
		STATUS			current
		DESCRIPTION		"Description"
		::=  {  nptPTP1588PortEntry  9  }

    nptPTP1588PortRxSyncPkts	OBJECT-TYPE	
		SYNTAX			Counter64
		MAX-ACCESS		read-only
		STATUS			current
		DESCRIPTION		"Description"
		::=  {  nptPTP1588PortEntry  10  }

    nptPTP1588PortDropSyncPkts	OBJECT-TYPE	
		SYNTAX			Counter64
		MAX-ACCESS		read-only
		STATUS			current
		DESCRIPTION		"Description"
		::=  {  nptPTP1588PortEntry  11  }

    nptPTP1588PortLostSyncPkts	OBJECT-TYPE	
		SYNTAX			Counter64
		MAX-ACCESS		read-only
		STATUS			current
		DESCRIPTION		"Description"
		::=  {  nptPTP1588PortEntry  12  }
        
    nptPTP1588PortTxFollowupPkts	OBJECT-TYPE	
		SYNTAX			Counter64
		MAX-ACCESS		read-only
		STATUS			current
		DESCRIPTION		"Description"
		::=  {  nptPTP1588PortEntry  13  }

    nptPTP1588PortRxFollowupPkts	OBJECT-TYPE	
		SYNTAX			Counter64
		MAX-ACCESS		read-only
		STATUS			current
		DESCRIPTION		"Description"
		::=  {  nptPTP1588PortEntry  14  }

    nptPTP1588PortDropFollowupPkts	OBJECT-TYPE	
		SYNTAX			Counter64
		MAX-ACCESS		read-only
		STATUS			current
		DESCRIPTION		"Description"
		::=  {  nptPTP1588PortEntry  15  }

    nptPTP1588PortLostFollowupPkts	OBJECT-TYPE	
		SYNTAX			Counter64
		MAX-ACCESS		read-only
		STATUS			current
		DESCRIPTION		"Description"
		::=  {  nptPTP1588PortEntry  16  }
        
    nptPTP1588PortTxDelayReqPkts	OBJECT-TYPE	
		SYNTAX			Counter64
		MAX-ACCESS		read-only
		STATUS			current
		DESCRIPTION		"Description"
		::=  {  nptPTP1588PortEntry  17  }

    nptPTP1588PortRxDelayReqPkts	OBJECT-TYPE	
		SYNTAX			Counter64
		MAX-ACCESS		read-only
		STATUS			current
		DESCRIPTION		"Description"
		::=  {  nptPTP1588PortEntry  18  }

    nptPTP1588PortDropDelayReqPkts	OBJECT-TYPE	
		SYNTAX			Counter64
		MAX-ACCESS		read-only
		STATUS			current
		DESCRIPTION		"Description"
		::=  {  nptPTP1588PortEntry  19  }

    nptPTP1588PortLostDelayReqPkts	OBJECT-TYPE	
		SYNTAX			Counter64
		MAX-ACCESS		read-only
		STATUS			current
		DESCRIPTION		"Description"
		::=  {  nptPTP1588PortEntry  20  }
        
    nptPTP1588PortTxDelayRespPkts	OBJECT-TYPE	
		SYNTAX			Counter64
		MAX-ACCESS		read-only
		STATUS			current
		DESCRIPTION		"Description"
		::=  {  nptPTP1588PortEntry  21  }

    nptPTP1588PortRxDelayRespPkts	OBJECT-TYPE	
		SYNTAX			Counter64
		MAX-ACCESS		read-only
		STATUS			current
		DESCRIPTION		"Description"
		::=  {  nptPTP1588PortEntry  22  }

    nptPTP1588PortDropDelayRespPkts	OBJECT-TYPE	
		SYNTAX			Counter64
		MAX-ACCESS		read-only
		STATUS			current
		DESCRIPTION		"Description"
		::=  {  nptPTP1588PortEntry  23  }

    nptPTP1588PortLostDelayRespPkts	OBJECT-TYPE	
		SYNTAX			Counter64
		MAX-ACCESS		read-only
		STATUS			current
		DESCRIPTION		"Description"
		::=  {  nptPTP1588PortEntry  24  }

    nptPTP1588PortTxSignalPkts	OBJECT-TYPE	
		SYNTAX			Counter64
		MAX-ACCESS		read-only
		STATUS			current
		DESCRIPTION		"Description"
		::=  {  nptPTP1588PortEntry  25  }

    nptPTP1588PortRxSignalPkts	OBJECT-TYPE	
		SYNTAX			Counter64
		MAX-ACCESS		read-only
		STATUS			current
		DESCRIPTION		"Description"
		::=  {  nptPTP1588PortEntry  26  }

    nptPTP1588PortDroppedSignalPkts	OBJECT-TYPE	
		SYNTAX			Counter64
		MAX-ACCESS		read-only
		STATUS			current
		DESCRIPTION		"Description"
		::=  {  nptPTP1588PortEntry  27  }

    nptPTP1588PortLostSignalPkts	OBJECT-TYPE	
		SYNTAX			Counter64
		MAX-ACCESS		read-only
		STATUS			current
		DESCRIPTION		"Description"
		::=  {  nptPTP1588PortEntry  28  }

    nptPTP1588PortTxManagementPkts	OBJECT-TYPE	
		SYNTAX			Counter64
		MAX-ACCESS		read-only
		STATUS			current
		DESCRIPTION		"Description"
		::=  {  nptPTP1588PortEntry  29  }

    nptPTP1588PortRxManagementPkts	OBJECT-TYPE	
		SYNTAX			Counter64
		MAX-ACCESS		read-only
		STATUS			current
		DESCRIPTION		"Description"
		::=  {  nptPTP1588PortEntry  30  }

    nptPTP1588PortDroppedManagementPkts	OBJECT-TYPE	
		SYNTAX			Counter64
		MAX-ACCESS		read-only
		STATUS			current
		DESCRIPTION		"Description"
		::=  {  nptPTP1588PortEntry  31  }

    nptPTP1588PortLostManagementPkts	OBJECT-TYPE	
		SYNTAX			Counter64
		MAX-ACCESS		read-only
		STATUS			current
		DESCRIPTION		"Description"
		::=  {  nptPTP1588PortEntry  32  }

	nptERPSTable	OBJECT-TYPE
		SYNTAX		SEQUENCE  OF  NptERPSEntry
		MAX-ACCESS	not-accessible
		STATUS		current
		DESCRIPTION	"Description"
		::=  { nptERPS  1 }

	nptERPSEntry	OBJECT-TYPE
		SYNTAX		NptERPSEntry
		MAX-ACCESS	not-accessible
		STATUS		current
		DESCRIPTION	"Row Description"
		INDEX		{  nptERPSIndex  }
		::=  { nptERPSTable 1 }

	NptERPSEntry  ::=  SEQUENCE {
	    nptERPSIndex  Integer32,
        nptERPSSwitchingInstanceName  DisplayString,
        nptERPSDisContinuityTime  DisplayString,
        nptERPSElapsed DisplayString,
        nptERPSRingName DisplayString,
		nptERPSTxRAPSTx Counter64,
		nptERPSTxRAPSRx Counter64,
		nptERPSTxRAPSRxInvalid Counter64
		}


	nptERPSIndex	OBJECT-TYPE	
		SYNTAX			Integer32  ( -2147483648 .. 2147483647  ) 
		MAX-ACCESS		read-only
		STATUS			current
		DESCRIPTION		"Column Description"
		::=  {  nptERPSEntry  1  }

    nptERPSSwitchingInstanceName	OBJECT-TYPE	
		SYNTAX			DisplayString 
		MAX-ACCESS		read-only
		STATUS			current
		DESCRIPTION		"Switching Instance Name"
		::=  {  nptERPSEntry  2  }

    nptERPSDisContinuityTime	OBJECT-TYPE	
		SYNTAX			DisplayString 
		MAX-ACCESS		read-only
		STATUS			current
		DESCRIPTION		"Discontinuity Time"
		::=  {  nptERPSEntry  3  }

    nptERPSElapsed	OBJECT-TYPE	
		SYNTAX			DisplayString 
		MAX-ACCESS		read-only
		STATUS			current
		DESCRIPTION		"dd:hh:mm:ss"
		::=  {  nptERPSEntry  4  }

    nptERPSRingName	OBJECT-TYPE	
		SYNTAX			DisplayString 
		MAX-ACCESS		read-only
		STATUS			current
		DESCRIPTION		"Ring Name"
		::=  {  nptERPSEntry  5  }

    nptERPSTxRAPSTx	OBJECT-TYPE	
		SYNTAX			Counter64
		MAX-ACCESS		read-only
		STATUS			current
		DESCRIPTION		"Number of R-APS messages transmitted"
		::=  {  nptERPSEntry  6  }

    nptERPSTxRAPSRx	OBJECT-TYPE	
		SYNTAX			Counter64
		MAX-ACCESS		read-only
		STATUS			current
		DESCRIPTION		"Number of R-APS messages received."
		::=  {  nptERPSEntry  7  }

    nptERPSTxRAPSRxInvalid	OBJECT-TYPE	
		SYNTAX			Counter64
		MAX-ACCESS		read-only
		STATUS			current
		DESCRIPTION		"Number of invalid R-APS messages received"
		::=  {  nptERPSEntry  8  }
		
	nptIGMPInterfaceTable	OBJECT-TYPE
		SYNTAX		SEQUENCE  OF  NptIGMPInterfaceEntry
		MAX-ACCESS	not-accessible
		STATUS		current
		DESCRIPTION	"Description"
		::=  { nptIGMPInterface  1 }

	nptIGMPInterfaceEntry	OBJECT-TYPE
		SYNTAX		NptIGMPInterfaceEntry
		MAX-ACCESS	not-accessible
		STATUS		current
		DESCRIPTION	"Row Description"
		INDEX		{  nptIGMPInterfaceIndex  }
		::=  { nptIGMPInterfaceTable 1 }

	NptIGMPInterfaceEntry  ::=  SEQUENCE {
	    nptIGMPInterfaceIndex  Integer32,
        nptIGMPInterfaceInstanceName  DisplayString,
        nptIGMPInterfaceInterfaceName  DisplayString,
        nptIGMPInterfaceDisContinuityTime  Integer32,
        nptIGMPInterfaceElapsed DisplayString,
		nptIGMPInterfaceWrongVersionQueriesCount Counter64,
		nptIGMPInterfaceJoinsCount Counter64,
		nptIGMPInterfaceFailedJoinsCount Counter64,
		nptIGMPInterfaceSentGeneralQueriesCount Counter64,
		nptIGMPInterfaceSentSpecificQueriesCount Counter64,
		nptIGMPInterfaceTotalReceivedMessages Counter64,
		nptIGMPInterfaceIGMPv2ReceivedMessages Counter64,
		nptIGMPInterfaceIGMPv3ReceivedMessages Counter64,
		nptIGMPInterfaceInvalidReceivedMessages Counter64,
		nptIGMPInterfaceDroppedIGMPv1Messages Counter64,
		nptIGMPInterfaceCurrentgroups Counter64
		}


	nptIGMPInterfaceIndex	OBJECT-TYPE	
		SYNTAX			Integer32  ( -2147483648 .. 2147483647  ) 
		MAX-ACCESS		read-only
		STATUS			current
		DESCRIPTION		"Column Description"
		::=  {  nptIGMPInterfaceEntry  1  }

    nptIGMPInterfaceInstanceName	OBJECT-TYPE	
		SYNTAX			DisplayString 
		MAX-ACCESS		read-only
		STATUS			current
		DESCRIPTION		"Instance Name"
		::=  {  nptIGMPInterfaceEntry  2  }

    nptIGMPInterfaceInterfaceName	OBJECT-TYPE	
		SYNTAX			DisplayString 
		MAX-ACCESS		read-only
		STATUS			current
		DESCRIPTION		"Interface Name"
		::=  {  nptIGMPInterfaceEntry  3  }

    nptIGMPInterfaceDisContinuityTime	OBJECT-TYPE	
		SYNTAX			Integer32 
		MAX-ACCESS		read-only
		STATUS			current
		DESCRIPTION		"Discontinuity Time"
		::=  {  nptIGMPInterfaceEntry  4  }

    nptIGMPInterfaceElapsed	OBJECT-TYPE	
		SYNTAX			DisplayString 
		MAX-ACCESS		read-only
		STATUS			current
		DESCRIPTION		"dd:hh:mm:ss"
		::=  {  nptIGMPInterfaceEntry  5  }

    nptIGMPInterfaceWrongVersionQueriesCount	OBJECT-TYPE	
		SYNTAX			Counter64 
		MAX-ACCESS		read-only
		STATUS			current
		DESCRIPTION		"description"
		::=  {  nptIGMPInterfaceEntry  6  }

    nptIGMPInterfaceJoinsCount	OBJECT-TYPE	
		SYNTAX			Counter64
		MAX-ACCESS		read-only
		STATUS			current
		DESCRIPTION		"description"
		::=  {  nptIGMPInterfaceEntry  7  }

    nptIGMPInterfaceFailedJoinsCount	OBJECT-TYPE	
		SYNTAX			Counter64
		MAX-ACCESS		read-only
		STATUS			current
		DESCRIPTION		"description"
		::=  {  nptIGMPInterfaceEntry  8  }

    nptIGMPInterfaceSentGeneralQueriesCount	OBJECT-TYPE	
		SYNTAX			Counter64
		MAX-ACCESS		read-only
		STATUS			current
		DESCRIPTION		"description"
		::=  {  nptIGMPInterfaceEntry  9  }

    nptIGMPInterfaceSentSpecificQueriesCount	OBJECT-TYPE	
		SYNTAX			Counter64
		MAX-ACCESS		read-only
		STATUS			current
		DESCRIPTION		"description"
		::=  {  nptIGMPInterfaceEntry  10  }

    nptIGMPInterfaceTotalReceivedMessages	OBJECT-TYPE	
		SYNTAX			Counter64
		MAX-ACCESS		read-only
		STATUS			current
		DESCRIPTION		"description"
		::=  {  nptIGMPInterfaceEntry  11  }

    nptIGMPInterfaceIGMPv2ReceivedMessages	OBJECT-TYPE	
		SYNTAX			Counter64
		MAX-ACCESS		read-only
		STATUS			current
		DESCRIPTION		"description"
		::=  {  nptIGMPInterfaceEntry  12  }

    nptIGMPInterfaceIGMPv3ReceivedMessages	OBJECT-TYPE	
		SYNTAX			Counter64
		MAX-ACCESS		read-only
		STATUS			current
		DESCRIPTION		"description"
		::=  {  nptIGMPInterfaceEntry  13  }

    nptIGMPInterfaceInvalidReceivedMessages	OBJECT-TYPE	
		SYNTAX			Counter64
		MAX-ACCESS		read-only
		STATUS			current
		DESCRIPTION		"description"
		::=  {  nptIGMPInterfaceEntry  14  }

    nptIGMPInterfaceDroppedIGMPv1Messages	OBJECT-TYPE	
		SYNTAX			Counter64
		MAX-ACCESS		read-only
		STATUS			current
		DESCRIPTION		"description"
		::=  {  nptIGMPInterfaceEntry  15  }

    nptIGMPInterfaceCurrentgroups	OBJECT-TYPE	
		SYNTAX			Counter64
		MAX-ACCESS		read-only
		STATUS			current
		DESCRIPTION		"description"
		::=  {  nptIGMPInterfaceEntry  16  }
		
	nptIGMPProxyUpstreamTable	OBJECT-TYPE
		SYNTAX		SEQUENCE  OF  NptIGMPProxyUpstreamEntry
		MAX-ACCESS	not-accessible
		STATUS		current
		DESCRIPTION	"Description"
		::=  { nptIGMPProxyUpstream  1 }

	nptIGMPProxyUpstreamEntry	OBJECT-TYPE
		SYNTAX		NptIGMPProxyUpstreamEntry
		MAX-ACCESS	not-accessible
		STATUS		current
		DESCRIPTION	"Row Description"
		INDEX		{  nptIGMPProxyUpstreamIndex  }
		::=  { nptIGMPProxyUpstreamTable 1 }

	NptIGMPProxyUpstreamEntry  ::=  SEQUENCE {
	    nptIGMPProxyUpstreamIndex  Integer32,
        nptIGMPProxyUpstreamInstanceName  DisplayString,
        nptIGMPProxyUpstreamInterfacePW  DisplayString,
        nptIGMPProxyUpstreamDisContinuityTime  Integer32,
        nptIGMPProxyUpstreamElapsed DisplayString,
		nptIGMPProxyUpstreamFailedJoinsCount Counter64,
		nptIGMPProxyUpstreamSentReports Counter64,
		nptIGMPProxyUpstreamTotalReceivedMessages Counter64,
		nptIGMPProxyUpstreamIGMPv1ReceivedMessages Counter64,
		nptIGMPProxyUpstreamIGMPv2ReceivedMessages Counter64,
		nptIGMPProxyUpstreamIGMPv3ReceivedMessages Counter64,
		nptIGMPProxyUpstreamInvalidReceivedMessages Counter64,
		nptIGMPProxyUpstreamCurrentgroups Counter64
		}


	nptIGMPProxyUpstreamIndex	OBJECT-TYPE	
		SYNTAX			Integer32  ( -2147483648 .. 2147483647  ) 
		MAX-ACCESS		read-only
		STATUS			current
		DESCRIPTION		"Column Description"
		::=  {  nptIGMPProxyUpstreamEntry  1  }

    nptIGMPProxyUpstreamInstanceName	OBJECT-TYPE	
		SYNTAX			DisplayString 
		MAX-ACCESS		read-only
		STATUS			current
		DESCRIPTION		"Instance Name"
		::=  {  nptIGMPProxyUpstreamEntry  2  }

    nptIGMPProxyUpstreamInterfacePW	OBJECT-TYPE	
		SYNTAX			DisplayString 
		MAX-ACCESS		read-only
		STATUS			current
		DESCRIPTION		"Interface | PW"
		::=  {  nptIGMPProxyUpstreamEntry  3  }

    nptIGMPProxyUpstreamDisContinuityTime	OBJECT-TYPE	
		SYNTAX			Integer32 
		MAX-ACCESS		read-only
		STATUS			current
		DESCRIPTION		"Discontinuity Time"
		::=  {  nptIGMPProxyUpstreamEntry  4  }

    nptIGMPProxyUpstreamElapsed	OBJECT-TYPE	
		SYNTAX			DisplayString 
		MAX-ACCESS		read-only
		STATUS			current
		DESCRIPTION		"dd:hh:mm:ss"
		::=  {  nptIGMPProxyUpstreamEntry  5  }

    nptIGMPProxyUpstreamFailedJoinsCount	OBJECT-TYPE	
		SYNTAX			Counter64
		MAX-ACCESS		read-only
		STATUS			current
		DESCRIPTION		"description"
		::=  {  nptIGMPProxyUpstreamEntry  6  }

    nptIGMPProxyUpstreamSentReports	OBJECT-TYPE	
		SYNTAX			Counter64
		MAX-ACCESS		read-only
		STATUS			current
		DESCRIPTION		"description"
		::=  {  nptIGMPProxyUpstreamEntry  7  }

    nptIGMPProxyUpstreamTotalReceivedMessages	OBJECT-TYPE	
		SYNTAX			Counter64
		MAX-ACCESS		read-only
		STATUS			current
		DESCRIPTION		"description"
		::=  {  nptIGMPProxyUpstreamEntry  8  }

    nptIGMPProxyUpstreamIGMPv1ReceivedMessages	OBJECT-TYPE	
		SYNTAX			Counter64
		MAX-ACCESS		read-only
		STATUS			current
		DESCRIPTION		"description"
		::=  {  nptIGMPProxyUpstreamEntry  9  }

    nptIGMPProxyUpstreamIGMPv2ReceivedMessages	OBJECT-TYPE	
		SYNTAX			Counter64
		MAX-ACCESS		read-only
		STATUS			current
		DESCRIPTION		"description"
		::=  {  nptIGMPProxyUpstreamEntry  10  }

    nptIGMPProxyUpstreamIGMPv3ReceivedMessages	OBJECT-TYPE	
		SYNTAX			Counter64
		MAX-ACCESS		read-only
		STATUS			current
		DESCRIPTION		"description"
		::=  {  nptIGMPProxyUpstreamEntry  11  }

    nptIGMPProxyUpstreamInvalidReceivedMessages	OBJECT-TYPE	
		SYNTAX			Counter64
		MAX-ACCESS		read-only
		STATUS			current
		DESCRIPTION		"description"
		::=  {  nptIGMPProxyUpstreamEntry  12  }

    nptIGMPProxyUpstreamCurrentgroups	OBJECT-TYPE	
		SYNTAX			Counter64
		MAX-ACCESS		read-only
		STATUS			current
		DESCRIPTION		"description"
		::=  {  nptIGMPProxyUpstreamEntry  13  }
		
	nptIGMPProxyDownstreamTable	OBJECT-TYPE
		SYNTAX		SEQUENCE  OF  NptIGMPProxyDownstreamEntry
		MAX-ACCESS	not-accessible
		STATUS		current
		DESCRIPTION	"Description"
		::=  { nptIGMPProxyDownstream  1 }

	nptIGMPProxyDownstreamEntry	OBJECT-TYPE
		SYNTAX		NptIGMPProxyDownstreamEntry
		MAX-ACCESS	not-accessible
		STATUS		current
		DESCRIPTION	"Row Description"
		INDEX		{  nptIGMPProxyDownstreamIndex  }
		::=  { nptIGMPProxyDownstreamTable 1 }

	NptIGMPProxyDownstreamEntry  ::=  SEQUENCE {
	    nptIGMPProxyDownstreamIndex  Integer32,
        nptIGMPProxyDownstreamInstanceName  DisplayString,
        nptIGMPProxyDownstreamInterfacePW  DisplayString,
        nptIGMPProxyDownstreamDisContinuityTime  Integer32,
        nptIGMPProxyDownstreamElapsed DisplayString,
		nptIGMPProxyDownstreamWrongVersionQueriesCount Counter64,
		nptIGMPProxyDownstreamJoinsCount Counter64,
		nptIGMPProxyDownstreamFailedJoinsCount Counter64,
		nptIGMPProxyDownstreamSentGeneralQueriesCount Counter64,
		nptIGMPProxyDownstreamSentSpecificQueriesCount Counter64,
		nptIGMPProxyDownstreamTotalReceivedMessages Counter64,
		nptIGMPProxyDownstreamIGMPv2ReceivedMessages Counter64,
		nptIGMPProxyDownstreamIGMPv3ReceivedMessages Counter64,
		nptIGMPProxyDownstreamInvalidReceivedMessages Counter64,
		nptIGMPProxyDownstreamDroppedIGMPv1Messages Counter64,
		nptIGMPProxyDownstreamCurrentgroups Counter64
		}


	nptIGMPProxyDownstreamIndex	OBJECT-TYPE	
		SYNTAX			Integer32  ( -2147483648 .. 2147483647  ) 
		MAX-ACCESS		read-only
		STATUS			current
		DESCRIPTION		"Column Description"
		::=  {  nptIGMPProxyDownstreamEntry  1  }

    nptIGMPProxyDownstreamInstanceName	OBJECT-TYPE	
		SYNTAX			DisplayString 
		MAX-ACCESS		read-only
		STATUS			current
		DESCRIPTION		"Instance Name"
		::=  {  nptIGMPProxyDownstreamEntry  2  }

    nptIGMPProxyDownstreamInterfacePW	OBJECT-TYPE	
		SYNTAX			DisplayString 
		MAX-ACCESS		read-only
		STATUS			current
		DESCRIPTION		"Interface | PW"
		::=  {  nptIGMPProxyDownstreamEntry  3  }

    nptIGMPProxyDownstreamDisContinuityTime	OBJECT-TYPE	
		SYNTAX			Integer32 
		MAX-ACCESS		read-only
		STATUS			current
		DESCRIPTION		"Discontinuity Time"
		::=  {  nptIGMPProxyDownstreamEntry  4  }

    nptIGMPProxyDownstreamElapsed	OBJECT-TYPE	
		SYNTAX			DisplayString 
		MAX-ACCESS		read-only
		STATUS			current
		DESCRIPTION		"dd:hh:mm:ss"
		::=  {  nptIGMPProxyDownstreamEntry  5  }

    nptIGMPProxyDownstreamWrongVersionQueriesCount	OBJECT-TYPE	
		SYNTAX			Counter64 
		MAX-ACCESS		read-only
		STATUS			current
		DESCRIPTION		"description"
		::=  {  nptIGMPProxyDownstreamEntry  6  }

    nptIGMPProxyDownstreamJoinsCount	OBJECT-TYPE	
		SYNTAX			Counter64
		MAX-ACCESS		read-only
		STATUS			current
		DESCRIPTION		"description"
		::=  {  nptIGMPProxyDownstreamEntry  7  }

    nptIGMPProxyDownstreamFailedJoinsCount	OBJECT-TYPE	
		SYNTAX			Counter64
		MAX-ACCESS		read-only
		STATUS			current
		DESCRIPTION		"description"
		::=  {  nptIGMPProxyDownstreamEntry  8  }

    nptIGMPProxyDownstreamSentGeneralQueriesCount	OBJECT-TYPE	
		SYNTAX			Counter64
		MAX-ACCESS		read-only
		STATUS			current
		DESCRIPTION		"description"
		::=  {  nptIGMPProxyDownstreamEntry  9  }

    nptIGMPProxyDownstreamSentSpecificQueriesCount	OBJECT-TYPE	
		SYNTAX			Counter64
		MAX-ACCESS		read-only
		STATUS			current
		DESCRIPTION		"description"
		::=  {  nptIGMPProxyDownstreamEntry  10  }

    nptIGMPProxyDownstreamTotalReceivedMessages	OBJECT-TYPE	
		SYNTAX			Counter64
		MAX-ACCESS		read-only
		STATUS			current
		DESCRIPTION		"description"
		::=  {  nptIGMPProxyDownstreamEntry  11  }

    nptIGMPProxyDownstreamIGMPv2ReceivedMessages	OBJECT-TYPE	
		SYNTAX			Counter64
		MAX-ACCESS		read-only
		STATUS			current
		DESCRIPTION		"description"
		::=  {  nptIGMPProxyDownstreamEntry  12  }

    nptIGMPProxyDownstreamIGMPv3ReceivedMessages	OBJECT-TYPE	
		SYNTAX			Counter64
		MAX-ACCESS		read-only
		STATUS			current
		DESCRIPTION		"description"
		::=  {  nptIGMPProxyDownstreamEntry  13  }

    nptIGMPProxyDownstreamInvalidReceivedMessages	OBJECT-TYPE	
		SYNTAX			Counter64
		MAX-ACCESS		read-only
		STATUS			current
		DESCRIPTION		"description"
		::=  {  nptIGMPProxyDownstreamEntry  14  }

    nptIGMPProxyDownstreamDroppedIGMPv1Messages	OBJECT-TYPE	
		SYNTAX			Counter64
		MAX-ACCESS		read-only
		STATUS			current
		DESCRIPTION		"description"
		::=  {  nptIGMPProxyDownstreamEntry  15  }

    nptIGMPProxyDownstreamCurrentgroups	OBJECT-TYPE	
		SYNTAX			Counter64
		MAX-ACCESS		read-only
		STATUS			current
		DESCRIPTION		"description"
		::=  {  nptIGMPProxyDownstreamEntry  16  }
		
	nptDHCPRelayAgentClientTable	OBJECT-TYPE
		SYNTAX		SEQUENCE  OF  NptDHCPRelayAgentClientEntry
		MAX-ACCESS	not-accessible
		STATUS		current
		DESCRIPTION	"Description"
		::=  { nptDHCPRelayAgentClient  1 }

	nptDHCPRelayAgentClientEntry	OBJECT-TYPE
		SYNTAX		NptDHCPRelayAgentClientEntry
		MAX-ACCESS	not-accessible
		STATUS		current
		DESCRIPTION	"Row Description"
		INDEX		{  nptDHCPRelayAgentClientIndex  }
		::=  { nptDHCPRelayAgentClientTable 1 }

	NptDHCPRelayAgentClientEntry  ::=  SEQUENCE {
	    nptDHCPRelayAgentClientIndex  Integer32,
        nptDHCPRelayAgentClientLifName  DisplayString,
        nptDHCPRelayAgentClientDisContinuityTime  Integer32,
        nptDHCPRelayAgentClientInstanceElapsed DisplayString,
		nptDHCPRelayAgentClientTotalRcv Counter64,
		nptDHCPRelayAgentClientTotalSnt Counter64,
		nptDHCPRelayAgentClientDiscardRcv Counter64,
		nptDHCPRelayAgentClientUnicastSnt Counter64,
		nptDHCPRelayAgentClientBroadcastSnt Counter64,
		nptDHCPRelayAgentClientDiscoverRcv Counter64,
		nptDHCPRelayAgentClientOfferSnt Counter64,
		nptDHCPRelayAgentClientRequestRcv Counter64,
		nptDHCPRelayAgentClientDeclineRcv Counter64,
		nptDHCPRelayAgentClientAckSnt Counter64,
		nptDHCPRelayAgentClientNakSnt Counter64,
		nptDHCPRelayAgentClientReleaseRcv Counter64,
		nptDHCPRelayAgentClientInformRcv Counter64,
		nptDHCPRelayAgentDiscardFromUnknownServers Counter64
		}


	nptDHCPRelayAgentClientIndex	OBJECT-TYPE	
		SYNTAX			Integer32  ( -2147483648 .. 2147483647  ) 
		MAX-ACCESS		read-only
		STATUS			current
		DESCRIPTION		"Column Description"
		::=  {  nptDHCPRelayAgentClientEntry  1  }

    nptDHCPRelayAgentClientLifName	OBJECT-TYPE	
		SYNTAX			DisplayString 
		MAX-ACCESS		read-only
		STATUS			current
		DESCRIPTION		"Lif Name"
		::=  {  nptDHCPRelayAgentClientEntry  2  }

    nptDHCPRelayAgentClientDisContinuityTime	OBJECT-TYPE	
		SYNTAX			Integer32
		MAX-ACCESS		read-only
		STATUS			current
		DESCRIPTION		"DisContinuity Time"
		::=  {  nptDHCPRelayAgentClientEntry  3  }

    nptDHCPRelayAgentClientInstanceElapsed	OBJECT-TYPE	
		SYNTAX			DisplayString
		MAX-ACCESS		read-only
		STATUS			current
		DESCRIPTION		"Elapsed Time"
		::=  {  nptDHCPRelayAgentClientEntry  4  }


    nptDHCPRelayAgentClientTotalRcv	OBJECT-TYPE	
		SYNTAX			Counter64
		MAX-ACCESS		read-only
		STATUS			current
		DESCRIPTION		"Description"
		::=  {  nptDHCPRelayAgentClientEntry  5  }

    nptDHCPRelayAgentClientTotalSnt	OBJECT-TYPE	
		SYNTAX			Counter64
		MAX-ACCESS		read-only
		STATUS			current
		DESCRIPTION		"Description"
		::=  {  nptDHCPRelayAgentClientEntry  6  }

    nptDHCPRelayAgentClientDiscardRcv	OBJECT-TYPE	
		SYNTAX			Counter64
		MAX-ACCESS		read-only
		STATUS			current
		DESCRIPTION		"Description"
		::=  {  nptDHCPRelayAgentClientEntry  7  }

    nptDHCPRelayAgentClientUnicastSnt	OBJECT-TYPE	
		SYNTAX			Counter64
		MAX-ACCESS		read-only
		STATUS			current
		DESCRIPTION		"Description"
		::=  {  nptDHCPRelayAgentClientEntry  8  }

    nptDHCPRelayAgentClientBroadcastSnt	OBJECT-TYPE	
		SYNTAX			Counter64
		MAX-ACCESS		read-only
		STATUS			current
		DESCRIPTION		"Description"
		::=  {  nptDHCPRelayAgentClientEntry  9  }

    nptDHCPRelayAgentClientDiscoverRcv	OBJECT-TYPE	
		SYNTAX			Counter64
		MAX-ACCESS		read-only
		STATUS			current
		DESCRIPTION		"Description"
		::=  {  nptDHCPRelayAgentClientEntry  10  }

    nptDHCPRelayAgentClientOfferSnt	OBJECT-TYPE	
		SYNTAX			Counter64
		MAX-ACCESS		read-only
		STATUS			current
		DESCRIPTION		"Description"
		::=  {  nptDHCPRelayAgentClientEntry  11  }

    nptDHCPRelayAgentClientRequestRcv	OBJECT-TYPE	
		SYNTAX			Counter64
		MAX-ACCESS		read-only
		STATUS			current
		DESCRIPTION		"Description"
		::=  {  nptDHCPRelayAgentClientEntry  12  }

    nptDHCPRelayAgentClientDeclineRcv	OBJECT-TYPE	
		SYNTAX			Counter64
		MAX-ACCESS		read-only
		STATUS			current
		DESCRIPTION		"Description"
		::=  {  nptDHCPRelayAgentClientEntry  13  }

    nptDHCPRelayAgentClientAckSnt	OBJECT-TYPE	
		SYNTAX			Counter64
		MAX-ACCESS		read-only
		STATUS			current
		DESCRIPTION		"Description"
		::=  {  nptDHCPRelayAgentClientEntry  14  }


    nptDHCPRelayAgentClientNakSnt	OBJECT-TYPE	
		SYNTAX			Counter64
		MAX-ACCESS		read-only
		STATUS			current
		DESCRIPTION		"Description"
		::=  {  nptDHCPRelayAgentClientEntry  15  }

    nptDHCPRelayAgentClientReleaseRcv	OBJECT-TYPE	
		SYNTAX			Counter64
		MAX-ACCESS		read-only
		STATUS			current
		DESCRIPTION		"Description"
		::=  {  nptDHCPRelayAgentClientEntry  16  }

    nptDHCPRelayAgentClientInformRcv	OBJECT-TYPE	
		SYNTAX			Counter64
		MAX-ACCESS		read-only
		STATUS			current
		DESCRIPTION		"Description"
		::=  {  nptDHCPRelayAgentClientEntry  17  }

    nptDHCPRelayAgentDiscardFromUnknownServers	OBJECT-TYPE	
		SYNTAX			Counter64
		MAX-ACCESS		read-only
		STATUS			current
		DESCRIPTION		"Description"
		::=  {  nptDHCPRelayAgentClientEntry  18  }
		
	nptDHCPRelayAgentServerTable	OBJECT-TYPE
		SYNTAX		SEQUENCE  OF  NptDHCPRelayAgentServerEntry
		MAX-ACCESS	not-accessible
		STATUS		current
		DESCRIPTION	"Description"
		::=  { nptDHCPRelayAgentServer  1 }

	nptDHCPRelayAgentServerEntry	OBJECT-TYPE
		SYNTAX		NptDHCPRelayAgentServerEntry
		MAX-ACCESS	not-accessible
		STATUS		current
		DESCRIPTION	"Row Description"
		INDEX		{  nptDHCPRelayAgentServerIndex  }
		::=  { nptDHCPRelayAgentServerTable 1 }

	NptDHCPRelayAgentServerEntry  ::=  SEQUENCE {
	    nptDHCPRelayAgentServerIndex  Integer32,
        nptDHCPRelayAgentServerLifName  DisplayString,
        nptDHCPRelayAgentServerAddress  DisplayString,
        nptDHCPRelayAgentServerDisContinuityTime  Integer32,
        nptDHCPRelayAgentServerInstanceElapsed DisplayString,
		nptDHCPRelayAgentServerTotalRcv Counter64,
		nptDHCPRelayAgentServerTotalSnt Counter64,
		nptDHCPRelayAgentServerDiscardRcv Counter64,
		nptDHCPRelayAgentServerDiscoverSnt Counter64,
		nptDHCPRelayAgentServerOfferRcv Counter64,
		nptDHCPRelayAgentServerRequestSnt Counter64,
		nptDHCPRelayAgentServerDeclineSnt Counter64,
		nptDHCPRelayAgentServerAckRcv Counter64,
		nptDHCPRelayAgentServerNakRcv Counter64,
		nptDHCPRelayAgentServerReleaseSnt Counter64,
		nptDHCPRelayAgentServerInformSnt Counter64
		}


	nptDHCPRelayAgentServerIndex	OBJECT-TYPE	
		SYNTAX			Integer32  ( -2147483648 .. 2147483647  ) 
		MAX-ACCESS		read-only
		STATUS			current
		DESCRIPTION		"Column Description"
		::=  {  nptDHCPRelayAgentServerEntry  1  }

    nptDHCPRelayAgentServerLifName	OBJECT-TYPE	
		SYNTAX			DisplayString 
		MAX-ACCESS		read-only
		STATUS			current
		DESCRIPTION		"Lif Name"
		::=  {  nptDHCPRelayAgentServerEntry  2  }

    nptDHCPRelayAgentServerAddress	OBJECT-TYPE	
		SYNTAX			DisplayString 
		MAX-ACCESS		read-only
		STATUS			current
		DESCRIPTION		"Address"
		::=  {  nptDHCPRelayAgentServerEntry  3  }

    nptDHCPRelayAgentServerDisContinuityTime	OBJECT-TYPE	
		SYNTAX			Integer32
		MAX-ACCESS		read-only
		STATUS			current
		DESCRIPTION		"DisContinuity Time"
		::=  {  nptDHCPRelayAgentServerEntry  4  }

    nptDHCPRelayAgentServerInstanceElapsed	OBJECT-TYPE	
		SYNTAX			DisplayString
		MAX-ACCESS		read-only
		STATUS			current
		DESCRIPTION		"Elapsed"
		::=  {  nptDHCPRelayAgentServerEntry  5  }


    nptDHCPRelayAgentServerTotalRcv	OBJECT-TYPE	
		SYNTAX			Counter64
		MAX-ACCESS		read-only
		STATUS			current
		DESCRIPTION		"Description"
		::=  {  nptDHCPRelayAgentServerEntry  6  }

    nptDHCPRelayAgentServerTotalSnt	OBJECT-TYPE	
		SYNTAX			Counter64
		MAX-ACCESS		read-only
		STATUS			current
		DESCRIPTION		"Description"
		::=  {  nptDHCPRelayAgentServerEntry  7  }

    nptDHCPRelayAgentServerDiscardRcv	OBJECT-TYPE	
		SYNTAX			Counter64
		MAX-ACCESS		read-only
		STATUS			current
		DESCRIPTION		"Description"
		::=  {  nptDHCPRelayAgentServerEntry  8  }

    nptDHCPRelayAgentServerDiscoverSnt	OBJECT-TYPE	
		SYNTAX			Counter64
		MAX-ACCESS		read-only
		STATUS			current
		DESCRIPTION		"Description"
		::=  {  nptDHCPRelayAgentServerEntry  9  }

    nptDHCPRelayAgentServerOfferRcv	OBJECT-TYPE	
		SYNTAX			Counter64
		MAX-ACCESS		read-only
		STATUS			current
		DESCRIPTION		"Description"
		::=  {  nptDHCPRelayAgentServerEntry  10  }

    nptDHCPRelayAgentServerRequestSnt	OBJECT-TYPE	
		SYNTAX			Counter64
		MAX-ACCESS		read-only
		STATUS			current
		DESCRIPTION		"Description"
		::=  {  nptDHCPRelayAgentServerEntry  11  }

    nptDHCPRelayAgentServerDeclineSnt	OBJECT-TYPE	
		SYNTAX			Counter64
		MAX-ACCESS		read-only
		STATUS			current
		DESCRIPTION		"Description"
		::=  {  nptDHCPRelayAgentServerEntry  12  }

    nptDHCPRelayAgentServerAckRcv	OBJECT-TYPE	
		SYNTAX			Counter64
		MAX-ACCESS		read-only
		STATUS			current
		DESCRIPTION		"Description"
		::=  {  nptDHCPRelayAgentServerEntry  13  }

    nptDHCPRelayAgentServerNakRcv	OBJECT-TYPE	
		SYNTAX			Counter64
		MAX-ACCESS		read-only
		STATUS			current
		DESCRIPTION		"Description"
		::=  {  nptDHCPRelayAgentServerEntry  14  }

    nptDHCPRelayAgentServerReleaseSnt	OBJECT-TYPE	
		SYNTAX			Counter64
		MAX-ACCESS		read-only
		STATUS			current
		DESCRIPTION		"Description"
		::=  {  nptDHCPRelayAgentServerEntry  15  }


    nptDHCPRelayAgentServerInformSnt	OBJECT-TYPE	
		SYNTAX			Counter64
		MAX-ACCESS		read-only
		STATUS			current
		DESCRIPTION		"Description"
		::=  {  nptDHCPRelayAgentServerEntry  16  }
		
	nptDHCPPWTable	OBJECT-TYPE
		SYNTAX		SEQUENCE  OF  NptDHCPPWEntry
		MAX-ACCESS	not-accessible
		STATUS		current
		DESCRIPTION	"Description"
		::=  { nptDHCPPW  1 }

	nptDHCPPWEntry	OBJECT-TYPE
		SYNTAX		NptDHCPPWEntry
		MAX-ACCESS	not-accessible
		STATUS		current
		DESCRIPTION	"Row Description"
		INDEX		{  nptDHCPPWIndex  }
		::=  { nptDHCPPWTable 1 }

	NptDHCPPWEntry  ::=  SEQUENCE {
	    nptDHCPPWIndex  Integer32,
        nptDHCPPWInstanceName  DisplayString,
        nptDHCPPWPeAddress  DisplayString,
        nptDHCPPWDisContinuityTime  DisplayString,
        nptDHCPPWElapsed DisplayString,
		nptDHCPPWTotal Counter64,
		nptDHCPPWBootRequest Counter64,
		nptDHCPPWBootReply Counter64,
		nptDHCPPWDecline Counter64,
		nptDHCPPWDiscover Counter64,
		nptDHCPPWInform Counter64,
		nptDHCPPWRelease Counter64,
		nptDHCPPWRequest Counter64,
		nptDHCPPWAck Counter64,
		nptDHCPPWOffer Counter64,
		nptDHCPPWNak Counter64,
		nptDHCPPWDiscarded Counter64,
		nptDHCPPWMalformed Counter64
		}


	nptDHCPPWIndex	OBJECT-TYPE	
		SYNTAX			Integer32  ( -2147483648 .. 2147483647  ) 
		MAX-ACCESS		read-only
		STATUS			current
		DESCRIPTION		"Column Description"
		::=  {  nptDHCPPWEntry  1  }

    nptDHCPPWInstanceName	OBJECT-TYPE	
		SYNTAX			DisplayString 
		MAX-ACCESS		read-only
		STATUS			current
		DESCRIPTION		"Instance Name"
		::=  {  nptDHCPPWEntry  2  }

    nptDHCPPWPeAddress	OBJECT-TYPE	
		SYNTAX			DisplayString 
		MAX-ACCESS		read-only
		STATUS			current
		DESCRIPTION		"Pe Address"
		::=  {  nptDHCPPWEntry  3  }

    nptDHCPPWDisContinuityTime	OBJECT-TYPE	
		SYNTAX			DisplayString
		MAX-ACCESS		read-only
		STATUS			current
		DESCRIPTION		"DisContinuity Time"
		::=  {  nptDHCPPWEntry  4  }

    nptDHCPPWElapsed	OBJECT-TYPE	
		SYNTAX			DisplayString
		MAX-ACCESS		read-only
		STATUS			current
		DESCRIPTION		"Elapsed"
		::=  {  nptDHCPPWEntry  5  }


    nptDHCPPWTotal	OBJECT-TYPE	
		SYNTAX			Counter64
		MAX-ACCESS		read-only
		STATUS			current
		DESCRIPTION		"Description"
		::=  {  nptDHCPPWEntry  6  }

    nptDHCPPWBootRequest	OBJECT-TYPE	
		SYNTAX			Counter64
		MAX-ACCESS		read-only
		STATUS			current
		DESCRIPTION		"Description"
		::=  {  nptDHCPPWEntry  7  }

    nptDHCPPWBootReply	OBJECT-TYPE	
		SYNTAX			Counter64
		MAX-ACCESS		read-only
		STATUS			current
		DESCRIPTION		"Description"
		::=  {  nptDHCPPWEntry  8  }

    nptDHCPPWDecline	OBJECT-TYPE	
		SYNTAX			Counter64
		MAX-ACCESS		read-only
		STATUS			current
		DESCRIPTION		"Description"
		::=  {  nptDHCPPWEntry  9  }

    nptDHCPPWDiscover	OBJECT-TYPE	
		SYNTAX			Counter64
		MAX-ACCESS		read-only
		STATUS			current
		DESCRIPTION		"Description"
		::=  {  nptDHCPPWEntry  10  }

    nptDHCPPWInform	OBJECT-TYPE	
		SYNTAX			Counter64
		MAX-ACCESS		read-only
		STATUS			current
		DESCRIPTION		"Description"
		::=  {  nptDHCPPWEntry  11  }

    nptDHCPPWRelease	OBJECT-TYPE	
		SYNTAX			Counter64
		MAX-ACCESS		read-only
		STATUS			current
		DESCRIPTION		"Description"
		::=  {  nptDHCPPWEntry  12  }

    nptDHCPPWRequest	OBJECT-TYPE	
		SYNTAX			Counter64
		MAX-ACCESS		read-only
		STATUS			current
		DESCRIPTION		"Description"
		::=  {  nptDHCPPWEntry  13  }

    nptDHCPPWAck	OBJECT-TYPE	
		SYNTAX			Counter64
		MAX-ACCESS		read-only
		STATUS			current
		DESCRIPTION		"Description"
		::=  {  nptDHCPPWEntry  14  }

    nptDHCPPWOffer	OBJECT-TYPE	
		SYNTAX			Counter64
		MAX-ACCESS		read-only
		STATUS			current
		DESCRIPTION		"Description"
		::=  {  nptDHCPPWEntry  15  }


    nptDHCPPWNak	OBJECT-TYPE	
		SYNTAX			Counter64
		MAX-ACCESS		read-only
		STATUS			current
		DESCRIPTION		"Description"
		::=  {  nptDHCPPWEntry  16  }

    nptDHCPPWDiscarded	OBJECT-TYPE	
		SYNTAX			Counter64
		MAX-ACCESS		read-only
		STATUS			current
		DESCRIPTION		"Description"
		::=  {  nptDHCPPWEntry  17  }


    nptDHCPPWMalformed	OBJECT-TYPE	
		SYNTAX			Counter64
		MAX-ACCESS		read-only
		STATUS			current
		DESCRIPTION		"Description"
		::=  {  nptDHCPPWEntry  18  }
		
	nptDHCPInterfaceTable	OBJECT-TYPE
		SYNTAX		SEQUENCE  OF  NptDHCPInterfaceEntry
		MAX-ACCESS	not-accessible
		STATUS		current
		DESCRIPTION	"Description"
		::=  { nptDHCPInterface  1 }

	nptDHCPInterfaceEntry	OBJECT-TYPE
		SYNTAX		NptDHCPInterfaceEntry
		MAX-ACCESS	not-accessible
		STATUS		current
		DESCRIPTION	"Row Description"
		INDEX		{  nptDHCPInterfaceIndex  }
		::=  { nptDHCPInterfaceTable 1 }

	NptDHCPInterfaceEntry  ::=  SEQUENCE {
	    nptDHCPInterfaceIndex  Integer32,
        nptDHCPInterfaceInstanceName  DisplayString,
        nptDHCPInterfaceLifName  DisplayString,
        nptDHCPInterfaceDisContinuityTime  DisplayString,
        nptDHCPInterfaceElapsed DisplayString,
		nptDHCPInterfaceTotal Counter64,
		nptDHCPInterfaceBootRequest Counter64,
		nptDHCPInterfaceBootReply Counter64,
		nptDHCPInterfaceDecline Counter64,
		nptDHCPInterfaceDiscover Counter64,
		nptDHCPInterfaceInform Counter64,
		nptDHCPInterfaceRelease Counter64,
		nptDHCPInterfaceRequest Counter64,
		nptDHCPInterfaceAck Counter64,
		nptDHCPInterfaceOffer Counter64,
		nptDHCPInterfaceNak Counter64,
		nptDHCPInterfaceDiscarded Counter64,
		nptDHCPInterfaceMalformed Counter64
		}


	nptDHCPInterfaceIndex	OBJECT-TYPE	
		SYNTAX			Integer32  ( -2147483648 .. 2147483647  ) 
		MAX-ACCESS		read-only
		STATUS			current
		DESCRIPTION		"Column Description"
		::=  {  nptDHCPInterfaceEntry  1  }

    nptDHCPInterfaceInstanceName	OBJECT-TYPE	
		SYNTAX			DisplayString 
		MAX-ACCESS		read-only
		STATUS			current
		DESCRIPTION		"Instance Name"
		::=  {  nptDHCPInterfaceEntry  2  }

    nptDHCPInterfaceLifName	OBJECT-TYPE	
		SYNTAX			DisplayString 
		MAX-ACCESS		read-only
		STATUS			current
		DESCRIPTION		"Lif Name"
		::=  {  nptDHCPInterfaceEntry  3  }

    nptDHCPInterfaceDisContinuityTime	OBJECT-TYPE	
		SYNTAX			DisplayString
		MAX-ACCESS		read-only
		STATUS			current
		DESCRIPTION		"DisContinuity Time"
		::=  {  nptDHCPInterfaceEntry  4  }

    nptDHCPInterfaceElapsed	OBJECT-TYPE	
		SYNTAX			DisplayString
		MAX-ACCESS		read-only
		STATUS			current
		DESCRIPTION		"Elapsed"
		::=  {  nptDHCPInterfaceEntry  5  }


    nptDHCPInterfaceTotal	OBJECT-TYPE	
		SYNTAX			Counter64
		MAX-ACCESS		read-only
		STATUS			current
		DESCRIPTION		"Description"
		::=  {  nptDHCPInterfaceEntry  6  }

    nptDHCPInterfaceBootRequest	OBJECT-TYPE	
		SYNTAX			Counter64
		MAX-ACCESS		read-only
		STATUS			current
		DESCRIPTION		"Description"
		::=  {  nptDHCPInterfaceEntry  7  }

    nptDHCPInterfaceBootReply	OBJECT-TYPE	
		SYNTAX			Counter64
		MAX-ACCESS		read-only
		STATUS			current
		DESCRIPTION		"Description"
		::=  {  nptDHCPInterfaceEntry  8  }

    nptDHCPInterfaceDecline	OBJECT-TYPE	
		SYNTAX			Counter64
		MAX-ACCESS		read-only
		STATUS			current
		DESCRIPTION		"Description"
		::=  {  nptDHCPInterfaceEntry  9  }

    nptDHCPInterfaceDiscover	OBJECT-TYPE	
		SYNTAX			Counter64
		MAX-ACCESS		read-only
		STATUS			current
		DESCRIPTION		"Description"
		::=  {  nptDHCPInterfaceEntry  10  }

    nptDHCPInterfaceInform	OBJECT-TYPE	
		SYNTAX			Counter64
		MAX-ACCESS		read-only
		STATUS			current
		DESCRIPTION		"Description"
		::=  {  nptDHCPInterfaceEntry  11  }

    nptDHCPInterfaceRelease	OBJECT-TYPE	
		SYNTAX			Counter64
		MAX-ACCESS		read-only
		STATUS			current
		DESCRIPTION		"Description"
		::=  {  nptDHCPInterfaceEntry  12  }

    nptDHCPInterfaceRequest	OBJECT-TYPE	
		SYNTAX			Counter64
		MAX-ACCESS		read-only
		STATUS			current
		DESCRIPTION		"Description"
		::=  {  nptDHCPInterfaceEntry  13  }

    nptDHCPInterfaceAck	OBJECT-TYPE	
		SYNTAX			Counter64
		MAX-ACCESS		read-only
		STATUS			current
		DESCRIPTION		"Description"
		::=  {  nptDHCPInterfaceEntry  14  }

    nptDHCPInterfaceOffer	OBJECT-TYPE	
		SYNTAX			Counter64
		MAX-ACCESS		read-only
		STATUS			current
		DESCRIPTION		"Description"
		::=  {  nptDHCPInterfaceEntry  15  }


    nptDHCPInterfaceNak	OBJECT-TYPE	
		SYNTAX			Counter64
		MAX-ACCESS		read-only
		STATUS			current
		DESCRIPTION		"Description"
		::=  {  nptDHCPInterfaceEntry  16  }

    nptDHCPInterfaceDiscarded	OBJECT-TYPE	
		SYNTAX			Counter64
		MAX-ACCESS		read-only
		STATUS			current
		DESCRIPTION		"Description"
		::=  {  nptDHCPInterfaceEntry  17  }


    nptDHCPInterfaceMalformed	OBJECT-TYPE	
		SYNTAX			Counter64
		MAX-ACCESS		read-only
		STATUS			current
		DESCRIPTION		"Description"
		::=  {  nptDHCPInterfaceEntry  18  }
		
	nptVRRPTable	OBJECT-TYPE
		SYNTAX		SEQUENCE  OF  NptVRRPEntry
		MAX-ACCESS	not-accessible
		STATUS		current
		DESCRIPTION	"Description"
		::=  { nptVRRP  1 }

	nptVRRPEntry	OBJECT-TYPE
		SYNTAX		NptVRRPEntry
		MAX-ACCESS	not-accessible
		STATUS		current
		DESCRIPTION	"Row Description"
		INDEX		{  nptVRRPIndex  }
		::=  { nptVRRPTable 1 }

	NptVRRPEntry  ::=  SEQUENCE {
	    nptVRRPIndex  Integer32,
        nptVRRPIfName DisplayString,
        nptVRRPDisContinuityTime  Integer32,
		nptVRRPElapsedTime  DisplayString,
        nptVRRPGroupNumber  Integer32,
		nptVRRPMasterTransitions Counter64,
		nptVRRPAdvertisementRecv Counter64,
		nptVRRPAdvertisementSent Counter64,
		nptVRRPIntervalErrors Counter64,
		nptVRRPPriorityZeroPktsRcvd Counter64,
		nptVRRPPriorityZeroPktsSent Counter64,
		nptVRRPInvalidTypePktsRcvd Counter64,
		nptVRRPAddressListErrors Counter64,
		nptVRRPPacketLengthErrors Counter64,
		nptVRRPVersionErrors Counter64
		}


	nptVRRPIndex	OBJECT-TYPE	
		SYNTAX			Integer32  ( -2147483648 .. 2147483647  ) 
		MAX-ACCESS		read-only
		STATUS			current
		DESCRIPTION		"Column Description"
		::=  {  nptVRRPEntry  1  }

    nptVRRPIfName	OBJECT-TYPE	
		SYNTAX			DisplayString 
		MAX-ACCESS		read-only
		STATUS			current
		DESCRIPTION		"if name"
		::=  {  nptVRRPEntry  2  }


    nptVRRPDisContinuityTime	OBJECT-TYPE	
		SYNTAX			Integer32 
		MAX-ACCESS		read-only
		STATUS			current
		DESCRIPTION		"Discontinuity Time"
		::=  {  nptVRRPEntry  3  }
		
	nptVRRPElapsedTime	OBJECT-TYPE	
		SYNTAX			DisplayString 
		MAX-ACCESS		read-only
		STATUS			current
		DESCRIPTION		"Elapsed Time"
		::=  {  nptVRRPEntry  4  }

    nptVRRPGroupNumber	OBJECT-TYPE	
		SYNTAX			Integer32 
		MAX-ACCESS		read-only
		STATUS			current
		DESCRIPTION		"group number"
		::=  {  nptVRRPEntry  5  }

    nptVRRPMasterTransitions	OBJECT-TYPE	
		SYNTAX			Counter64
		MAX-ACCESS		read-only
		STATUS			current
		DESCRIPTION		"description"
		::=  {  nptVRRPEntry  6  }

    nptVRRPAdvertisementRecv	OBJECT-TYPE	
		SYNTAX			Counter64
		MAX-ACCESS		read-only
		STATUS			current
		DESCRIPTION		"description"
		::=  {  nptVRRPEntry  7  }

    nptVRRPAdvertisementSent	OBJECT-TYPE	
		SYNTAX			Counter64
		MAX-ACCESS		read-only
		STATUS			current
		DESCRIPTION		"description"
		::=  {  nptVRRPEntry  8  }

    nptVRRPIntervalErrors	OBJECT-TYPE	
		SYNTAX			Counter64
		MAX-ACCESS		read-only
		STATUS			current
		DESCRIPTION		"description"
		::=  {  nptVRRPEntry  9  }

    nptVRRPPriorityZeroPktsRcvd	OBJECT-TYPE	
		SYNTAX			Counter64
		MAX-ACCESS		read-only
		STATUS			current
		DESCRIPTION		"description"
		::=  {  nptVRRPEntry  10  }

    nptVRRPPriorityZeroPktsSent	OBJECT-TYPE	
		SYNTAX			Counter64
		MAX-ACCESS		read-only
		STATUS			current
		DESCRIPTION		"description"
		::=  {  nptVRRPEntry  11  }

    nptVRRPInvalidTypePktsRcvd	OBJECT-TYPE	
		SYNTAX			Counter64
		MAX-ACCESS		read-only
		STATUS			current
		DESCRIPTION		"description"
		::=  {  nptVRRPEntry  12  }

    nptVRRPAddressListErrors	OBJECT-TYPE	
		SYNTAX			Counter64
		MAX-ACCESS		read-only
		STATUS			current
		DESCRIPTION		"description"
		::=  {  nptVRRPEntry  13  }

    nptVRRPPacketLengthErrors	OBJECT-TYPE	
		SYNTAX			Counter64
		MAX-ACCESS		read-only
		STATUS			current
		DESCRIPTION		"description"
		::=  {  nptVRRPEntry  14  }

    nptVRRPVersionErrors	OBJECT-TYPE	
		SYNTAX			Counter64
		MAX-ACCESS		read-only
		STATUS			current
		DESCRIPTION		"description"
		::=  {  nptVRRPEntry  15  }
		
	nptDAIPWTable	OBJECT-TYPE
		SYNTAX		SEQUENCE  OF  NptDAIPWEntry
		MAX-ACCESS	not-accessible
		STATUS		current
		DESCRIPTION	"Description"
		::=  { nptDAIPW  1 }

	nptDAIPWEntry	OBJECT-TYPE
		SYNTAX		NptDAIPWEntry
		MAX-ACCESS	not-accessible
		STATUS		current
		DESCRIPTION	"Row Description"
		INDEX		{  nptDAIPWIndex  }
		::=  { nptDAIPWTable 1 }

	NptDAIPWEntry  ::=  SEQUENCE {
	    nptDAIPWIndex  Integer32,
        nptDAIPWInstanceName  DisplayString,
        nptDAIPWPeAddress  DisplayString,
        nptDAIPWDisContinuityTime  DisplayString,
        nptDAIPWInstanceElapsed DisplayString,
		nptDAIPWTotalRecved Counter64,
		nptDAIPWUntrustedReceived Counter64,
		nptDAIPWFilterBypassed Counter64,
		nptDAIPWPassedPackets Counter64,
		nptDAIPWFailedPackets Counter64,
		nptDAIPWMalformedPackets Counter64
		}


	nptDAIPWIndex	OBJECT-TYPE	
		SYNTAX			Integer32  ( -2147483648 .. 2147483647  ) 
		MAX-ACCESS		read-only
		STATUS			current
		DESCRIPTION		"Column Description"
		::=  {  nptDAIPWEntry  1  }

    nptDAIPWInstanceName	OBJECT-TYPE	
		SYNTAX			DisplayString 
		MAX-ACCESS		read-only
		STATUS			current
		DESCRIPTION		"Instance Name"
		::=  {  nptDAIPWEntry  2  }

    nptDAIPWPeAddress	OBJECT-TYPE	
		SYNTAX			DisplayString 
		MAX-ACCESS		read-only
		STATUS			current
		DESCRIPTION		"remote-tpe"
		::=  {  nptDAIPWEntry  3  }

    nptDAIPWDisContinuityTime	OBJECT-TYPE	
		SYNTAX			DisplayString
		MAX-ACCESS		read-only
		STATUS			current
		DESCRIPTION		"DisContinuity Time"
		::=  {  nptDAIPWEntry  4  }

    nptDAIPWInstanceElapsed	OBJECT-TYPE	
		SYNTAX			DisplayString
		MAX-ACCESS		read-only
		STATUS			current
		DESCRIPTION		"Elapsed"
		::=  {  nptDAIPWEntry  5  }


    nptDAIPWTotalRecved	OBJECT-TYPE	
		SYNTAX			Counter64
		MAX-ACCESS		read-only
		STATUS			current
		DESCRIPTION		"Description"
		::=  {  nptDAIPWEntry  6  }

    nptDAIPWUntrustedReceived	OBJECT-TYPE	
		SYNTAX			Counter64
		MAX-ACCESS		read-only
		STATUS			current
		DESCRIPTION		"Description"
		::=  {  nptDAIPWEntry  7  }

    nptDAIPWFilterBypassed	OBJECT-TYPE	
		SYNTAX			Counter64
		MAX-ACCESS		read-only
		STATUS			current
		DESCRIPTION		"Description"
		::=  {  nptDAIPWEntry  8  }

    nptDAIPWPassedPackets	OBJECT-TYPE	
		SYNTAX			Counter64
		MAX-ACCESS		read-only
		STATUS			current
		DESCRIPTION		"Description"
		::=  {  nptDAIPWEntry  9  }

    nptDAIPWFailedPackets	OBJECT-TYPE	
		SYNTAX			Counter64
		MAX-ACCESS		read-only
		STATUS			current
		DESCRIPTION		"Description"
		::=  {  nptDAIPWEntry  10  }

    nptDAIPWMalformedPackets	OBJECT-TYPE	
		SYNTAX			Counter64
		MAX-ACCESS		read-only
		STATUS			current
		DESCRIPTION		"Description"
		::=  {  nptDAIPWEntry  11  }
		
	nptDAIInterfaceTable	OBJECT-TYPE
		SYNTAX		SEQUENCE  OF  NptDAIInterfaceEntry
		MAX-ACCESS	not-accessible
		STATUS		current
		DESCRIPTION	"Description"
		::=  { nptDAIInterface  1 }

	nptDAIInterfaceEntry	OBJECT-TYPE
		SYNTAX		NptDAIInterfaceEntry
		MAX-ACCESS	not-accessible
		STATUS		current
		DESCRIPTION	"Row Description"
		INDEX		{  nptDAIInterfaceIndex  }
		::=  { nptDAIInterfaceTable 1 }

	NptDAIInterfaceEntry  ::=  SEQUENCE {
	    nptDAIInterfaceIndex  Integer32,
        nptDAIInterfaceInstanceName  DisplayString,
        nptDAIInterfaceLifName  DisplayString,
        nptDAIInterfaceDisContinuityTime  DisplayString,
        nptDAIInterfaceInstanceElapsed DisplayString,
		nptDAIInterfaceTotalRecved Counter64,
		nptDAIInterfaceUntrustedReceived Counter64,
		nptDAIInterfaceFilterBypassed Counter64,
		nptDAIInterfacePassedPackets Counter64,
		nptDAIInterfaceFailedPackets Counter64,
		nptDAIInterfaceMalformedPackets Counter64
		}


	nptDAIInterfaceIndex	OBJECT-TYPE	
		SYNTAX			Integer32  ( -2147483648 .. 2147483647  ) 
		MAX-ACCESS		read-only
		STATUS			current
		DESCRIPTION		"Column Description"
		::=  {  nptDAIInterfaceEntry  1  }

    nptDAIInterfaceInstanceName	OBJECT-TYPE	
		SYNTAX			DisplayString 
		MAX-ACCESS		read-only
		STATUS			current
		DESCRIPTION		"Instance Name"
		::=  {  nptDAIInterfaceEntry  2  }

    nptDAIInterfaceLifName	OBJECT-TYPE	
		SYNTAX			DisplayString 
		MAX-ACCESS		read-only
		STATUS			current
		DESCRIPTION		"Lif Name"
		::=  {  nptDAIInterfaceEntry  3  }

    nptDAIInterfaceDisContinuityTime	OBJECT-TYPE	
		SYNTAX			DisplayString
		MAX-ACCESS		read-only
		STATUS			current
		DESCRIPTION		"DisContinuity Time"
		::=  {  nptDAIInterfaceEntry  4  }

    nptDAIInterfaceInstanceElapsed	OBJECT-TYPE	
		SYNTAX			DisplayString
		MAX-ACCESS		read-only
		STATUS			current
		DESCRIPTION		"Elapsed"
		::=  {  nptDAIInterfaceEntry  5  }


    nptDAIInterfaceTotalRecved	OBJECT-TYPE	
		SYNTAX			Counter64
		MAX-ACCESS		read-only
		STATUS			current
		DESCRIPTION		"Description"
		::=  {  nptDAIInterfaceEntry  6  }

    nptDAIInterfaceUntrustedReceived	OBJECT-TYPE	
		SYNTAX			Counter64
		MAX-ACCESS		read-only
		STATUS			current
		DESCRIPTION		"Description"
		::=  {  nptDAIInterfaceEntry  7  }

    nptDAIInterfaceFilterBypassed	OBJECT-TYPE	
		SYNTAX			Counter64
		MAX-ACCESS		read-only
		STATUS			current
		DESCRIPTION		"Description"
		::=  {  nptDAIInterfaceEntry  8  }

    nptDAIInterfacePassedPackets	OBJECT-TYPE	
		SYNTAX			Counter64
		MAX-ACCESS		read-only
		STATUS			current
		DESCRIPTION		"Description"
		::=  {  nptDAIInterfaceEntry  9  }

    nptDAIInterfaceFailedPackets	OBJECT-TYPE	
		SYNTAX			Counter64
		MAX-ACCESS		read-only
		STATUS			current
		DESCRIPTION		"Description"
		::=  {  nptDAIInterfaceEntry  10  }

    nptDAIInterfaceMalformedPackets	OBJECT-TYPE	
		SYNTAX			Counter64
		MAX-ACCESS		read-only
		STATUS			current
		DESCRIPTION		"Description"
		::=  {  nptDAIInterfaceEntry  11  }
		
	nptPIMInstanceTable	OBJECT-TYPE
		SYNTAX		SEQUENCE  OF  NptPIMInstanceEntry
		MAX-ACCESS	not-accessible
		STATUS		current
		DESCRIPTION	"Description"
		::=  { nptPIMInstance  1 }

	nptPIMInstanceEntry	OBJECT-TYPE
		SYNTAX		NptPIMInstanceEntry
		MAX-ACCESS	not-accessible
		STATUS		current
		DESCRIPTION	"Row Description"
		INDEX		{  nptPIMInstanceIndex  }
		::=  { nptPIMInstanceTable 1 }

	NptPIMInstanceEntry  ::=  SEQUENCE {
	    nptPIMInstanceIndex  Integer32,
        nptPIMInstanceInstanceName DisplayString,
		nptPIMInstanceDiscTime  DisplayString,
		nptPIMInstanceFamily  DisplayString,
		nptPIMInstanceHelloRx Counter64,
		nptPIMInstanceHelloTx Counter64,
		nptPIMInstanceHelloRxErr Counter64,
		nptPIMInstanceRegisterRx Counter64,
		nptPIMInstanceRegisterTx Counter64,
		nptPIMInstanceRegisterRxErr Counter64,
		nptPIMInstanceRegisterStopRx Counter64,
		nptPIMInstanceRegisterStopTx Counter64,
		nptPIMInstanceRegisterStopRxErr Counter64,
		nptPIMInstanceJoinPruneRx Counter64,
		nptPIMInstanceJoinPruneTx Counter64,
		nptPIMInstanceJoinPruneRxErr Counter64,
		nptPIMInstanceBootstrapRx Counter64,
		nptPIMInstanceBootstrapTx Counter64,
		nptPIMInstanceBootstrapRxErr Counter64,
		nptPIMInstanceAssertRx Counter64,
		nptPIMInstanceAssertTx Counter64,
		nptPIMInstanceAssertRxErr Counter64,
		nptPIMInstanceCandidateRpRx Counter64,
		nptPIMInstanceCandidateRpTx Counter64,
		nptPIMInstanceCandidateRpRxErr Counter64,
		nptPIMInstanceRxHelloUnknownOpt Counter64,
		nptPIMInstanceRxUnknownNeighbor Counter64,
		nptPIMInstanceRxUnknownMsgType Counter64,
		nptPIMInstanceRxUnknownVersion Counter64,
		nptPIMInstanceRxBadChecksum Counter64,
		nptPIMInstanceRxBadLength Counter64,
		nptPIMInstanceRxIgnoredType Counter64
		}


	nptPIMInstanceIndex	OBJECT-TYPE	
		SYNTAX			Integer32  ( -2147483648 .. 2147483647  ) 
		MAX-ACCESS		read-only
		STATUS			current
		DESCRIPTION		"Column Description"
		::=  {  nptPIMInstanceEntry  1  }

    nptPIMInstanceInstanceName	OBJECT-TYPE	
		SYNTAX			DisplayString 
		MAX-ACCESS		read-only
		STATUS			current
		DESCRIPTION		"instance name"
		::=  {  nptPIMInstanceEntry  2  }
		
		
	nptPIMInstanceDiscTime	OBJECT-TYPE	
		SYNTAX			DisplayString 
		MAX-ACCESS		read-only
		STATUS			current
		DESCRIPTION		"Disc Time"
		::=  {  nptPIMInstanceEntry  3  }

	nptPIMInstanceFamily	OBJECT-TYPE	
		SYNTAX			DisplayString 
		MAX-ACCESS		read-only
		STATUS			current
		DESCRIPTION		"Family type"
		::=  {  nptPIMInstanceEntry  4  }
        
    nptPIMInstanceHelloRx	OBJECT-TYPE	
		SYNTAX			Counter64
		MAX-ACCESS		read-only
		STATUS			current
		DESCRIPTION		"description"
		::=  {  nptPIMInstanceEntry  5  }

    nptPIMInstanceHelloTx	OBJECT-TYPE	
		SYNTAX			Counter64
		MAX-ACCESS		read-only
		STATUS			current
		DESCRIPTION		"description"
		::=  {  nptPIMInstanceEntry  6  }

    nptPIMInstanceHelloRxErr	OBJECT-TYPE	
		SYNTAX			Counter64
		MAX-ACCESS		read-only
		STATUS			current
		DESCRIPTION		"description"
		::=  {  nptPIMInstanceEntry  7  }

    nptPIMInstanceRegisterRx	OBJECT-TYPE	
		SYNTAX			Counter64
		MAX-ACCESS		read-only
		STATUS			current
		DESCRIPTION		"description"
		::=  {  nptPIMInstanceEntry  8  }

    nptPIMInstanceRegisterTx	OBJECT-TYPE	
		SYNTAX			Counter64
		MAX-ACCESS		read-only
		STATUS			current
		DESCRIPTION		"description"
		::=  {  nptPIMInstanceEntry  9  }

    nptPIMInstanceRegisterRxErr	OBJECT-TYPE	
		SYNTAX			Counter64
		MAX-ACCESS		read-only
		STATUS			current
		DESCRIPTION		"description"
		::=  {  nptPIMInstanceEntry  10  }

    nptPIMInstanceRegisterStopRx	OBJECT-TYPE	
		SYNTAX			Counter64
		MAX-ACCESS		read-only
		STATUS			current
		DESCRIPTION		"description"
		::=  {  nptPIMInstanceEntry  11  }

    nptPIMInstanceRegisterStopTx	OBJECT-TYPE	
		SYNTAX			Counter64
		MAX-ACCESS		read-only
		STATUS			current
		DESCRIPTION		"description"
		::=  {  nptPIMInstanceEntry  12  }

    nptPIMInstanceRegisterStopRxErr	OBJECT-TYPE	
		SYNTAX			Counter64
		MAX-ACCESS		read-only
		STATUS			current
		DESCRIPTION		"description"
		::=  {  nptPIMInstanceEntry  13  }

    nptPIMInstanceJoinPruneRx	OBJECT-TYPE	
		SYNTAX			Counter64
		MAX-ACCESS		read-only
		STATUS			current
		DESCRIPTION		"description"
		::=  {  nptPIMInstanceEntry  14  }

    nptPIMInstanceJoinPruneTx	OBJECT-TYPE	
		SYNTAX			Counter64
		MAX-ACCESS		read-only
		STATUS			current
		DESCRIPTION		"description"
		::=  {  nptPIMInstanceEntry  15  }

    nptPIMInstanceJoinPruneRxErr	OBJECT-TYPE	
		SYNTAX			Counter64
		MAX-ACCESS		read-only
		STATUS			current
		DESCRIPTION		"description"
		::=  {  nptPIMInstanceEntry  16  }

    nptPIMInstanceBootstrapRx	OBJECT-TYPE	
		SYNTAX			Counter64
		MAX-ACCESS		read-only
		STATUS			current
		DESCRIPTION		"description"
		::=  {  nptPIMInstanceEntry  17  }

    nptPIMInstanceBootstrapTx	OBJECT-TYPE	
		SYNTAX			Counter64
		MAX-ACCESS		read-only
		STATUS			current
		DESCRIPTION		"description"
		::=  {  nptPIMInstanceEntry  18  }

    nptPIMInstanceBootstrapRxErr	OBJECT-TYPE	
		SYNTAX			Counter64
		MAX-ACCESS		read-only
		STATUS			current
		DESCRIPTION		"description"
		::=  {  nptPIMInstanceEntry  19  }

    nptPIMInstanceAssertRx	OBJECT-TYPE	
		SYNTAX			Counter64
		MAX-ACCESS		read-only
		STATUS			current
		DESCRIPTION		"description"
		::=  {  nptPIMInstanceEntry  20  }

    nptPIMInstanceAssertTx	OBJECT-TYPE	
		SYNTAX			Counter64
		MAX-ACCESS		read-only
		STATUS			current
		DESCRIPTION		"description"
		::=  {  nptPIMInstanceEntry  21  }

    nptPIMInstanceAssertRxErr	OBJECT-TYPE	
		SYNTAX			Counter64
		MAX-ACCESS		read-only
		STATUS			current
		DESCRIPTION		"description"
		::=  {  nptPIMInstanceEntry  22  }

    nptPIMInstanceCandidateRpRx	OBJECT-TYPE	
		SYNTAX			Counter64
		MAX-ACCESS		read-only
		STATUS			current
		DESCRIPTION		"description"
		::=  {  nptPIMInstanceEntry  23  }

    nptPIMInstanceCandidateRpTx	OBJECT-TYPE	
		SYNTAX			Counter64
		MAX-ACCESS		read-only
		STATUS			current
		DESCRIPTION		"description"
		::=  {  nptPIMInstanceEntry  24  }
    
    nptPIMInstanceCandidateRpRxErr	OBJECT-TYPE	
		SYNTAX			Counter64
		MAX-ACCESS		read-only
		STATUS			current
		DESCRIPTION		"description"
		::=  {  nptPIMInstanceEntry  25  }

    nptPIMInstanceRxHelloUnknownOpt	OBJECT-TYPE	
		SYNTAX			Counter64
		MAX-ACCESS		read-only
		STATUS			current
		DESCRIPTION		"description"
		::=  {  nptPIMInstanceEntry  26  }

    nptPIMInstanceRxUnknownNeighbor	OBJECT-TYPE	
		SYNTAX			Counter64
		MAX-ACCESS		read-only
		STATUS			current
		DESCRIPTION		"description"
		::=  {  nptPIMInstanceEntry  27  }
        
    nptPIMInstanceRxUnknownMsgType	OBJECT-TYPE	
		SYNTAX			Counter64
		MAX-ACCESS		read-only
		STATUS			current
		DESCRIPTION		"description"
		::=  {  nptPIMInstanceEntry  28  }

    nptPIMInstanceRxUnknownVersion	OBJECT-TYPE	
		SYNTAX			Counter64
		MAX-ACCESS		read-only
		STATUS			current
		DESCRIPTION		"description"
		::=  {  nptPIMInstanceEntry  29  }
    
    nptPIMInstanceRxBadChecksum	OBJECT-TYPE	
		SYNTAX			Counter64
		MAX-ACCESS		read-only
		STATUS			current
		DESCRIPTION		"description"
		::=  {  nptPIMInstanceEntry  30  }

    nptPIMInstanceRxBadLength	OBJECT-TYPE	
		SYNTAX			Counter64
		MAX-ACCESS		read-only
		STATUS			current
		DESCRIPTION		"description"
		::=  {  nptPIMInstanceEntry  31  }

    nptPIMInstanceRxIgnoredType	OBJECT-TYPE	
		SYNTAX			Counter64
		MAX-ACCESS		read-only
		STATUS			current
		DESCRIPTION		"description"
		::=  {  nptPIMInstanceEntry  32  }
		
        
	nptPIMLifTable	OBJECT-TYPE
		SYNTAX		SEQUENCE  OF  NptPIMLifEntry
		MAX-ACCESS	not-accessible
		STATUS		current
		DESCRIPTION	"Description"
		::=  { nptPIMLif  1 }

	nptPIMLifEntry	OBJECT-TYPE
		SYNTAX		NptPIMLifEntry
		MAX-ACCESS	not-accessible
		STATUS		current
		DESCRIPTION	"Row Description"
		INDEX		{  nptPIMLifIndex  }
		::=  { nptPIMLifTable 1 }

	NptPIMLifEntry  ::=  SEQUENCE {
	    nptPIMLifIndex  Integer32,
        nptPIMLifInstanceName DisplayString,
        nptPIMLifInterfaceName DisplayString,
		nptPIMLifDiscTime  DisplayString,
		nptPIMLifHelloRx Counter64,
		nptPIMLifHelloTx Counter64,
		nptPIMLifHelloRxErr Counter64,
		nptPIMLifRegisterRx Counter64,
		nptPIMLifRegisterTx Counter64,
		nptPIMLifRegisterRxErr Counter64,
		nptPIMLifRegisterStopRx Counter64,
		nptPIMLifRegisterStopTx Counter64,
		nptPIMLifRegisterStopRxErr Counter64,
		nptPIMLifJoinPruneRx Counter64,
		nptPIMLifJoinPruneTx Counter64,
		nptPIMLifJoinPruneRxErr Counter64,
		nptPIMLifBootstrapRx Counter64,
		nptPIMLifBootstrapTx Counter64,
		nptPIMLifBootstrapRxErr Counter64,
		nptPIMLifAssertRx Counter64,
		nptPIMLifAssertTx Counter64,
		nptPIMLifAssertRxErr Counter64,
		nptPIMLifCandidateRpRx Counter64,
		nptPIMLifCandidateRpTx Counter64,
		nptPIMLifCandidateRpRxErr Counter64,
		nptPIMLifRxHelloUnknownOpt Counter64,
		nptPIMLifRxUnknownNeighbor Counter64
		}


	nptPIMLifIndex	OBJECT-TYPE	
		SYNTAX			Integer32  ( -2147483648 .. 2147483647  ) 
		MAX-ACCESS		read-only
		STATUS			current
		DESCRIPTION		"Column Description"
		::=  {  nptPIMLifEntry  1  }

    nptPIMLifInstanceName	OBJECT-TYPE	
		SYNTAX			DisplayString 
		MAX-ACCESS		read-only
		STATUS			current
		DESCRIPTION		"instance name"
		::=  {  nptPIMLifEntry  2  }

    nptPIMLifInterfaceName	OBJECT-TYPE	
		SYNTAX			DisplayString 
		MAX-ACCESS		read-only
		STATUS			current
		DESCRIPTION		"interface name"
		::=  {  nptPIMLifEntry  3  }
		
		
	nptPIMLifDiscTime	OBJECT-TYPE	
		SYNTAX			DisplayString 
		MAX-ACCESS		read-only
		STATUS			current
		DESCRIPTION		"Elapsed Time"
		::=  {  nptPIMLifEntry  4  }

    nptPIMLifHelloRx	OBJECT-TYPE	
		SYNTAX			Counter64
		MAX-ACCESS		read-only
		STATUS			current
		DESCRIPTION		"description"
		::=  {  nptPIMLifEntry  5  }

    nptPIMLifHelloTx	OBJECT-TYPE	
		SYNTAX			Counter64
		MAX-ACCESS		read-only
		STATUS			current
		DESCRIPTION		"description"
		::=  {  nptPIMLifEntry  6  }

    nptPIMLifHelloRxErr	OBJECT-TYPE	
		SYNTAX			Counter64
		MAX-ACCESS		read-only
		STATUS			current
		DESCRIPTION		"description"
		::=  {  nptPIMLifEntry  7  }

    nptPIMLifRegisterRx	OBJECT-TYPE	
		SYNTAX			Counter64
		MAX-ACCESS		read-only
		STATUS			current
		DESCRIPTION		"description"
		::=  {  nptPIMLifEntry  8  }

    nptPIMLifRegisterTx	OBJECT-TYPE	
		SYNTAX			Counter64
		MAX-ACCESS		read-only
		STATUS			current
		DESCRIPTION		"description"
		::=  {  nptPIMLifEntry  9  }

    nptPIMLifRegisterRxErr	OBJECT-TYPE	
		SYNTAX			Counter64
		MAX-ACCESS		read-only
		STATUS			current
		DESCRIPTION		"description"
		::=  {  nptPIMLifEntry  10  }

    nptPIMLifRegisterStopRx	OBJECT-TYPE	
		SYNTAX			Counter64
		MAX-ACCESS		read-only
		STATUS			current
		DESCRIPTION		"description"
		::=  {  nptPIMLifEntry  11  }

    nptPIMLifRegisterStopTx	OBJECT-TYPE	
		SYNTAX			Counter64
		MAX-ACCESS		read-only
		STATUS			current
		DESCRIPTION		"description"
		::=  {  nptPIMLifEntry  12  }

    nptPIMLifRegisterStopRxErr	OBJECT-TYPE	
		SYNTAX			Counter64
		MAX-ACCESS		read-only
		STATUS			current
		DESCRIPTION		"description"
		::=  {  nptPIMLifEntry  13  }

    nptPIMLifJoinPruneRx	OBJECT-TYPE	
		SYNTAX			Counter64
		MAX-ACCESS		read-only
		STATUS			current
		DESCRIPTION		"description"
		::=  {  nptPIMLifEntry  14  }

    nptPIMLifJoinPruneTx	OBJECT-TYPE	
		SYNTAX			Counter64
		MAX-ACCESS		read-only
		STATUS			current
		DESCRIPTION		"description"
		::=  {  nptPIMLifEntry  15  }

    nptPIMLifJoinPruneRxErr	OBJECT-TYPE	
		SYNTAX			Counter64
		MAX-ACCESS		read-only
		STATUS			current
		DESCRIPTION		"description"
		::=  {  nptPIMLifEntry  16  }

    nptPIMLifBootstrapRx	OBJECT-TYPE	
		SYNTAX			Counter64
		MAX-ACCESS		read-only
		STATUS			current
		DESCRIPTION		"description"
		::=  {  nptPIMLifEntry  17  }

    nptPIMLifBootstrapTx	OBJECT-TYPE	
		SYNTAX			Counter64
		MAX-ACCESS		read-only
		STATUS			current
		DESCRIPTION		"description"
		::=  {  nptPIMLifEntry  18  }

    nptPIMLifBootstrapRxErr	OBJECT-TYPE	
		SYNTAX			Counter64
		MAX-ACCESS		read-only
		STATUS			current
		DESCRIPTION		"description"
		::=  {  nptPIMLifEntry  19  }

    nptPIMLifAssertRx	OBJECT-TYPE	
		SYNTAX			Counter64
		MAX-ACCESS		read-only
		STATUS			current
		DESCRIPTION		"description"
		::=  {  nptPIMLifEntry  20  }

    nptPIMLifAssertTx	OBJECT-TYPE	
		SYNTAX			Counter64
		MAX-ACCESS		read-only
		STATUS			current
		DESCRIPTION		"description"
		::=  {  nptPIMLifEntry  21  }

    nptPIMLifAssertRxErr	OBJECT-TYPE	
		SYNTAX			Counter64
		MAX-ACCESS		read-only
		STATUS			current
		DESCRIPTION		"description"
		::=  {  nptPIMLifEntry  22  }

    nptPIMLifCandidateRpRx	OBJECT-TYPE	
		SYNTAX			Counter64
		MAX-ACCESS		read-only
		STATUS			current
		DESCRIPTION		"description"
		::=  {  nptPIMLifEntry  23  }

    nptPIMLifCandidateRpTx	OBJECT-TYPE	
		SYNTAX			Counter64
		MAX-ACCESS		read-only
		STATUS			current
		DESCRIPTION		"description"
		::=  {  nptPIMLifEntry  24  }
    
    nptPIMLifCandidateRpRxErr	OBJECT-TYPE	
		SYNTAX			Counter64
		MAX-ACCESS		read-only
		STATUS			current
		DESCRIPTION		"description"
		::=  {  nptPIMLifEntry  25  }

    nptPIMLifRxHelloUnknownOpt	OBJECT-TYPE	
		SYNTAX			Counter64
		MAX-ACCESS		read-only
		STATUS			current
		DESCRIPTION		"description"
		::=  {  nptPIMLifEntry  26  }

    nptPIMLifRxUnknownNeighbor	OBJECT-TYPE	
		SYNTAX			Counter64
		MAX-ACCESS		read-only
		STATUS			current
		DESCRIPTION		"description"
		::=  {  nptPIMLifEntry  27  }
		
	nptBgpNeighborTable	OBJECT-TYPE
		SYNTAX		SEQUENCE  OF  NptBgpNeighborEntry
		MAX-ACCESS	not-accessible
		STATUS		current
		DESCRIPTION	"Description"
		::=  { nptBgpNeighbor  1 }

	nptBgpNeighborEntry	OBJECT-TYPE
		SYNTAX		NptBgpNeighborEntry
		MAX-ACCESS	not-accessible
		STATUS		current
		DESCRIPTION	"Row Description"
		INDEX		{  nptBgpNeighborIndex  }
		::=  { nptBgpNeighborTable 1 }

	NptBgpNeighborEntry  ::=  SEQUENCE {
	    nptBgpNeighborIndex  Integer32,
        nptBgpNeighborInstanceName  DisplayString,
        nptBgpNeighborPeerAddrPlusPort  DisplayString,
        nptBgpNeighborPeerAs  Integer32,
        nptBgpNeighborLocalAddrPlusPort DisplayString,
		nptBgpNeighborLocalAs Integer32,
		nptBgpNeighborContinuityTime  DisplayString,
		nptBgpNeighborElapsedTime  DisplayString,
		nptBgpNeighborReceivedUpdate Integer32,
		nptBgpNeighborReceivedNotif Integer32,
		nptBgpNeighborSentUpdate Integer32,
		nptBgpNeighborSentNotif Integer32
		}


	nptBgpNeighborIndex	OBJECT-TYPE	
		SYNTAX			Integer32  ( -2147483648 .. 2147483647  ) 
		MAX-ACCESS		read-only
		STATUS			current
		DESCRIPTION		"Column Description"
		::=  {  nptBgpNeighborEntry  1  }

    nptBgpNeighborInstanceName	OBJECT-TYPE	
		SYNTAX			DisplayString 
		MAX-ACCESS		read-only
		STATUS			current
		DESCRIPTION		"Instance Name"
		::=  {  nptBgpNeighborEntry  2  }

    nptBgpNeighborPeerAddrPlusPort	OBJECT-TYPE	
		SYNTAX			DisplayString 
		MAX-ACCESS		read-only
		STATUS			current
		DESCRIPTION		"Peer"
		::=  {  nptBgpNeighborEntry  3  }

    nptBgpNeighborPeerAs	OBJECT-TYPE	
		SYNTAX			Integer32
		MAX-ACCESS		read-only
		STATUS			current
		DESCRIPTION		"AS"
		::=  {  nptBgpNeighborEntry  4  }

    nptBgpNeighborLocalAddrPlusPort	OBJECT-TYPE	
		SYNTAX			DisplayString
		MAX-ACCESS		read-only
		STATUS			current
		DESCRIPTION		"Local"
		::=  {  nptBgpNeighborEntry  5  }


    nptBgpNeighborLocalAs	OBJECT-TYPE	
		SYNTAX			Integer32
		MAX-ACCESS		read-only
		STATUS			current
		DESCRIPTION		"AS"
		::=  {  nptBgpNeighborEntry  6  }
		
	nptBgpNeighborContinuityTime	OBJECT-TYPE	
		SYNTAX			DisplayString
		MAX-ACCESS		read-only
		STATUS			current
		DESCRIPTION		"Continuity Time"
		::=  {  nptBgpNeighborEntry  7  }

    nptBgpNeighborElapsedTime	OBJECT-TYPE	
		SYNTAX			DisplayString
		MAX-ACCESS		read-only
		STATUS			current
		DESCRIPTION		"Elapsed Time"
		::=  {  nptBgpNeighborEntry  8  }

    nptBgpNeighborReceivedUpdate	OBJECT-TYPE	
		SYNTAX			Integer32
		MAX-ACCESS		read-only
		STATUS			current
		DESCRIPTION		"Description"
		::=  {  nptBgpNeighborEntry  9  }

    nptBgpNeighborReceivedNotif	OBJECT-TYPE	
		SYNTAX			Integer32
		MAX-ACCESS		read-only
		STATUS			current
		DESCRIPTION		"Description"
		::=  {  nptBgpNeighborEntry  10  }

    nptBgpNeighborSentUpdate	OBJECT-TYPE	
		SYNTAX			Integer32
		MAX-ACCESS		read-only
		STATUS			current
		DESCRIPTION		"Description"
		::=  {  nptBgpNeighborEntry  11  }

    nptBgpNeighborSentNotif	OBJECT-TYPE	
		SYNTAX			Integer32
		MAX-ACCESS		read-only
		STATUS			current
		DESCRIPTION		"Description"
		::=  {  nptBgpNeighborEntry  12  }
		
	nptMldInterfaceTable	OBJECT-TYPE
		SYNTAX		SEQUENCE  OF  NptMldInterfaceEntry
		MAX-ACCESS	not-accessible
		STATUS		current
		DESCRIPTION	"Description"
		::=  { nptMldInterface  1 }

	nptMldInterfaceEntry	OBJECT-TYPE
		SYNTAX		NptMldInterfaceEntry
		MAX-ACCESS	not-accessible
		STATUS		current
		DESCRIPTION	"Row Description"
		INDEX		{  nptMldInterfaceIndex  }
		::=  { nptMldInterfaceTable 1 }

	NptMldInterfaceEntry  ::=  SEQUENCE {
	    nptMldInterfaceIndex  Integer32,
        nptMldInterfaceInstanceName  DisplayString,
        nptMldInterfaceInterfaceName  DisplayString,
        nptMldInterfaceDiscontinuityTime  Integer32,
        nptMldInterfaceElapsed DisplayString,
		nptMldInterfaceWrongVersionQueries Integer32,
		nptMldInterfaceJoinsCount Integer32,
		nptMldInterfaceFailedJoinsCount Integer32,
		nptMldInterfaceSentGeneralQueries Integer32,
		nptMldInterfaceSentSpecificQueries Integer32,
		nptMldInterfaceTotalReceivedMsg Integer32,
		nptMldInterfaceV1ReceivedMsg Integer32,
		nptMldInterfaceV2ReceivedMsg Integer32,
		nptMldInterfaceInvalidReceivedMsg Integer32,
		nptMldInterfaceDroppedV1Msg Integer32,
		nptMldInterfaceCurrentGroups Integer32
		}


	nptMldInterfaceIndex	OBJECT-TYPE	
		SYNTAX			Integer32  ( -2147483648 .. 2147483647  ) 
		MAX-ACCESS		read-only
		STATUS			current
		DESCRIPTION		"Column Description"
		::=  {  nptMldInterfaceEntry  1  }

    nptMldInterfaceInstanceName	OBJECT-TYPE	
		SYNTAX			DisplayString 
		MAX-ACCESS		read-only
		STATUS			current
		DESCRIPTION		"Instance Name"
		::=  {  nptMldInterfaceEntry  2  }

    nptMldInterfaceInterfaceName	OBJECT-TYPE	
		SYNTAX			DisplayString 
		MAX-ACCESS		read-only
		STATUS			current
		DESCRIPTION		"Interface Name"
		::=  {  nptMldInterfaceEntry  3  }

    nptMldInterfaceDiscontinuityTime	OBJECT-TYPE	
		SYNTAX			Integer32
		MAX-ACCESS		read-only
		STATUS			current
		DESCRIPTION		"Discontinuity Time"
		::=  {  nptMldInterfaceEntry  4  }

    nptMldInterfaceElapsed	OBJECT-TYPE	
		SYNTAX			DisplayString
		MAX-ACCESS		read-only
		STATUS			current
		DESCRIPTION		"Elapsed"
		::=  {  nptMldInterfaceEntry  5  }


    nptMldInterfaceWrongVersionQueries	OBJECT-TYPE	
		SYNTAX			Integer32
		MAX-ACCESS		read-only
		STATUS			current
		DESCRIPTION		"Description"
		::=  {  nptMldInterfaceEntry  6  }

    nptMldInterfaceJoinsCount	OBJECT-TYPE	
		SYNTAX			Integer32
		MAX-ACCESS		read-only
		STATUS			current
		DESCRIPTION		"Description"
		::=  {  nptMldInterfaceEntry  7  }

    nptMldInterfaceFailedJoinsCount	OBJECT-TYPE	
		SYNTAX			Integer32
		MAX-ACCESS		read-only
		STATUS			current
		DESCRIPTION		"Description"
		::=  {  nptMldInterfaceEntry  8  }

    nptMldInterfaceSentGeneralQueries	OBJECT-TYPE	
		SYNTAX			Integer32
		MAX-ACCESS		read-only
		STATUS			current
		DESCRIPTION		"Description"
		::=  {  nptMldInterfaceEntry  9  }

    nptMldInterfaceSentSpecificQueries	OBJECT-TYPE	
		SYNTAX			Integer32
		MAX-ACCESS		read-only
		STATUS			current
		DESCRIPTION		"Description"
		::=  {  nptMldInterfaceEntry  10  }

    nptMldInterfaceTotalReceivedMsg	OBJECT-TYPE	
		SYNTAX			Integer32
		MAX-ACCESS		read-only
		STATUS			current
		DESCRIPTION		"Description"
		::=  {  nptMldInterfaceEntry  11  }

    nptMldInterfaceV1ReceivedMsg	OBJECT-TYPE	
		SYNTAX			Integer32
		MAX-ACCESS		read-only
		STATUS			current
		DESCRIPTION		"Description"
		::=  {  nptMldInterfaceEntry  12  }

    nptMldInterfaceV2ReceivedMsg	OBJECT-TYPE	
		SYNTAX			Integer32
		MAX-ACCESS		read-only
		STATUS			current
		DESCRIPTION		"Description"
		::=  {  nptMldInterfaceEntry  13  }

    nptMldInterfaceInvalidReceivedMsg	OBJECT-TYPE	
		SYNTAX			Integer32
		MAX-ACCESS		read-only
		STATUS			current
		DESCRIPTION		"Description"
		::=  {  nptMldInterfaceEntry  14  }

    nptMldInterfaceDroppedV1Msg	OBJECT-TYPE	
		SYNTAX			Integer32
		MAX-ACCESS		read-only
		STATUS			current
		DESCRIPTION		"Description"
		::=  {  nptMldInterfaceEntry  15  }

    nptMldInterfaceCurrentGroups	OBJECT-TYPE	
		SYNTAX			Integer32
		MAX-ACCESS		read-only
		STATUS			current
		DESCRIPTION		"Description"
		::=  {  nptMldInterfaceEntry  16  }
		
	nptDhcpv6RelayAgentTable	OBJECT-TYPE
		SYNTAX		SEQUENCE  OF  NptDhcpv6RelayAgentEntry
		MAX-ACCESS	not-accessible
		STATUS		current
		DESCRIPTION	"Description"
		::=  { nptDhcpv6RelayAgent  1 }

	nptDhcpv6RelayAgentEntry	OBJECT-TYPE
		SYNTAX		NptDhcpv6RelayAgentEntry
		MAX-ACCESS	not-accessible
		STATUS		current
		DESCRIPTION	"Row Description"
		INDEX		{  nptDhcpv6RelayAgentIndex  }
		::=  { nptDhcpv6RelayAgentTable 1 }

	NptDhcpv6RelayAgentEntry  ::=  SEQUENCE {
	    nptDhcpv6RelayAgentIndex  Integer32,
        nptDhcpv6RelayAgentInstanceName  DisplayString,
        nptDhcpv6RelayAgentInterfaceName  DisplayString,
        nptDhcpv6RelayAgentDiscontinuityTime  Integer32,
        nptDhcpv6RelayAgentElapsed DisplayString,
		nptDhcpv6RelayAgentClientTotalSnt Integer32,
		nptDhcpv6RelayAgentClientTotalRcv Integer32,
		nptDhcpv6RelayAgentClientSolicitRcv Integer32,
		nptDhcpv6RelayAgentClientAdvertiseSnt Integer32,
		nptDhcpv6RelayAgentClientRequestRcv Integer32,
		nptDhcpv6RelayAgentClientConfirmRcv Integer32,
		nptDhcpv6RelayAgentClientRenewRcv Integer32,
		nptDhcpv6RelayAgentClientRebindRcv Integer32,
		nptDhcpv6RelayAgentClientReplySnt Integer32,
		nptDhcpv6RelayAgentClientReleaseRcv Integer32,
		nptDhcpv6RelayAgentClientDeclineRcv Integer32,
		nptDhcpv6RelayAgentClientReconfigureSnt Integer32,
		nptDhcpv6RelayAgentClientInfoRequestRcv Integer32,
		nptDhcpv6RelayAgentClientRelayFwdRcv Integer32,
		nptDhcpv6RelayAgentClientRelayReplySnt Integer32,
		nptDhcpv6RelayAgentClientDiscardedSnt Integer32,
		nptDhcpv6RelayAgentClientDiscardedRcv Integer32,
		nptDhcpv6RelayAgentClientDiscardedRelayReplySnt Integer32
		}


	nptDhcpv6RelayAgentIndex	OBJECT-TYPE	
		SYNTAX			Integer32  ( -2147483648 .. 2147483647  ) 
		MAX-ACCESS		read-only
		STATUS			current
		DESCRIPTION		"Column Description"
		::=  {  nptDhcpv6RelayAgentEntry  1  }

    nptDhcpv6RelayAgentInstanceName	OBJECT-TYPE	
		SYNTAX			DisplayString 
		MAX-ACCESS		read-only
		STATUS			current
		DESCRIPTION		"Instance Name"
		::=  {  nptDhcpv6RelayAgentEntry  2  }

    nptDhcpv6RelayAgentInterfaceName	OBJECT-TYPE	
		SYNTAX			DisplayString 
		MAX-ACCESS		read-only
		STATUS			current
		DESCRIPTION		"Interface Name"
		::=  {  nptDhcpv6RelayAgentEntry  3  }

    nptDhcpv6RelayAgentDiscontinuityTime	OBJECT-TYPE	
		SYNTAX			Integer32
		MAX-ACCESS		read-only
		STATUS			current
		DESCRIPTION		"Discontinuity Time"
		::=  {  nptDhcpv6RelayAgentEntry  4  }

    nptDhcpv6RelayAgentElapsed	OBJECT-TYPE	
		SYNTAX			DisplayString
		MAX-ACCESS		read-only
		STATUS			current
		DESCRIPTION		"Elapsed"
		::=  {  nptDhcpv6RelayAgentEntry  5  }


    nptDhcpv6RelayAgentClientTotalSnt	OBJECT-TYPE	
		SYNTAX			Integer32
		MAX-ACCESS		read-only
		STATUS			current
		DESCRIPTION		"Description"
		::=  {  nptDhcpv6RelayAgentEntry  6  }

    nptDhcpv6RelayAgentClientTotalRcv	OBJECT-TYPE	
		SYNTAX			Integer32
		MAX-ACCESS		read-only
		STATUS			current
		DESCRIPTION		"Description"
		::=  {  nptDhcpv6RelayAgentEntry  7  }

    nptDhcpv6RelayAgentClientSolicitRcv	OBJECT-TYPE	
		SYNTAX			Integer32
		MAX-ACCESS		read-only
		STATUS			current
		DESCRIPTION		"Description"
		::=  {  nptDhcpv6RelayAgentEntry  8  }

    nptDhcpv6RelayAgentClientAdvertiseSnt	OBJECT-TYPE	
		SYNTAX			Integer32
		MAX-ACCESS		read-only
		STATUS			current
		DESCRIPTION		"Description"
		::=  {  nptDhcpv6RelayAgentEntry  9  }

    nptDhcpv6RelayAgentClientRequestRcv	OBJECT-TYPE	
		SYNTAX			Integer32
		MAX-ACCESS		read-only
		STATUS			current
		DESCRIPTION		"Description"
		::=  {  nptDhcpv6RelayAgentEntry  10  }

    nptDhcpv6RelayAgentClientConfirmRcv	OBJECT-TYPE	
		SYNTAX			Integer32
		MAX-ACCESS		read-only
		STATUS			current
		DESCRIPTION		"Description"
		::=  {  nptDhcpv6RelayAgentEntry  11  }

    nptDhcpv6RelayAgentClientRenewRcv	OBJECT-TYPE	
		SYNTAX			Integer32
		MAX-ACCESS		read-only
		STATUS			current
		DESCRIPTION		"Description"
		::=  {  nptDhcpv6RelayAgentEntry  12  }

    nptDhcpv6RelayAgentClientRebindRcv	OBJECT-TYPE	
		SYNTAX			Integer32
		MAX-ACCESS		read-only
		STATUS			current
		DESCRIPTION		"Description"
		::=  {  nptDhcpv6RelayAgentEntry  13  }

    nptDhcpv6RelayAgentClientReplySnt	OBJECT-TYPE	
		SYNTAX			Integer32
		MAX-ACCESS		read-only
		STATUS			current
		DESCRIPTION		"Description"
		::=  {  nptDhcpv6RelayAgentEntry  14  }

    nptDhcpv6RelayAgentClientReleaseRcv	OBJECT-TYPE	
		SYNTAX			Integer32
		MAX-ACCESS		read-only
		STATUS			current
		DESCRIPTION		"Description"
		::=  {  nptDhcpv6RelayAgentEntry  15  }

    nptDhcpv6RelayAgentClientDeclineRcv	OBJECT-TYPE	
		SYNTAX			Integer32
		MAX-ACCESS		read-only
		STATUS			current
		DESCRIPTION		"Description"
		::=  {  nptDhcpv6RelayAgentEntry  16  }

    nptDhcpv6RelayAgentClientReconfigureSnt	OBJECT-TYPE	
		SYNTAX			Integer32
		MAX-ACCESS		read-only
		STATUS			current
		DESCRIPTION		"Description"
		::=  {  nptDhcpv6RelayAgentEntry  17  }

    nptDhcpv6RelayAgentClientInfoRequestRcv	OBJECT-TYPE	
		SYNTAX			Integer32
		MAX-ACCESS		read-only
		STATUS			current
		DESCRIPTION		"Description"
		::=  {  nptDhcpv6RelayAgentEntry  18  }

    nptDhcpv6RelayAgentClientRelayFwdRcv	OBJECT-TYPE	
		SYNTAX			Integer32
		MAX-ACCESS		read-only
		STATUS			current
		DESCRIPTION		"Description"
		::=  {  nptDhcpv6RelayAgentEntry  19  }

    nptDhcpv6RelayAgentClientRelayReplySnt	OBJECT-TYPE	
		SYNTAX			Integer32
		MAX-ACCESS		read-only
		STATUS			current
		DESCRIPTION		"Description"
		::=  {  nptDhcpv6RelayAgentEntry  20  }

    nptDhcpv6RelayAgentClientDiscardedSnt	OBJECT-TYPE	
		SYNTAX			Integer32
		MAX-ACCESS		read-only
		STATUS			current
		DESCRIPTION		"Description"
		::=  {  nptDhcpv6RelayAgentEntry  21  }

    nptDhcpv6RelayAgentClientDiscardedRcv	OBJECT-TYPE	
		SYNTAX			Integer32
		MAX-ACCESS		read-only
		STATUS			current
		DESCRIPTION		"Description"
		::=  {  nptDhcpv6RelayAgentEntry  22  }

    nptDhcpv6RelayAgentClientDiscardedRelayReplySnt	OBJECT-TYPE	
		SYNTAX			Integer32
		MAX-ACCESS		read-only
		STATUS			current
		DESCRIPTION		"Description"
		::=  {  nptDhcpv6RelayAgentEntry  23  }
		
	nptDhcpv6PhtRelayAgentTable	OBJECT-TYPE
		SYNTAX		SEQUENCE  OF  NptDhcpv6PhtRelayAgentEntry
		MAX-ACCESS	not-accessible
		STATUS		current
		DESCRIPTION	"Description"
		::=  { nptDhcpv6PhtRelayAgent  1 }

	nptDhcpv6PhtRelayAgentEntry	OBJECT-TYPE
		SYNTAX		NptDhcpv6PhtRelayAgentEntry
		MAX-ACCESS	not-accessible
		STATUS		current
		DESCRIPTION	"Row Description"
		INDEX		{  nptDhcpv6PhtRelayAgentIndex  }
		::=  { nptDhcpv6PhtRelayAgentTable 1 }

	NptDhcpv6PhtRelayAgentEntry  ::=  SEQUENCE {
	    nptDhcpv6PhtRelayAgentIndex  Integer32,
        nptDhcpv6PhtRelayAgentInstanceName  DisplayString,
        nptDhcpv6PhtRelayAgentInterfaceName  DisplayString,
        nptDhcpv6PhtRelayAgentDiscontinuityTime  Integer32,
        nptDhcpv6PhtRelayAgentElapsed DisplayString,
		nptDhcpv6PhtRelayAgentClientTotalSnt Integer32,
		nptDhcpv6PhtRelayAgentClientTotalRcv Integer32,
		nptDhcpv6PhtRelayAgentClientSolicitRcv Integer32,
		nptDhcpv6PhtRelayAgentClientAdvertiseSnt Integer32,
		nptDhcpv6PhtRelayAgentClientRequestRcv Integer32,
		nptDhcpv6PhtRelayAgentClientConfirmRcv Integer32,
		nptDhcpv6PhtRelayAgentClientRenewRcv Integer32,
		nptDhcpv6PhtRelayAgentClientRebindRcv Integer32,
		nptDhcpv6PhtRelayAgentClientReplySnt Integer32,
		nptDhcpv6PhtRelayAgentClientReleaseRcv Integer32,
		nptDhcpv6PhtRelayAgentClientDeclineRcv Integer32,
		nptDhcpv6PhtRelayAgentClientReconfigureSnt Integer32,
		nptDhcpv6PhtRelayAgentClientInfoRequestRcv Integer32,
		nptDhcpv6PhtRelayAgentClientRelayFwdRcv Integer32,
		nptDhcpv6PhtRelayAgentClientRelayReplySnt Integer32,
		nptDhcpv6PhtRelayAgentClientDiscardedSnt Integer32,
		nptDhcpv6PhtRelayAgentClientDiscardedRcv Integer32,
		nptDhcpv6PhtRelayAgentClientDiscardedRelayReplySnt Integer32
		}


	nptDhcpv6PhtRelayAgentIndex	OBJECT-TYPE	
		SYNTAX			Integer32  ( -2147483648 .. 2147483647  ) 
		MAX-ACCESS		read-only
		STATUS			current
		DESCRIPTION		"Column Description"
		::=  {  nptDhcpv6PhtRelayAgentEntry  1  }

    nptDhcpv6PhtRelayAgentInstanceName	OBJECT-TYPE	
		SYNTAX			DisplayString 
		MAX-ACCESS		read-only
		STATUS			current
		DESCRIPTION		"Instance Name"
		::=  {  nptDhcpv6PhtRelayAgentEntry  2  }

    nptDhcpv6PhtRelayAgentInterfaceName	OBJECT-TYPE	
		SYNTAX			DisplayString 
		MAX-ACCESS		read-only
		STATUS			current
		DESCRIPTION		"Interface Name"
		::=  {  nptDhcpv6PhtRelayAgentEntry  3  }

    nptDhcpv6PhtRelayAgentDiscontinuityTime	OBJECT-TYPE	
		SYNTAX			Integer32
		MAX-ACCESS		read-only
		STATUS			current
		DESCRIPTION		"Discontinuity Time"
		::=  {  nptDhcpv6PhtRelayAgentEntry  4  }

    nptDhcpv6PhtRelayAgentElapsed	OBJECT-TYPE	
		SYNTAX			DisplayString
		MAX-ACCESS		read-only
		STATUS			current
		DESCRIPTION		"Elapsed"
		::=  {  nptDhcpv6PhtRelayAgentEntry  5  }


    nptDhcpv6PhtRelayAgentClientTotalSnt	OBJECT-TYPE	
		SYNTAX			Integer32
		MAX-ACCESS		read-only
		STATUS			current
		DESCRIPTION		"Description"
		::=  {  nptDhcpv6PhtRelayAgentEntry  6  }

    nptDhcpv6PhtRelayAgentClientTotalRcv	OBJECT-TYPE	
		SYNTAX			Integer32
		MAX-ACCESS		read-only
		STATUS			current
		DESCRIPTION		"Description"
		::=  {  nptDhcpv6PhtRelayAgentEntry  7  }

    nptDhcpv6PhtRelayAgentClientSolicitRcv	OBJECT-TYPE	
		SYNTAX			Integer32
		MAX-ACCESS		read-only
		STATUS			current
		DESCRIPTION		"Description"
		::=  {  nptDhcpv6PhtRelayAgentEntry  8  }

    nptDhcpv6PhtRelayAgentClientAdvertiseSnt	OBJECT-TYPE	
		SYNTAX			Integer32
		MAX-ACCESS		read-only
		STATUS			current
		DESCRIPTION		"Description"
		::=  {  nptDhcpv6PhtRelayAgentEntry  9  }

    nptDhcpv6PhtRelayAgentClientRequestRcv	OBJECT-TYPE	
		SYNTAX			Integer32
		MAX-ACCESS		read-only
		STATUS			current
		DESCRIPTION		"Description"
		::=  {  nptDhcpv6PhtRelayAgentEntry  10  }

    nptDhcpv6PhtRelayAgentClientConfirmRcv	OBJECT-TYPE	
		SYNTAX			Integer32
		MAX-ACCESS		read-only
		STATUS			current
		DESCRIPTION		"Description"
		::=  {  nptDhcpv6PhtRelayAgentEntry  11  }

    nptDhcpv6PhtRelayAgentClientRenewRcv	OBJECT-TYPE	
		SYNTAX			Integer32
		MAX-ACCESS		read-only
		STATUS			current
		DESCRIPTION		"Description"
		::=  {  nptDhcpv6PhtRelayAgentEntry  12  }

    nptDhcpv6PhtRelayAgentClientRebindRcv	OBJECT-TYPE	
		SYNTAX			Integer32
		MAX-ACCESS		read-only
		STATUS			current
		DESCRIPTION		"Description"
		::=  {  nptDhcpv6PhtRelayAgentEntry  13  }

    nptDhcpv6PhtRelayAgentClientReplySnt	OBJECT-TYPE	
		SYNTAX			Integer32
		MAX-ACCESS		read-only
		STATUS			current
		DESCRIPTION		"Description"
		::=  {  nptDhcpv6PhtRelayAgentEntry  14  }

    nptDhcpv6PhtRelayAgentClientReleaseRcv	OBJECT-TYPE	
		SYNTAX			Integer32
		MAX-ACCESS		read-only
		STATUS			current
		DESCRIPTION		"Description"
		::=  {  nptDhcpv6PhtRelayAgentEntry  15  }

    nptDhcpv6PhtRelayAgentClientDeclineRcv	OBJECT-TYPE	
		SYNTAX			Integer32
		MAX-ACCESS		read-only
		STATUS			current
		DESCRIPTION		"Description"
		::=  {  nptDhcpv6PhtRelayAgentEntry  16  }

    nptDhcpv6PhtRelayAgentClientReconfigureSnt	OBJECT-TYPE	
		SYNTAX			Integer32
		MAX-ACCESS		read-only
		STATUS			current
		DESCRIPTION		"Description"
		::=  {  nptDhcpv6PhtRelayAgentEntry  17  }

    nptDhcpv6PhtRelayAgentClientInfoRequestRcv	OBJECT-TYPE	
		SYNTAX			Integer32
		MAX-ACCESS		read-only
		STATUS			current
		DESCRIPTION		"Description"
		::=  {  nptDhcpv6PhtRelayAgentEntry  18  }

    nptDhcpv6PhtRelayAgentClientRelayFwdRcv	OBJECT-TYPE	
		SYNTAX			Integer32
		MAX-ACCESS		read-only
		STATUS			current
		DESCRIPTION		"Description"
		::=  {  nptDhcpv6PhtRelayAgentEntry  19  }

    nptDhcpv6PhtRelayAgentClientRelayReplySnt	OBJECT-TYPE	
		SYNTAX			Integer32
		MAX-ACCESS		read-only
		STATUS			current
		DESCRIPTION		"Description"
		::=  {  nptDhcpv6PhtRelayAgentEntry  20  }

    nptDhcpv6PhtRelayAgentClientDiscardedSnt	OBJECT-TYPE	
		SYNTAX			Integer32
		MAX-ACCESS		read-only
		STATUS			current
		DESCRIPTION		"Description"
		::=  {  nptDhcpv6PhtRelayAgentEntry  21  }

    nptDhcpv6PhtRelayAgentClientDiscardedRcv	OBJECT-TYPE	
		SYNTAX			Integer32
		MAX-ACCESS		read-only
		STATUS			current
		DESCRIPTION		"Description"
		::=  {  nptDhcpv6PhtRelayAgentEntry  22  }

    nptDhcpv6PhtRelayAgentClientDiscardedRelayReplySnt	OBJECT-TYPE	
		SYNTAX			Integer32
		MAX-ACCESS		read-only
		STATUS			current
		DESCRIPTION		"Description"
		::=  {  nptDhcpv6PhtRelayAgentEntry  23  }
		
	nptDhcpv6RelayAgentServerTable	OBJECT-TYPE
		SYNTAX		SEQUENCE  OF  NptDhcpv6RelayAgentServerEntry
		MAX-ACCESS	not-accessible
		STATUS		current
		DESCRIPTION	"Description"
		::=  { nptDhcpv6RelayAgentServer  1 }

	nptDhcpv6RelayAgentServerEntry	OBJECT-TYPE
		SYNTAX		NptDhcpv6RelayAgentServerEntry
		MAX-ACCESS	not-accessible
		STATUS		current
		DESCRIPTION	"Row Description"
		INDEX		{  nptDhcpv6RelayAgentServerIndex  }
		::=  { nptDhcpv6RelayAgentServerTable 1 }

	NptDhcpv6RelayAgentServerEntry  ::=  SEQUENCE {
	    nptDhcpv6RelayAgentServerIndex  Integer32,
        nptDhcpv6RelayAgentServerInstanceName  DisplayString,
        nptDhcpv6RelayAgentServerInterfaceName  DisplayString,
        nptDhcpv6RelayAgentServerSpecificAddress  DisplayString,
        nptDhcpv6RelayAgentServerDiscontinuityTime  Integer32,
        nptDhcpv6RelayAgentServerElapsed DisplayString,
		nptDhcpv6RelayAgentServerRelayFwdlSnt Integer32,
		nptDhcpv6RelayAgentServerRelayFwdlRcv Integer32,
		nptDhcpv6RelayAgentServerRelayReplylRcv Integer32,
		nptDhcpv6RelayAgentServerDiscardSnt Integer32,
		nptDhcpv6RelayAgentServerDiscardRcv Integer32
		}


	nptDhcpv6RelayAgentServerIndex	OBJECT-TYPE	
		SYNTAX			Integer32  ( -2147483648 .. 2147483647  ) 
		MAX-ACCESS		read-only
		STATUS			current
		DESCRIPTION		"Column Description"
		::=  {  nptDhcpv6RelayAgentServerEntry  1  }

    nptDhcpv6RelayAgentServerInstanceName	OBJECT-TYPE	
		SYNTAX			DisplayString 
		MAX-ACCESS		read-only
		STATUS			current
		DESCRIPTION		"Instance Name"
		::=  {  nptDhcpv6RelayAgentServerEntry  2  }

    nptDhcpv6RelayAgentServerInterfaceName	OBJECT-TYPE	
		SYNTAX			DisplayString 
		MAX-ACCESS		read-only
		STATUS			current
		DESCRIPTION		"Interface Name"
		::=  {  nptDhcpv6RelayAgentServerEntry  3  }

    nptDhcpv6RelayAgentServerSpecificAddress	OBJECT-TYPE	
		SYNTAX			DisplayString 
		MAX-ACCESS		read-only
		STATUS			current
		DESCRIPTION		"Specific Server Address"
		::=  {  nptDhcpv6RelayAgentServerEntry  4  }

    nptDhcpv6RelayAgentServerDiscontinuityTime	OBJECT-TYPE	
		SYNTAX			Integer32
		MAX-ACCESS		read-only
		STATUS			current
		DESCRIPTION		"Discontinuity Time"
		::=  {  nptDhcpv6RelayAgentServerEntry  5  }

    nptDhcpv6RelayAgentServerElapsed	OBJECT-TYPE	
		SYNTAX			DisplayString
		MAX-ACCESS		read-only
		STATUS			current
		DESCRIPTION		"Elapsed"
		::=  {  nptDhcpv6RelayAgentServerEntry  6  }


    nptDhcpv6RelayAgentServerRelayFwdlSnt	OBJECT-TYPE	
		SYNTAX			Integer32
		MAX-ACCESS		read-only
		STATUS			current
		DESCRIPTION		"Description"
		::=  {  nptDhcpv6RelayAgentServerEntry  7  }

    nptDhcpv6RelayAgentServerRelayFwdlRcv	OBJECT-TYPE	
		SYNTAX			Integer32
		MAX-ACCESS		read-only
		STATUS			current
		DESCRIPTION		"Description"
		::=  {  nptDhcpv6RelayAgentServerEntry  8  }

    nptDhcpv6RelayAgentServerRelayReplylRcv	OBJECT-TYPE	
		SYNTAX			Integer32
		MAX-ACCESS		read-only
		STATUS			current
		DESCRIPTION		"Description"
		::=  {  nptDhcpv6RelayAgentServerEntry  9  }

    nptDhcpv6RelayAgentServerDiscardSnt	OBJECT-TYPE	
		SYNTAX			Integer32
		MAX-ACCESS		read-only
		STATUS			current
		DESCRIPTION		"Description"
		::=  {  nptDhcpv6RelayAgentServerEntry  10  }

    nptDhcpv6RelayAgentServerDiscardRcv	OBJECT-TYPE	
		SYNTAX			Integer32
		MAX-ACCESS		read-only
		STATUS			current
		DESCRIPTION		"Description"
		::=  {  nptDhcpv6RelayAgentServerEntry  11  }
		
	nptOspfV3InstanceTable	OBJECT-TYPE
		SYNTAX		SEQUENCE  OF  NptOspfV3InstanceEntry
		MAX-ACCESS	not-accessible
		STATUS		current
		DESCRIPTION	"Description"
		::=  { nptOspfV3Instance  1 }

	nptOspfV3InstanceEntry	OBJECT-TYPE
		SYNTAX		NptOspfV3InstanceEntry
		MAX-ACCESS	not-accessible
		STATUS		current
		DESCRIPTION	"Row Description"
		INDEX		{  nptOspfV3InstanceIndex  }
		::=  { nptOspfV3InstanceTable 1 }

	NptOspfV3InstanceEntry  ::=  SEQUENCE {
	    nptOspfV3InstanceIndex  Integer32,
        nptOspfV3InstanceInstanceName  DisplayString,
        nptOspfV3InstanceDiscontinuityTime  Integer32,
        nptOspfV3InstanceElapsed DisplayString,
		nptOspfV3InstanceRxLengthErr Counter64,
		nptOspfV3InstanceRxResourceErr Counter64,
		nptOspfV3InstanceRxInvalidInterface Counter64,
		nptOspfV3InstanceRxInvalidVritualLink Counter64,
		nptOspfV3InstanceRxInvalidVersion Counter64,
		nptOspfV3InstanceRxBadSource Counter64,
		nptOspfV3InstanceRxBadPacket Counter64
		}


	nptOspfV3InstanceIndex	OBJECT-TYPE	
		SYNTAX			Integer32  ( -2147483648 .. 2147483647  ) 
		MAX-ACCESS		read-only
		STATUS			current
		DESCRIPTION		"Column Description"
		::=  {  nptOspfV3InstanceEntry  1  }

    nptOspfV3InstanceInstanceName	OBJECT-TYPE	
		SYNTAX			DisplayString 
		MAX-ACCESS		read-only
		STATUS			current
		DESCRIPTION		"Instance Name"
		::=  {  nptOspfV3InstanceEntry  2  }

    nptOspfV3InstanceDiscontinuityTime	OBJECT-TYPE	
		SYNTAX			Integer32
		MAX-ACCESS		read-only
		STATUS			current
		DESCRIPTION		"Discontinuity Time"
		::=  {  nptOspfV3InstanceEntry  3  }

    nptOspfV3InstanceElapsed	OBJECT-TYPE	
		SYNTAX			DisplayString
		MAX-ACCESS		read-only
		STATUS			current
		DESCRIPTION		"Elapsed"
		::=  {  nptOspfV3InstanceEntry  4  }


    nptOspfV3InstanceRxLengthErr	OBJECT-TYPE	
		SYNTAX			Counter64
		MAX-ACCESS		read-only
		STATUS			current
		DESCRIPTION		"Description"
		::=  {  nptOspfV3InstanceEntry  5  }

    nptOspfV3InstanceRxResourceErr	OBJECT-TYPE	
		SYNTAX			Counter64
		MAX-ACCESS		read-only
		STATUS			current
		DESCRIPTION		"Description"
		::=  {  nptOspfV3InstanceEntry  6  }

    nptOspfV3InstanceRxInvalidInterface	OBJECT-TYPE	
		SYNTAX			Counter64
		MAX-ACCESS		read-only
		STATUS			current
		DESCRIPTION		"Description"
		::=  {  nptOspfV3InstanceEntry  7  }

    nptOspfV3InstanceRxInvalidVritualLink	OBJECT-TYPE	
		SYNTAX			Counter64
		MAX-ACCESS		read-only
		STATUS			current
		DESCRIPTION		"Description"
		::=  {  nptOspfV3InstanceEntry  8  }

    nptOspfV3InstanceRxInvalidVersion	OBJECT-TYPE	
		SYNTAX			Counter64
		MAX-ACCESS		read-only
		STATUS			current
		DESCRIPTION		"Description"
		::=  {  nptOspfV3InstanceEntry  9  }

    nptOspfV3InstanceRxBadSource	OBJECT-TYPE	
		SYNTAX			Counter64
		MAX-ACCESS		read-only
		STATUS			current
		DESCRIPTION		"Description"
		::=  {  nptOspfV3InstanceEntry  10  }

    nptOspfV3InstanceRxBadPacket	OBJECT-TYPE	
		SYNTAX			Counter64
		MAX-ACCESS		read-only
		STATUS			current
		DESCRIPTION		"Description"
		::=  {  nptOspfV3InstanceEntry  11  }
		
	nptOspfV3InterfaceTable	OBJECT-TYPE
		SYNTAX		SEQUENCE  OF  NptOspfV3InterfaceEntry
		MAX-ACCESS	not-accessible
		STATUS		current
		DESCRIPTION	"Description"
		::=  { nptOspfV3Interface  1 }

	nptOspfV3InterfaceEntry	OBJECT-TYPE
		SYNTAX		NptOspfV3InterfaceEntry
		MAX-ACCESS	not-accessible
		STATUS		current
		DESCRIPTION	"Row Description"
		INDEX		{  nptOspfV3InterfaceIndex  }
		::=  { nptOspfV3InterfaceTable 1 }

	NptOspfV3InterfaceEntry  ::=  SEQUENCE {
	    nptOspfV3InterfaceIndex  Integer32,
        nptOspfV3InterfaceInstanceName  DisplayString,
        nptOspfV3InterfaceInterfaceName  DisplayString,
        nptOspfV3InterfaceDiscontinuityTime  Integer32,
        nptOspfV3InterfaceElapsed DisplayString,
		nptOspfV3InterfaceRxPktInvalid Counter64,
		nptOspfV3InterfaceRxByteInvalid Counter64,
		nptOspfV3InterfaceTxPktHello Counter64,
		nptOspfV3InterfaceTxByteHello Counter64,
		nptOspfV3InterfaceRxPktHello Counter64,
		nptOspfV3InterfaceRxByteHello Counter64,
		nptOspfV3InterfaceTxPktDbD Counter64,
		nptOspfV3InterfaceTxByteDbD Counter64,
		nptOspfV3InterfaceRxPktDbD Counter64,
		nptOspfV3InterfaceRxByteDbD Counter64,
		nptOspfV3InterfaceTxPktLsReq Counter64,
		nptOspfV3InterfaceTxByteLsReq Counter64,
		nptOspfV3InterfaceRxPktLsReq Counter64,
		nptOspfV3InterfaceRxByteLsReq Counter64,
		nptOspfV3InterfaceTxPktLsUpd Counter64,
		nptOspfV3InterfaceTxByteLsUpd Counter64,
		nptOspfV3InterfaceRxPktLsUpd Counter64,
		nptOspfV3InterfaceRxByteLsUpd Counter64,
		nptOspfV3InterfaceTxPktLsAck Counter64,
		nptOspfV3InterfaceTxByteLsAck Counter64,
		nptOspfV3InterfaceRxPktLsAck Counter64,
		nptOspfV3InterfaceRxByteLsAck Counter64,
		nptOspfV3InterfacePktHeadErrLength Counter64,
		nptOspfV3InterfacePktHeadErrVersion Counter64,
		nptOspfV3InterfacePktHeadErrBadSrc Counter64,
		nptOspfV3InterfacePktHeadErrAreaMismatch Counter64,
		nptOspfV3InterfaceLsaErrUpdBadLen Counter64,
		nptOspfV3InterfaceLsaErrBadType Counter64,
		nptOspfV3InterfaceLsaErrBadLen Counter64,
		nptOspfV3InterfaceLsaErrBadData Counter64,
		nptOspfV3InterfaceLsaErrBadCksum Counter64,
		nptOspfV3InterfacePktDropSelfOrig Counter64,
		nptOspfV3InterfacePktDropDuplicateID Counter64,
		nptOspfV3InterfacePktDropHelloErrors Counter64,
		nptOspfV3InterfacePkDropMtuMismatch Counter64,
		nptOspfV3InterfacePktDropNbrIgnored Counter64,
		nptOspfV3InterfacePktDropResourceErr Counter64,
		nptOspfV3InterfacePktDropIfStandby Counter64,
		nptOspfV3InterfacePktDropUnkNbmaNbr Counter64,
		nptOspfV3InterfacePktDropUnkVirtNbr Counter64,
		nptOspfV3InterfacePktDropHelloMismatch Counter64,
		nptOspfV3InterfacePktDropDeadMismatch Counter64,
		nptOspfV3InterfacePktDropOptionsMismatch Counter64,
		nptOspfV3InterfacePktDropNbrAdminDown Counter64,
		nptOspfV3InterfacePktDropPktLocalAddr Counter64,
		nptOspfV3InterfacePktDropBadPacket Counter64
		}


	nptOspfV3InterfaceIndex	OBJECT-TYPE	
		SYNTAX			Integer32  ( -2147483648 .. 2147483647  ) 
		MAX-ACCESS		read-only
		STATUS			current
		DESCRIPTION		"Column Description"
		::=  {  nptOspfV3InterfaceEntry  1  }

    nptOspfV3InterfaceInstanceName	OBJECT-TYPE	
		SYNTAX			DisplayString 
		MAX-ACCESS		read-only
		STATUS			current
		DESCRIPTION		"Instance Name"
		::=  {  nptOspfV3InterfaceEntry  2  }

    nptOspfV3InterfaceInterfaceName	OBJECT-TYPE	
		SYNTAX			DisplayString 
		MAX-ACCESS		read-only
		STATUS			current
		DESCRIPTION		"Interface Name"
		::=  {  nptOspfV3InterfaceEntry  3  }

    nptOspfV3InterfaceDiscontinuityTime	OBJECT-TYPE	
		SYNTAX			Integer32
		MAX-ACCESS		read-only
		STATUS			current
		DESCRIPTION		"Discontinuity Time"
		::=  {  nptOspfV3InterfaceEntry  4  }

    nptOspfV3InterfaceElapsed	OBJECT-TYPE	
		SYNTAX			DisplayString
		MAX-ACCESS		read-only
		STATUS			current
		DESCRIPTION		"Elapsed"
		::=  {  nptOspfV3InterfaceEntry  5  }


    nptOspfV3InterfaceRxPktInvalid	OBJECT-TYPE	
		SYNTAX			Counter64
		MAX-ACCESS		read-only
		STATUS			current
		DESCRIPTION		"Description"
		::=  {  nptOspfV3InterfaceEntry  6  }

    nptOspfV3InterfaceRxByteInvalid	OBJECT-TYPE	
		SYNTAX			Counter64
		MAX-ACCESS		read-only
		STATUS			current
		DESCRIPTION		"Description"
		::=  {  nptOspfV3InterfaceEntry  7  }

    nptOspfV3InterfaceTxPktHello	OBJECT-TYPE	
		SYNTAX			Counter64
		MAX-ACCESS		read-only
		STATUS			current
		DESCRIPTION		"Description"
		::=  {  nptOspfV3InterfaceEntry  8  }

    nptOspfV3InterfaceTxByteHello	OBJECT-TYPE	
		SYNTAX			Counter64
		MAX-ACCESS		read-only
		STATUS			current
		DESCRIPTION		"Description"
		::=  {  nptOspfV3InterfaceEntry  9  }

    nptOspfV3InterfaceRxPktHello	OBJECT-TYPE	
		SYNTAX			Counter64
		MAX-ACCESS		read-only
		STATUS			current
		DESCRIPTION		"Description"
		::=  {  nptOspfV3InterfaceEntry  10  }

    nptOspfV3InterfaceRxByteHello	OBJECT-TYPE	
		SYNTAX			Counter64
		MAX-ACCESS		read-only
		STATUS			current
		DESCRIPTION		"Description"
		::=  {  nptOspfV3InterfaceEntry  11  }

    nptOspfV3InterfaceTxPktDbD	OBJECT-TYPE	
		SYNTAX			Counter64
		MAX-ACCESS		read-only
		STATUS			current
		DESCRIPTION		"Description"
		::=  {  nptOspfV3InterfaceEntry  12  }

    nptOspfV3InterfaceTxByteDbD	OBJECT-TYPE	
		SYNTAX			Counter64
		MAX-ACCESS		read-only
		STATUS			current
		DESCRIPTION		"Description"
		::=  {  nptOspfV3InterfaceEntry  13  }

    nptOspfV3InterfaceRxPktDbD	OBJECT-TYPE	
		SYNTAX			Counter64
		MAX-ACCESS		read-only
		STATUS			current
		DESCRIPTION		"Description"
		::=  {  nptOspfV3InterfaceEntry  14  }

    nptOspfV3InterfaceRxByteDbD	OBJECT-TYPE	
		SYNTAX			Counter64
		MAX-ACCESS		read-only
		STATUS			current
		DESCRIPTION		"Description"
		::=  {  nptOspfV3InterfaceEntry  15  }

    nptOspfV3InterfaceTxPktLsReq	OBJECT-TYPE	
		SYNTAX			Counter64
		MAX-ACCESS		read-only
		STATUS			current
		DESCRIPTION		"Description"
		::=  {  nptOspfV3InterfaceEntry  16  }

    nptOspfV3InterfaceTxByteLsReq	OBJECT-TYPE	
		SYNTAX			Counter64
		MAX-ACCESS		read-only
		STATUS			current
		DESCRIPTION		"Description"
		::=  {  nptOspfV3InterfaceEntry  17  }

    nptOspfV3InterfaceRxPktLsReq	OBJECT-TYPE	
		SYNTAX			Counter64
		MAX-ACCESS		read-only
		STATUS			current
		DESCRIPTION		"Description"
		::=  {  nptOspfV3InterfaceEntry  18  }

    nptOspfV3InterfaceRxByteLsReq	OBJECT-TYPE	
		SYNTAX			Counter64
		MAX-ACCESS		read-only
		STATUS			current
		DESCRIPTION		"Description"
		::=  {  nptOspfV3InterfaceEntry  19  }

    nptOspfV3InterfaceTxPktLsUpd	OBJECT-TYPE	
		SYNTAX			Counter64
		MAX-ACCESS		read-only
		STATUS			current
		DESCRIPTION		"Description"
		::=  {  nptOspfV3InterfaceEntry  20  }

    nptOspfV3InterfaceTxByteLsUpd	OBJECT-TYPE	
		SYNTAX			Counter64
		MAX-ACCESS		read-only
		STATUS			current
		DESCRIPTION		"Description"
		::=  {  nptOspfV3InterfaceEntry  21  }

    nptOspfV3InterfaceRxPktLsUpd	OBJECT-TYPE	
		SYNTAX			Counter64
		MAX-ACCESS		read-only
		STATUS			current
		DESCRIPTION		"Description"
		::=  {  nptOspfV3InterfaceEntry  22  }

    nptOspfV3InterfaceRxByteLsUpd	OBJECT-TYPE	
		SYNTAX			Counter64
		MAX-ACCESS		read-only
		STATUS			current
		DESCRIPTION		"Description"
		::=  {  nptOspfV3InterfaceEntry  23  }

    nptOspfV3InterfaceTxPktLsAck	OBJECT-TYPE	
		SYNTAX			Counter64
		MAX-ACCESS		read-only
		STATUS			current
		DESCRIPTION		"Description"
		::=  {  nptOspfV3InterfaceEntry  24  }

    nptOspfV3InterfaceTxByteLsAck	OBJECT-TYPE	
		SYNTAX			Counter64
		MAX-ACCESS		read-only
		STATUS			current
		DESCRIPTION		"Description"
		::=  {  nptOspfV3InterfaceEntry  25  }

    nptOspfV3InterfaceRxPktLsAck	OBJECT-TYPE	
		SYNTAX			Counter64
		MAX-ACCESS		read-only
		STATUS			current
		DESCRIPTION		"Description"
		::=  {  nptOspfV3InterfaceEntry  26  }

    nptOspfV3InterfaceRxByteLsAck	OBJECT-TYPE	
		SYNTAX			Counter64
		MAX-ACCESS		read-only
		STATUS			current
		DESCRIPTION		"Description"
		::=  {  nptOspfV3InterfaceEntry  27  }

    nptOspfV3InterfacePktHeadErrLength	OBJECT-TYPE	
		SYNTAX			Counter64
		MAX-ACCESS		read-only
		STATUS			current
		DESCRIPTION		"Description"
		::=  {  nptOspfV3InterfaceEntry  28  }

    nptOspfV3InterfacePktHeadErrVersion	OBJECT-TYPE	
		SYNTAX			Counter64
		MAX-ACCESS		read-only
		STATUS			current
		DESCRIPTION		"Description"
		::=  {  nptOspfV3InterfaceEntry  29  }

    nptOspfV3InterfacePktHeadErrBadSrc	OBJECT-TYPE	
		SYNTAX			Counter64
		MAX-ACCESS		read-only
		STATUS			current
		DESCRIPTION		"Description"
		::=  {  nptOspfV3InterfaceEntry  30  }

    nptOspfV3InterfacePktHeadErrAreaMismatch	OBJECT-TYPE	
		SYNTAX			Counter64
		MAX-ACCESS		read-only
		STATUS			current
		DESCRIPTION		"Description"
		::=  {  nptOspfV3InterfaceEntry  31  }

    nptOspfV3InterfaceLsaErrUpdBadLen	OBJECT-TYPE	
		SYNTAX			Counter64
		MAX-ACCESS		read-only
		STATUS			current
		DESCRIPTION		"Description"
		::=  {  nptOspfV3InterfaceEntry  32  }

    nptOspfV3InterfaceLsaErrBadType	OBJECT-TYPE	
		SYNTAX			Counter64
		MAX-ACCESS		read-only
		STATUS			current
		DESCRIPTION		"Description"
		::=  {  nptOspfV3InterfaceEntry  33  }

    nptOspfV3InterfaceLsaErrBadLen	OBJECT-TYPE	
		SYNTAX			Counter64
		MAX-ACCESS		read-only
		STATUS			current
		DESCRIPTION		"Description"
		::=  {  nptOspfV3InterfaceEntry  34  }

    nptOspfV3InterfaceLsaErrBadData	OBJECT-TYPE	
		SYNTAX			Counter64
		MAX-ACCESS		read-only
		STATUS			current
		DESCRIPTION		"Description"
		::=  {  nptOspfV3InterfaceEntry  35  }

    nptOspfV3InterfaceLsaErrBadCksum	OBJECT-TYPE	
		SYNTAX			Counter64
		MAX-ACCESS		read-only
		STATUS			current
		DESCRIPTION		"Description"
		::=  {  nptOspfV3InterfaceEntry  36  }

    nptOspfV3InterfacePktDropSelfOrig	OBJECT-TYPE	
		SYNTAX			Counter64
		MAX-ACCESS		read-only
		STATUS			current
		DESCRIPTION		"Description"
		::=  {  nptOspfV3InterfaceEntry  37  }

    nptOspfV3InterfacePktDropDuplicateID	OBJECT-TYPE	
		SYNTAX			Counter64
		MAX-ACCESS		read-only
		STATUS			current
		DESCRIPTION		"Description"
		::=  {  nptOspfV3InterfaceEntry  38  }

    nptOspfV3InterfacePktDropHelloErrors	OBJECT-TYPE	
		SYNTAX			Counter64
		MAX-ACCESS		read-only
		STATUS			current
		DESCRIPTION		"Description"
		::=  {  nptOspfV3InterfaceEntry  39  }

    nptOspfV3InterfacePkDropMtuMismatch	OBJECT-TYPE	
		SYNTAX			Counter64
		MAX-ACCESS		read-only
		STATUS			current
		DESCRIPTION		"Description"
		::=  {  nptOspfV3InterfaceEntry  40  }

    nptOspfV3InterfacePktDropNbrIgnored	OBJECT-TYPE	
		SYNTAX			Counter64
		MAX-ACCESS		read-only
		STATUS			current
		DESCRIPTION		"Description"
		::=  {  nptOspfV3InterfaceEntry  41  }

    nptOspfV3InterfacePktDropResourceErr	OBJECT-TYPE	
		SYNTAX			Counter64
		MAX-ACCESS		read-only
		STATUS			current
		DESCRIPTION		"Description"
		::=  {  nptOspfV3InterfaceEntry  42  }

    nptOspfV3InterfacePktDropIfStandby	OBJECT-TYPE	
		SYNTAX			Counter64
		MAX-ACCESS		read-only
		STATUS			current
		DESCRIPTION		"Description"
		::=  {  nptOspfV3InterfaceEntry  43  }

    nptOspfV3InterfacePktDropUnkNbmaNbr	OBJECT-TYPE	
		SYNTAX			Counter64
		MAX-ACCESS		read-only
		STATUS			current
		DESCRIPTION		"Description"
		::=  {  nptOspfV3InterfaceEntry  44  }

    nptOspfV3InterfacePktDropUnkVirtNbr	OBJECT-TYPE	
		SYNTAX			Counter64
		MAX-ACCESS		read-only
		STATUS			current
		DESCRIPTION		"Description"
		::=  {  nptOspfV3InterfaceEntry  45  }

    nptOspfV3InterfacePktDropHelloMismatch	OBJECT-TYPE	
		SYNTAX			Counter64
		MAX-ACCESS		read-only
		STATUS			current
		DESCRIPTION		"Description"
		::=  {  nptOspfV3InterfaceEntry  46  }

    nptOspfV3InterfacePktDropDeadMismatch	OBJECT-TYPE	
		SYNTAX			Counter64
		MAX-ACCESS		read-only
		STATUS			current
		DESCRIPTION		"Description"
		::=  {  nptOspfV3InterfaceEntry  47  }

    nptOspfV3InterfacePktDropOptionsMismatch	OBJECT-TYPE	
		SYNTAX			Counter64
		MAX-ACCESS		read-only
		STATUS			current
		DESCRIPTION		"Description"
		::=  {  nptOspfV3InterfaceEntry  48  }

    nptOspfV3InterfacePktDropNbrAdminDown	OBJECT-TYPE	
		SYNTAX			Counter64
		MAX-ACCESS		read-only
		STATUS			current
		DESCRIPTION		"Description"
		::=  {  nptOspfV3InterfaceEntry  49  }

    nptOspfV3InterfacePktDropPktLocalAddr	OBJECT-TYPE	
		SYNTAX			Counter64
		MAX-ACCESS		read-only
		STATUS			current
		DESCRIPTION		"Description"
		::=  {  nptOspfV3InterfaceEntry  50  }

    nptOspfV3InterfacePktDropBadPacket	OBJECT-TYPE	
		SYNTAX			Counter64
		MAX-ACCESS		read-only
		STATUS			current
		DESCRIPTION		"Description"
		::=  {  nptOspfV3InterfaceEntry  51  }
		
	nptNdpProtocolTable	OBJECT-TYPE
		SYNTAX		SEQUENCE  OF  NptNdpProtocolEntry
		MAX-ACCESS	not-accessible
		STATUS		current
		DESCRIPTION	"Description"
		::=  { nptNdpProtocol  1 }

	nptNdpProtocolEntry	OBJECT-TYPE
		SYNTAX		NptNdpProtocolEntry
		MAX-ACCESS	not-accessible
		STATUS		current
		DESCRIPTION	"Row Description"
		INDEX		{  nptNdpProtocolIndex  }
		::=  { nptNdpProtocolTable 1 }

	NptNdpProtocolEntry  ::=  SEQUENCE {
	    nptNdpProtocolIndex  Integer32,
        nptNdpProtocolLifName  DisplayString,
		nptNdpProtocolNsRx Integer32,
		nptNdpProtocolNsTx Integer32,
		nptNdpProtocolNaRx Integer32,
		nptNdpProtocolNaTx Integer32,
		nptNdpProtocolRsRx Integer32,
		nptNdpProtocolRsTx Integer32,
		nptNdpProtocolRaRx Integer32,
		nptNdpProtocolRaTx Integer32,
		nptNdpProtocolDiscontinuityTime DisplayString,
		nptNdpProtocolElapsed DisplayString
		}


	nptNdpProtocolIndex	OBJECT-TYPE	
		SYNTAX			Integer32  ( -2147483648 .. 2147483647  ) 
		MAX-ACCESS		read-only
		STATUS			current
		DESCRIPTION		"Column Description"
		::=  {  nptNdpProtocolEntry  1  }


    nptNdpProtocolLifName	OBJECT-TYPE	
		SYNTAX			DisplayString 
		MAX-ACCESS		read-only
		STATUS			current
		DESCRIPTION		"Lif Name"
		::=  {  nptNdpProtocolEntry  2  }


    nptNdpProtocolNsRx	OBJECT-TYPE	
		SYNTAX			Integer32
		MAX-ACCESS		read-only
		STATUS			current
		DESCRIPTION		"Description"
		::=  {  nptNdpProtocolEntry  3  }

    nptNdpProtocolNsTx	OBJECT-TYPE	
		SYNTAX			Integer32
		MAX-ACCESS		read-only
		STATUS			current
		DESCRIPTION		"Description"
		::=  {  nptNdpProtocolEntry  4  }

    nptNdpProtocolNaRx	OBJECT-TYPE	
		SYNTAX			Integer32
		MAX-ACCESS		read-only
		STATUS			current
		DESCRIPTION		"Description"
		::=  {  nptNdpProtocolEntry  5  }

    nptNdpProtocolNaTx	OBJECT-TYPE	
		SYNTAX			Integer32
		MAX-ACCESS		read-only
		STATUS			current
		DESCRIPTION		"Description"
		::=  {  nptNdpProtocolEntry  6  }

    nptNdpProtocolRsRx	OBJECT-TYPE	
		SYNTAX			Integer32
		MAX-ACCESS		read-only
		STATUS			current
		DESCRIPTION		"Description"
		::=  {  nptNdpProtocolEntry  7  }

    nptNdpProtocolRsTx	OBJECT-TYPE	
		SYNTAX			Integer32
		MAX-ACCESS		read-only
		STATUS			current
		DESCRIPTION		"Description"
		::=  {  nptNdpProtocolEntry  8  }

    nptNdpProtocolRaRx	OBJECT-TYPE	
		SYNTAX			Integer32
		MAX-ACCESS		read-only
		STATUS			current
		DESCRIPTION		"Description"
		::=  {  nptNdpProtocolEntry  9  }

    nptNdpProtocolRaTx	OBJECT-TYPE	
		SYNTAX			Integer32
		MAX-ACCESS		read-only
		STATUS			current
		DESCRIPTION		"Description"
		::=  {  nptNdpProtocolEntry  10  }

    nptNdpProtocolDiscontinuityTime	OBJECT-TYPE	
		SYNTAX			DisplayString
		MAX-ACCESS		read-only
		STATUS			current
		DESCRIPTION		"Discontinuity Time"
		::=  {  nptNdpProtocolEntry  11  }

    nptNdpProtocolElapsed	OBJECT-TYPE	
		SYNTAX			DisplayString
		MAX-ACCESS		read-only
		STATUS			current
		DESCRIPTION		"Elapsed Time"
		::=  {  nptNdpProtocolEntry  12  }
		
	nptNdpTrackingTable	OBJECT-TYPE
		SYNTAX		SEQUENCE  OF  NptNdpTrackingEntry
		MAX-ACCESS	not-accessible
		STATUS		current
		DESCRIPTION	"Description"
		::=  { nptNdpTracking  1 }

	nptNdpTrackingEntry	OBJECT-TYPE
		SYNTAX		NptNdpTrackingEntry
		MAX-ACCESS	not-accessible
		STATUS		current
		DESCRIPTION	"Row Description"
		INDEX		{  nptNdpTrackingIndex  }
		::=  { nptNdpTrackingTable 1 }

	NptNdpTrackingEntry  ::=  SEQUENCE {
	    nptNdpTrackingIndex  Integer32,
        nptNdpTrackingInstanceName  DisplayString,
        nptNdpTrackingLifName  DisplayString,
        nptNdpTrackingPrefix  DisplayString,
        nptNdpTrackingMaskLen Integer32,
		nptNdpTrackingPrefixUpSec Integer32,
		nptNdpTrackingPrefixDownSec Integer32,
		nptNdpTrackingPrefixDownPercent Integer32,
		nptNdpTrackingPrefixDiscontinuityTime DisplayString,
		nptNdpTrackingPreifxElapsed DisplayString,
		nptNdpTrackingDestination DisplayString,
		nptNdpTrackingDstUpSec Integer32,
		nptNdpTrackingDstDownSec Integer32,
		nptNdpTrackingDstDownPercent Integer32,
		nptNdpTrackingDstDiscontinuityTime DisplayString,
		nptNdpTrackingDstElapsed DisplayString,
		nptNdpTrackingDstProbesSent Integer32,
		nptNdpTrackingDstProbesPassed Integer32,
		nptNdpTrackingDstProbesFailed Integer32,
		nptNdpTrackingDstProbesFailedRate Integer32
		}


	nptNdpTrackingIndex	OBJECT-TYPE	
		SYNTAX			Integer32  ( -2147483648 .. 2147483647  ) 
		MAX-ACCESS		read-only
		STATUS			current
		DESCRIPTION		"Column Description"
		::=  {  nptNdpTrackingEntry  1  }

    nptNdpTrackingInstanceName	OBJECT-TYPE	
		SYNTAX			DisplayString 
		MAX-ACCESS		read-only
		STATUS			current
		DESCRIPTION		"Instance Name"
		::=  {  nptNdpTrackingEntry  2  }

    nptNdpTrackingLifName	OBJECT-TYPE	
		SYNTAX			DisplayString 
		MAX-ACCESS		read-only
		STATUS			current
		DESCRIPTION		"Lif Name"
		::=  {  nptNdpTrackingEntry  3  }

    nptNdpTrackingPrefix	OBJECT-TYPE	
		SYNTAX			DisplayString
		MAX-ACCESS		read-only
		STATUS			current
		DESCRIPTION		"IPv6-address"
		::=  {  nptNdpTrackingEntry  4  }

    nptNdpTrackingMaskLen	OBJECT-TYPE	
		SYNTAX			Integer32
		MAX-ACCESS		read-only
		STATUS			current
		DESCRIPTION		"MaskLen"
		::=  {  nptNdpTrackingEntry  5  }


    nptNdpTrackingPrefixUpSec	OBJECT-TYPE	
		SYNTAX			Integer32
		MAX-ACCESS		read-only
		STATUS			current
		DESCRIPTION		"Description"
		::=  {  nptNdpTrackingEntry  6  }

    nptNdpTrackingPrefixDownSec	OBJECT-TYPE	
		SYNTAX			Integer32
		MAX-ACCESS		read-only
		STATUS			current
		DESCRIPTION		"Description"
		::=  {  nptNdpTrackingEntry  7  }

    nptNdpTrackingPrefixDownPercent	OBJECT-TYPE	
		SYNTAX			Integer32
		MAX-ACCESS		read-only
		STATUS			current
		DESCRIPTION		"Description"
		::=  {  nptNdpTrackingEntry  8  }

    nptNdpTrackingPrefixDiscontinuityTime	OBJECT-TYPE	
		SYNTAX			DisplayString
		MAX-ACCESS		read-only
		STATUS			current
		DESCRIPTION		"Discontinuity Time"
		::=  {  nptNdpTrackingEntry  9  }

    nptNdpTrackingPreifxElapsed	OBJECT-TYPE	
		SYNTAX			DisplayString
		MAX-ACCESS		read-only
		STATUS			current
		DESCRIPTION		"Elapsed Time"
		::=  {  nptNdpTrackingEntry  10  }

    nptNdpTrackingDestination	OBJECT-TYPE	
		SYNTAX			DisplayString
		MAX-ACCESS		read-only
		STATUS			current
		DESCRIPTION		"IPv6-address"
		::=  {  nptNdpTrackingEntry  11  }

    nptNdpTrackingDstUpSec	OBJECT-TYPE	
		SYNTAX			Integer32
		MAX-ACCESS		read-only
		STATUS			current
		DESCRIPTION		"Description"
		::=  {  nptNdpTrackingEntry  12  }

    nptNdpTrackingDstDownSec	OBJECT-TYPE	
		SYNTAX			Integer32
		MAX-ACCESS		read-only
		STATUS			current
		DESCRIPTION		"Description"
		::=  {  nptNdpTrackingEntry  13  }

    nptNdpTrackingDstDownPercent	OBJECT-TYPE	
		SYNTAX			Integer32
		MAX-ACCESS		read-only
		STATUS			current
		DESCRIPTION		"Description"
		::=  {  nptNdpTrackingEntry  14  }

    nptNdpTrackingDstDiscontinuityTime	OBJECT-TYPE	
		SYNTAX			DisplayString
		MAX-ACCESS		read-only
		STATUS			current
		DESCRIPTION		"Discontinuity Time"
		::=  {  nptNdpTrackingEntry  15  }

    nptNdpTrackingDstElapsed	OBJECT-TYPE	
		SYNTAX			DisplayString
		MAX-ACCESS		read-only
		STATUS			current
		DESCRIPTION		"Elapsed Time"
		::=  {  nptNdpTrackingEntry  16  }

    nptNdpTrackingDstProbesSent	OBJECT-TYPE	
		SYNTAX			Integer32
		MAX-ACCESS		read-only
		STATUS			current
		DESCRIPTION		"Description"
		::=  {  nptNdpTrackingEntry  17  }

    nptNdpTrackingDstProbesPassed	OBJECT-TYPE	
		SYNTAX			Integer32
		MAX-ACCESS		read-only
		STATUS			current
		DESCRIPTION		"Description"
		::=  {  nptNdpTrackingEntry  18  }

    nptNdpTrackingDstProbesFailed	OBJECT-TYPE	
		SYNTAX			Integer32
		MAX-ACCESS		read-only
		STATUS			current
		DESCRIPTION		"Description"
		::=  {  nptNdpTrackingEntry  19  }

    nptNdpTrackingDstProbesFailedRate	OBJECT-TYPE	
		SYNTAX			Integer32
		MAX-ACCESS		read-only
		STATUS			current
		DESCRIPTION		"Description"
		::=  {  nptNdpTrackingEntry  20  }
		
	nptmthBfdAutoTable	OBJECT-TYPE
		SYNTAX		SEQUENCE  OF  NptmthBfdAutoEntry
		MAX-ACCESS	not-accessible
		STATUS		current
		DESCRIPTION	"Description"
		::=  { nptmthBfdAuto  1 }

	nptmthBfdAutoEntry	OBJECT-TYPE
		SYNTAX		NptmthBfdAutoEntry
		MAX-ACCESS	not-accessible
		STATUS		current
		DESCRIPTION	"Row Description"
		INDEX		{  nptmthBfdAutoIndex  }
		::=  { nptmthBfdAutoTable 1 }

	NptmthBfdAutoEntry		::=  SEQUENCE {
	    nptmthBfdAutoIndex  		 		Integer32,
		nptmthBfdAutoInstanceName			DisplayString,
		nptmthBfdAutoSourceAddress			DisplayString,
		nptmthBfdAutoDestinationAddress		DisplayString,
		nptmthBfdAutoDiscontinuityTime		DisplayString,
		nptmthBfdAutoElapsed				DisplayString,
		nptmthBfdAutoPscRx					Integer32,
		nptmthBfdAutoPscTx			 		Integer32,
		nptmthBfdAutoPscInvalidRx	 		Integer32,
		nptmthBfdAutoUnknownRx				Integer32
		}


	nptmthBfdAutoIndex	OBJECT-TYPE	
		SYNTAX			Integer32     ( -2147483648 .. 2147483647  ) 
		MAX-ACCESS		read-only
		STATUS			current
		DESCRIPTION		"Column Description"
		::=  {  nptmthBfdAutoEntry  1  }


    nptmthBfdAutoInstanceName	OBJECT-TYPE	
		SYNTAX			DisplayString   
		MAX-ACCESS		read-only
		STATUS			current
		DESCRIPTION		"description"
		::=  {  nptmthBfdAutoEntry  2  }


    nptmthBfdAutoSourceAddress	OBJECT-TYPE	
		SYNTAX			DisplayString
		MAX-ACCESS		read-only
		STATUS			current
		DESCRIPTION		"description"
		::=  {  nptmthBfdAutoEntry  3  }

    nptmthBfdAutoDestinationAddress	OBJECT-TYPE	
		SYNTAX			DisplayString
		MAX-ACCESS		read-only
		STATUS			current
		DESCRIPTION		"description"
		::=  {  nptmthBfdAutoEntry  4  }
		
    nptmthBfdAutoDiscontinuityTime	OBJECT-TYPE	
		SYNTAX			DisplayString
		MAX-ACCESS		read-only
		STATUS			current
		DESCRIPTION		"description"
		::=  {  nptmthBfdAutoEntry  5  }
		
    nptmthBfdAutoElapsed	OBJECT-TYPE	
		SYNTAX			DisplayString
		MAX-ACCESS		read-only
		STATUS			current
		DESCRIPTION		"description"
		::=  {  nptmthBfdAutoEntry  6  }		

    nptmthBfdAutoPscRx	OBJECT-TYPE	
		SYNTAX			Integer32
		MAX-ACCESS		read-only
		STATUS			current
		DESCRIPTION		"Rx BFD Control Packets"
		::=  {  nptmthBfdAutoEntry  7  }

    nptmthBfdAutoPscTx	OBJECT-TYPE	
		SYNTAX			Integer32
		MAX-ACCESS		read-only
		STATUS			current
		DESCRIPTION		"Tx BFD Control Packets"
		::=  {  nptmthBfdAutoEntry  8  }
		
    nptmthBfdAutoPscInvalidRx	OBJECT-TYPE	
		SYNTAX			Integer32
		MAX-ACCESS		read-only
		STATUS			current
		DESCRIPTION		"Rx Invalid BFD Control Packets"
		::=  {  nptmthBfdAutoEntry  9  }	

    nptmthBfdAutoUnknownRx	OBJECT-TYPE	
		SYNTAX			Integer32
		MAX-ACCESS		read-only
		STATUS			current
		DESCRIPTION		"Unknown BFD Control Packets"
		::=  {  nptmthBfdAutoEntry  10  }		
		
	nptmthBfdManualTable	OBJECT-TYPE
		SYNTAX		SEQUENCE  OF  NptmthBfdManualEntry
		MAX-ACCESS	not-accessible
		STATUS		current
		DESCRIPTION	"Description"
		::=  { nptmthBfdManual 1 }

	nptmthBfdManualEntry	OBJECT-TYPE
		SYNTAX		NptmthBfdManualEntry
		MAX-ACCESS	not-accessible
		STATUS		current
		DESCRIPTION	"Row Description"
		INDEX		{  nptmthBfdManualIndex  }
		::=  { nptmthBfdManualTable 1 }

	NptmthBfdManualEntry		::=  SEQUENCE {
	    nptmthBfdManualIndex  		 		Integer32,
		nptmthBfdManualInstanceName			DisplayString,
		nptmthBfdManualSourceAddress		DisplayString,
		nptmthBfdManualDestinationAddress	DisplayString,
		nptmthBfdManualDiscontinuityTime	DisplayString,
		nptmthBfdManualElapsed				DisplayString,
		nptmthBfdManualPscRx				Integer32,
		nptmthBfdManualPscTx			 	Integer32,
		nptmthBfdManualPscInvalidRx	 		Integer32,
		nptmthBfdManualUnknownRx			Integer32
		}


	nptmthBfdManualIndex	OBJECT-TYPE	
		SYNTAX			Integer32     ( -2147483648 .. 2147483647  ) 
		MAX-ACCESS		read-only
		STATUS			current
		DESCRIPTION		"Column Description"
		::=  {  nptmthBfdManualEntry  1  }


    nptmthBfdManualInstanceName	OBJECT-TYPE	
		SYNTAX			DisplayString   
		MAX-ACCESS		read-only
		STATUS			current
		DESCRIPTION		"description"
		::=  {  nptmthBfdManualEntry  2  }


    nptmthBfdManualSourceAddress	OBJECT-TYPE	
		SYNTAX			DisplayString
		MAX-ACCESS		read-only
		STATUS			current
		DESCRIPTION		"description"
		::=  {  nptmthBfdManualEntry  3  }

    nptmthBfdManualDestinationAddress	OBJECT-TYPE	
		SYNTAX			DisplayString
		MAX-ACCESS		read-only
		STATUS			current
		DESCRIPTION		"description"
		::=  {  nptmthBfdManualEntry  4  }
		
    nptmthBfdManualDiscontinuityTime	OBJECT-TYPE	
		SYNTAX			DisplayString
		MAX-ACCESS		read-only
		STATUS			current
		DESCRIPTION		"description"
		::=  {  nptmthBfdManualEntry  5  }
		
    nptmthBfdManualElapsed	OBJECT-TYPE	
		SYNTAX			DisplayString
		MAX-ACCESS		read-only
		STATUS			current
		DESCRIPTION		"description"
		::=  {  nptmthBfdManualEntry  6  }		

    nptmthBfdManualPscRx	OBJECT-TYPE	
		SYNTAX			Integer32
		MAX-ACCESS		read-only
		STATUS			current
		DESCRIPTION		"Rx BFD Control Packets"
		::=  {  nptmthBfdManualEntry  7  }

    nptmthBfdManualPscTx	OBJECT-TYPE	
		SYNTAX			Integer32
		MAX-ACCESS		read-only
		STATUS			current
		DESCRIPTION		"Tx BFD Control Packets"
		::=  {  nptmthBfdManualEntry  8  }
		
    nptmthBfdManualPscInvalidRx	OBJECT-TYPE	
		SYNTAX			Integer32
		MAX-ACCESS		read-only
		STATUS			current
		DESCRIPTION		"Rx Invalid BFD Control Packets"
		::=  {  nptmthBfdManualEntry  9  }	

    nptmthBfdManualUnknownRx	OBJECT-TYPE	
		SYNTAX			Integer32
		MAX-ACCESS		read-only
		STATUS			current
		DESCRIPTION		"Unknown BFD Control Packets"
		::=  {  nptmthBfdManualEntry  10  }	

	nptLLDPStatisticsTable	OBJECT-TYPE
		SYNTAX		SEQUENCE  OF  NptLLDPStatisticsEntry
		MAX-ACCESS	not-accessible
		STATUS		current
		DESCRIPTION	"Description"
		::=  { nptLLDPStatistics 1 }

	nptLLDPStatisticsEntry	OBJECT-TYPE
		SYNTAX		NptLLDPStatisticsEntry
		MAX-ACCESS	not-accessible
		STATUS		current
		DESCRIPTION	"Row Description"
		INDEX		{  nptLLDPStatisticsIndex  }
		::=  { nptLLDPStatisticsTable 1 }

	NptLLDPStatisticsEntry		::=  SEQUENCE {
	    nptLLDPStatisticsIndex  		 	    Integer32,
		nptLLDPStatisticsPortName			    DisplayString,
		nptLLDPStatisticsDiscontinuityTime	    DisplayString,
        nptLLDPStatisticsElapsed                DisplayString,
		nptLLDPStatisticsFramesOut				Integer32,
		nptLLDPStatisticsLengthErrors			Integer32,
		nptLLDPStatisticsAgeoutsTotal			Integer32,
		nptLLDPStatisticsFramesDiscarded	    Integer32,
		nptLLDPStatisticsFramesInErrors			Integer32,
        nptLLDPStatisticsFramesIn               Integer32,
        nptLLDPStatisticsTLVsDiscarded          Integer32,
        nptLLDPStatisticsTLVsUnrecognized       Integer32,
        nptLLDPStatisticsRxPortAgeouts          Integer32
		}

	nptLLDPStatisticsIndex              OBJECT-TYPE	
		SYNTAX			Integer32     ( -2147483648 .. 2147483647  ) 
		MAX-ACCESS		read-only
		STATUS			current
		DESCRIPTION		"Column Description"
		::=  {  nptLLDPStatisticsEntry  1  }


    nptLLDPStatisticsPortName	        OBJECT-TYPE	
		SYNTAX			DisplayString   
		MAX-ACCESS		read-only
		STATUS			current
		DESCRIPTION		"description"
		::=  {  nptLLDPStatisticsEntry  2  }


    nptLLDPStatisticsDiscontinuityTime	OBJECT-TYPE	
		SYNTAX			DisplayString
		MAX-ACCESS		read-only
		STATUS			current
		DESCRIPTION		"description"
		::=  {  nptLLDPStatisticsEntry  3  }

    nptLLDPStatisticsElapsed        	OBJECT-TYPE	
		SYNTAX			DisplayString
		MAX-ACCESS		read-only
		STATUS			current
		DESCRIPTION		"description"
		::=  {  nptLLDPStatisticsEntry  4  }
		
    nptLLDPStatisticsFramesOut	OBJECT-TYPE	
		SYNTAX			Integer32
		MAX-ACCESS		read-only
		STATUS			current
		DESCRIPTION		"description"
		::=  {  nptLLDPStatisticsEntry  5  }
		
    nptLLDPStatisticsLengthErrors	OBJECT-TYPE	
		SYNTAX			Integer32
		MAX-ACCESS		read-only
		STATUS			current
		DESCRIPTION		"description"
		::=  {  nptLLDPStatisticsEntry  6  }		

    nptLLDPStatisticsAgeoutsTotal	OBJECT-TYPE	
		SYNTAX			Integer32
		MAX-ACCESS		read-only
		STATUS			current
		DESCRIPTION		"Rx BFD Control Packets"
		::=  {  nptLLDPStatisticsEntry  7  }

    nptLLDPStatisticsFramesDiscarded	OBJECT-TYPE	
		SYNTAX			Integer32
		MAX-ACCESS		read-only
		STATUS			current
		DESCRIPTION		"Tx BFD Control Packets"
		::=  {  nptLLDPStatisticsEntry  8  }
		
    nptLLDPStatisticsFramesInErrors	OBJECT-TYPE	
		SYNTAX			Integer32
		MAX-ACCESS		read-only
		STATUS			current
		DESCRIPTION		"Rx Invalid BFD Control Packets"
		::=  {  nptLLDPStatisticsEntry  9  }	

    nptLLDPStatisticsFramesIn	OBJECT-TYPE	
		SYNTAX			Integer32
		MAX-ACCESS		read-only
		STATUS			current
		DESCRIPTION		"Unknown BFD Control Packets"
		::=  {  nptLLDPStatisticsEntry  10  }	

    nptLLDPStatisticsTLVsDiscarded	OBJECT-TYPE	
		SYNTAX			Integer32
		MAX-ACCESS		read-only
		STATUS			current
		DESCRIPTION		"Unknown BFD Control Packets"
		::=  {  nptLLDPStatisticsEntry  11  }

    nptLLDPStatisticsTLVsUnrecognized	OBJECT-TYPE	
		SYNTAX			Integer32
		MAX-ACCESS		read-only
		STATUS			current
		DESCRIPTION		"Unknown BFD Control Packets"
		::=  {  nptLLDPStatisticsEntry  12  }

    nptLLDPStatisticsRxPortAgeouts	OBJECT-TYPE	
		SYNTAX			Integer32
		MAX-ACCESS		read-only
		STATUS			current
		DESCRIPTION		"Unknown BFD Control Packets"
		::=  {  nptLLDPStatisticsEntry  13  }	
        
	nptPhysicalPortTable	OBJECT-TYPE
		SYNTAX		SEQUENCE  OF  NptPhysicalPortEntry
		MAX-ACCESS	not-accessible
		STATUS		current
		DESCRIPTION	"The nptPhysicalPortTable is a MIB table that contains information about the physical ports of NPT. It provides details such as the port number, port name, port traffic statistics. This MIB table is read-only and can be used to monitor the traffic statistics of individual physical ports on the device. The table is indexed by the port number, and each row corresponds to a single physical port. The information in this table is useful for network administrators to troubleshoot connectivity issues, identify unused or faulty ports, and manage network traffic flows."
		::=  { nptPhysicalPort  1 }

	nptPhysicalPortEntry	OBJECT-TYPE
		SYNTAX		NptPhysicalPortEntry
		MAX-ACCESS	not-accessible
		STATUS		current
		DESCRIPTION	"The nptPhysicalPortEntry is a MIB item that represents a single physical port on NPT. The entry is indexed by the port number, and each attribute can be accessed individually. The nptPhysicalPortEntry is part of the nptPhysicalPortTable MIB item, which contains information about all the physical ports on the device."
		INDEX		{  nptPhysicalPortIndex  }
		::=  { nptPhysicalPortTable 1 }

	NptPhysicalPortEntry  ::=  SEQUENCE {
	    nptPhysicalPortIndex  Integer32,
        nptPhysicalPortName  DisplayString,
        nptPhysicalPortDisContinuityTime  DisplayString,
        nptPhysicalPortElapsed DisplayString,
		nptPhysicalPortRxOctets Counter64,
		nptPhysicalPortRxPkts Counter64,
		nptPhysicalPortRxBroadcastPkts Counter64,
		nptPhysicalPortRxMulticastPkts Counter64,
		nptPhysicalPortTxOctets Counter64,
		nptPhysicalPortTxPkts Counter64,
		nptPhysicalPortRxErrorPkts Counter64,
		nptPhysicalPortRxPkts64 Counter64,
		nptPhysicalPortRxPkts65To127 Counter64,
		nptPhysicalPortRxPkts128To255 Counter64,
		nptPhysicalPortRxPkts256To511 Counter64,
		nptPhysicalPortRxPkts512To1023 Counter64,
		nptPhysicalPortRxPktsOver1024 Counter64,
		nptPhysicalPortRxPausePkts Counter64,
		nptPhysicalPortRxCRCAlignErrorPkts Counter64,
		nptPhysicalPortRxUndersizePkts Counter64,
		nptPhysicalPortRxOversizePkts Counter64,
		nptPhysicalPortRxFragments Counter64,
		nptPhysicalPortRxJabberPkts Counter64,
		nptPhysicalPortCollisionErrors Counter64,
		nptPhysicalPortPcsLcv Counter64,
		nptPhysicalPortPcsEs Counter64,
		nptPhysicalPortPcsSes Counter64,
		nptPhysicalPortPcsUas Counter64
		}


	nptPhysicalPortIndex	OBJECT-TYPE	
		SYNTAX			Integer32  ( -2147483648 .. 2147483647  ) 
		MAX-ACCESS		read-only
		STATUS			current
		DESCRIPTION		"The index value for each physical port on the NE. This index value uniquely identifies each physical port on the device. The index value is an integer between 0 and N, where N + 1 is the total number of physical ports on the device. The nptPhysicalPortIndex is part of the nptPhysicalPortTable MIB table."
		::=  {  nptPhysicalPortEntry  1  }

    nptPhysicalPortName	OBJECT-TYPE	
		SYNTAX			DisplayString 
		MAX-ACCESS		read-only
		STATUS			current
		DESCRIPTION		"The name or label for each physical port on the NE. This name or label is typically assigned by the network administrator and is used to identify individual physical port. The name or label is a human-readable string."
		::=  {  nptPhysicalPortEntry  2  }

    nptPhysicalPortDisContinuityTime	OBJECT-TYPE	
		SYNTAX			DisplayString
		MAX-ACCESS		read-only
		STATUS			current
		DESCRIPTION		"The time when the operational status of a physical port on a network device last changed. This MIB item is used to detect when a physical port has been disconnected or reconnected, and can be used to trigger an alarm or notification."
		::=  {  nptPhysicalPortEntry  3  }

    nptPhysicalPortElapsed	OBJECT-TYPE	
		SYNTAX			DisplayString 
		MAX-ACCESS		read-only
		STATUS			current
		DESCRIPTION		"The elapsed time since the last counter reset. This MIB item is used to monitor the uptime/counter reset time of individual physical ports on the device and can be used to detect potential issues or failures. Format is dd:hh:mm:ss"
		::=  {  nptPhysicalPortEntry  4  }

    nptPhysicalPortRxOctets	OBJECT-TYPE	
		SYNTAX			Counter64
		MAX-ACCESS		read-only
		STATUS			current
		DESCRIPTION		"Received total number of bytes for all good packets (Unicast+Multicast+Broadcast)."
		::=  {  nptPhysicalPortEntry  5  }

    nptPhysicalPortRxPkts	OBJECT-TYPE	
		SYNTAX			Counter64
		MAX-ACCESS		read-only
		STATUS			current
		DESCRIPTION		"Received total number of good packets (Unicast+Multicast+Broadcast)."
		::=  {  nptPhysicalPortEntry  6  }

    nptPhysicalPortRxBroadcastPkts	OBJECT-TYPE	
		SYNTAX			Counter64
		MAX-ACCESS		read-only
		STATUS			current
		DESCRIPTION		"Received total number of good Broadcast packets."
		::=  {  nptPhysicalPortEntry  7  }

    nptPhysicalPortRxMulticastPkts	OBJECT-TYPE	
		SYNTAX			Counter64
		MAX-ACCESS		read-only
		STATUS			current
		DESCRIPTION		"Received total number of good Multicast packets."
		::=  {  nptPhysicalPortEntry  8  }

    nptPhysicalPortTxOctets	OBJECT-TYPE	
		SYNTAX			Counter64
		MAX-ACCESS		read-only
		STATUS			current
		DESCRIPTION		"Transmited total number of bytes for all good packets (Unicast+Multicast+Broadcast)."
		::=  {  nptPhysicalPortEntry  9  }

    nptPhysicalPortTxPkts	OBJECT-TYPE	
		SYNTAX			Counter64
		MAX-ACCESS		read-only
		STATUS			current
		DESCRIPTION		"Transmited total number of good packets (Unicast+Multicast+Broadcast)."
		::=  {  nptPhysicalPortEntry  10  }

    nptPhysicalPortRxErrorPkts	OBJECT-TYPE	
		SYNTAX			Counter64
		MAX-ACCESS		read-only
		STATUS			current
		DESCRIPTION		"Received total number of dropped packets, Includes all bad packets and dropped good packets."
		::=  {  nptPhysicalPortEntry  11  }

    nptPhysicalPortRxPkts64	OBJECT-TYPE	
		SYNTAX			Counter64
		MAX-ACCESS		read-only
		STATUS			current
		DESCRIPTION		"Received total number of good packets with size of 64bytes."
		::=  {  nptPhysicalPortEntry  12  }

    nptPhysicalPortRxPkts65To127	OBJECT-TYPE	
		SYNTAX			Counter64
		MAX-ACCESS		read-only
		STATUS			current
		DESCRIPTION		"Received total number of good packets with size of from 65 to 127 bytes."
		::=  {  nptPhysicalPortEntry  13  }

    nptPhysicalPortRxPkts128To255	OBJECT-TYPE	
		SYNTAX			Counter64
		MAX-ACCESS		read-only
		STATUS			current
		DESCRIPTION		"Received total number of good packets with size of from 128 to 255 bytes."
		::=  {  nptPhysicalPortEntry  14  }

    nptPhysicalPortRxPkts256To511	OBJECT-TYPE	
		SYNTAX			Counter64
		MAX-ACCESS		read-only
		STATUS			current
		DESCRIPTION		"Received total number of good packets with size of from 256 to 511 bytes."
		::=  {  nptPhysicalPortEntry  15  }

    nptPhysicalPortRxPkts512To1023	OBJECT-TYPE	
		SYNTAX			Counter64
		MAX-ACCESS		read-only
		STATUS			current
		DESCRIPTION		"Received total number of good packets with size of from 512 to 1023 bytes."
		::=  {  nptPhysicalPortEntry  16  }

    nptPhysicalPortRxPktsOver1024	OBJECT-TYPE	
		SYNTAX			Counter64
		MAX-ACCESS		read-only
		STATUS			current
		DESCRIPTION		"Received total number of good packets with size of from 1024 to MTU bytes."
		::=  {  nptPhysicalPortEntry  17  }

    nptPhysicalPortRxPausePkts	OBJECT-TYPE	
		SYNTAX			Counter64
		MAX-ACCESS		read-only
		STATUS			current
		DESCRIPTION		"Received total number of Pause frames."
		::=  {  nptPhysicalPortEntry  18  }

    nptPhysicalPortRxCRCAlignErrorPkts	OBJECT-TYPE	
		SYNTAX			Counter64
		MAX-ACCESS		read-only
		STATUS			current
		DESCRIPTION		"Received total number of bad packet which meets all the following conditions:  1.       Packet length is valid(between 64 and MTU). 2.       Packet has invalid CRC.3.       Collision event has not been detected."
		::=  {  nptPhysicalPortEntry  19  }

    nptPhysicalPortRxUndersizePkts	OBJECT-TYPE	
		SYNTAX			Counter64
		MAX-ACCESS		read-only
		STATUS			current
		DESCRIPTION		"Received total number of bad packet which meets all the following conditions: 1.       Packet length is less than 64bytes. 2.       Packet has valid CRC. 3.       Collision event has not been detected"
		::=  {  nptPhysicalPortEntry  20  }

    nptPhysicalPortRxOversizePkts	OBJECT-TYPE	
		SYNTAX			Counter64
		MAX-ACCESS		read-only
		STATUS			current
		DESCRIPTION		"Received total number of bad packet which meets all the following conditions: 1.       Packet length is larger than MTU. 2.       Packet has valid CRC. 3.       Collision event has not been detected."
		::=  {  nptPhysicalPortEntry  21  }

    nptPhysicalPortRxFragments	OBJECT-TYPE	
		SYNTAX			Counter64
		MAX-ACCESS		read-only
		STATUS			current
		DESCRIPTION		"The total number of packets received that were less than 64 octets in length (excluding framing bits but including FCS octets) and had either a bad Frame Check Sequence (FCS) with an integral number of octets (FCS Error) or a bad FCS with a non-integral number of octets (Alignment Error)."
		::=  {  nptPhysicalPortEntry  22  }

    nptPhysicalPortRxJabberPkts	OBJECT-TYPE	
		SYNTAX			Counter64
		MAX-ACCESS		read-only
		STATUS			current
		DESCRIPTION		"The total number of packets received that were longer than 1518 octets (excluding framing bits, but including FCS octets), and had either a bad Frame Check Sequence (FCS) with an integral number of octets (FCS Error) or a bad FCS with a non-integral number of octets (Alignment Error)."
		::=  {  nptPhysicalPortEntry  23  }

    nptPhysicalPortCollisionErrors	OBJECT-TYPE	
		SYNTAX			Counter64
		MAX-ACCESS		read-only
		STATUS			current
		DESCRIPTION		"Total number of collision events have been detected."
		::=  {  nptPhysicalPortEntry  24  }

    nptPhysicalPortPcsLcv	OBJECT-TYPE	
		SYNTAX			Counter64
		MAX-ACCESS		read-only
		STATUS			current
		DESCRIPTION		"PCS Errored Blocks, counts the number of times of entering to Error state (Errored  Blocks or sequence) or Line Code Violation"
		::=  {  nptPhysicalPortEntry  25  }

    nptPhysicalPortPcsEs	OBJECT-TYPE	
		SYNTAX			Counter64
		MAX-ACCESS		read-only
		STATUS			current
		DESCRIPTION		"Number of PCS Errored seconds near end accumulated. Rx_LCV or LOS,  LOSYNC,  Hi-BER"
		::=  {  nptPhysicalPortEntry  26  }

    nptPhysicalPortPcsSes	OBJECT-TYPE	
		SYNTAX			Counter64
		MAX-ACCESS		read-only
		STATUS			current
		DESCRIPTION		"Number of PCS Severely errored seconds near end accumulated. If 30% Rx_LCV are errored or LOS,  LOSYNC,  Hi-BER, this second is SES."
		::=  {  nptPhysicalPortEntry  27  }

    nptPhysicalPortPcsUas	OBJECT-TYPE	
		SYNTAX			Counter64
		MAX-ACCESS		read-only
		STATUS			current
		DESCRIPTION		"Number of PCS unavailable seconds near end accumulated"
		::=  {  nptPhysicalPortEntry  28  }
		
	nptIfTMDFSRVTable	OBJECT-TYPE
		SYNTAX		SEQUENCE  OF  NptIfTMDFSRVEntry
		MAX-ACCESS	not-accessible
		STATUS		current
		DESCRIPTION	"The nptIfTMDFSRVTable MIB table provides information about the Traffic Management - DiffServ (TM-DFSRV). The table contains a list of TM-DFSRV counters. This MIB table is read-only and can be used to monitor the statistics of DiffServ services on the device."
		::=  { nptIfTMDFSRV  1 }

	nptIfTMDFSRVEntry	OBJECT-TYPE
		SYNTAX		NptIfTMDFSRVEntry
		MAX-ACCESS	not-accessible
		STATUS		current
		DESCRIPTION	"The nptIfTMDFSRVEntry is a MIB item that represents a single Traffic Management - DiffServ counters' entry in the nptIfTMDFSRVTable. Each entry in the table contains information about its associated parameters."
		INDEX		{  nptIfTMDFSRVIndex  }
		::=  { nptIfTMDFSRVTable 1 }

	NptIfTMDFSRVEntry  ::=  SEQUENCE {
	    nptIfTMDFSRVIndex  Integer32,
        nptIfTMDFSRVIfName  DisplayString,
        nptIfTMDFSRVDisContinuityTime  DisplayString,
        nptIfTMDFSRVElapsed DisplayString,
        nptIfTMDFSRVEnabled  Integer32,
        nptIfTMDFSRVPmState  Integer32,
		nptIfTMDFSRVPassOctets Counter64,
		nptIfTMDFSRVPassPkts Counter64,
		nptIfTMDFSRVWREDDiscardOctets Counter64,
		nptIfTMDFSRVWREDDiscardPkts Counter64,
		nptIfTMDFSRVCoS0PassOctets	Counter64,
		nptIfTMDFSRVCoS0PassPkts	Counter64,
		nptIfTMDFSRVWREDCoS0DiscardOctets	Counter64,
		nptIfTMDFSRVWREDCoS0DiscardPkts		Counter64,
		nptIfTMDFSRVCoS1PassOctets	Counter64,
		nptIfTMDFSRVCoS1PassPkts	Counter64,
		nptIfTMDFSRVWREDCoS1DiscardOctets	Counter64,
		nptIfTMDFSRVWREDCoS1DiscardPkts		Counter64,
		nptIfTMDFSRVCoS2PassOctets	Counter64,
		nptIfTMDFSRVCoS2PassPkts	Counter64,
		nptIfTMDFSRVWREDCoS2DiscardOctets	Counter64,
		nptIfTMDFSRVWREDCoS2DiscardPkts		Counter64,
		nptIfTMDFSRVCoS3PassOctets	Counter64,
		nptIfTMDFSRVCoS3PassPkts	Counter64,
		nptIfTMDFSRVWREDCoS3DiscardOctets	Counter64,
		nptIfTMDFSRVWREDCoS3DiscardPkts		Counter64,
		nptIfTMDFSRVCoS4PassOctets	Counter64,
		nptIfTMDFSRVCoS4PassPkts	Counter64,
		nptIfTMDFSRVWREDCoS4DiscardOctets	Counter64,
		nptIfTMDFSRVWREDCoS4DiscardPkts		Counter64,
		nptIfTMDFSRVCoS5PassOctets	Counter64,
		nptIfTMDFSRVCoS5PassPkts	Counter64,
		nptIfTMDFSRVWREDCoS5DiscardOctets	Counter64,
		nptIfTMDFSRVWREDCoS5DiscardPkts		Counter64,
		nptIfTMDFSRVCoS6PassOctets	Counter64,
		nptIfTMDFSRVCoS6PassPkts	Counter64,
		nptIfTMDFSRVWREDCoS6DiscardOctets	Counter64,
		nptIfTMDFSRVWREDCoS6DiscardPkts		Counter64,
		nptIfTMDFSRVCoS7PassOctets	Counter64,
		nptIfTMDFSRVCoS7PassPkts	Counter64,
		nptIfTMDFSRVWREDCoS7DiscardOctets	Counter64,
		nptIfTMDFSRVWREDCoS7DiscardPkts		Counter64
		}


	nptIfTMDFSRVIndex	OBJECT-TYPE	
		SYNTAX			Integer32  ( -2147483648 .. 2147483647  ) 
		MAX-ACCESS		read-only
		STATUS			current
		DESCRIPTION		"The index value for the nptIfTMDFSRVTable. Each entry in the nptIfTMDFSRVTable has a unique index value assigned to it. The nptIfTMDFSRVIndex can be used to identify and locate specific interface in the nptIfTMDFSRVTable. The index value is a positive integer."
		::=  {  nptIfTMDFSRVEntry  1  }

    nptIfTMDFSRVIfName	OBJECT-TYPE	
		SYNTAX			DisplayString 
		MAX-ACCESS		read-only
		STATUS			current
		DESCRIPTION		"The name of the interface in the nptIfTMDFSRVTable, used for identifying specific interface"
		::=  {  nptIfTMDFSRVEntry  2  }

    nptIfTMDFSRVDisContinuityTime	OBJECT-TYPE	
		SYNTAX			DisplayString
		MAX-ACCESS		read-only
		STATUS			current
		DESCRIPTION		"The time when the operational status of a port on a network device last changed. This MIB item is used to detect when a interface has been disconnected or reconnected, and can be used to trigger an alarm or notification."
		::=  {  nptIfTMDFSRVEntry  3  }

    nptIfTMDFSRVElapsed	OBJECT-TYPE	
		SYNTAX			DisplayString 
		MAX-ACCESS		read-only
		STATUS			current
		DESCRIPTION		"The elapsed time since the last counter reset. This MIB item is used to monitor the uptime/counter reset time of individual interface on the device and can be used to detect potential issues or failures. Format is dd:hh:mm:ss"
		::=  {  nptIfTMDFSRVEntry  4  }


    nptIfTMDFSRVEnabled	OBJECT-TYPE	
		SYNTAX			Integer32
		MAX-ACCESS		read-only
		STATUS			current
		DESCRIPTION		"The admin status of TM-DFSRV. 0 means disabled,1 means enabled."
		::=  {  nptIfTMDFSRVEntry  5  }

    nptIfTMDFSRVPmState	OBJECT-TYPE	
		SYNTAX			Integer32
		MAX-ACCESS		read-only
		STATUS			current
		DESCRIPTION		"The operational state of the TM-DFSRV. 0 means no,1 mean yes."
		::=  {  nptIfTMDFSRVEntry  6  }

    nptIfTMDFSRVPassOctets	OBJECT-TYPE	
		SYNTAX			Counter64
		MAX-ACCESS		read-only
		STATUS			current
		DESCRIPTION		"Number of bytes passed by this TM block"
		::=  {  nptIfTMDFSRVEntry  7  }

    nptIfTMDFSRVPassPkts	OBJECT-TYPE	
		SYNTAX			Counter64
		MAX-ACCESS		read-only
		STATUS			current
		DESCRIPTION		"Number of packets passed by this TM block"
		::=  {  nptIfTMDFSRVEntry  8  }

    nptIfTMDFSRVWREDDiscardOctets	OBJECT-TYPE	
		SYNTAX			Counter64
		MAX-ACCESS		read-only
		STATUS			current
		DESCRIPTION		"Number of octets discarded by WRED on this TM block "
		::=  {  nptIfTMDFSRVEntry  9  }

    nptIfTMDFSRVWREDDiscardPkts	OBJECT-TYPE	
		SYNTAX			Counter64
		MAX-ACCESS		read-only
		STATUS			current
		DESCRIPTION		"Number of packets discarded by WRED on this TM block "
		::=  {  nptIfTMDFSRVEntry  10  }
		
		
    nptIfTMDFSRVCoS0PassOctets	OBJECT-TYPE	
		SYNTAX			Counter64
		MAX-ACCESS		read-only
		STATUS			current
		DESCRIPTION		"Number of bytes passed by CoS 0 of this TM block"
		::=  {  nptIfTMDFSRVEntry  11  }
		
	nptIfTMDFSRVCoS0PassPkts	OBJECT-TYPE	
		SYNTAX			Counter64
		MAX-ACCESS		read-only
		STATUS			current
		DESCRIPTION		"Number of packets passed by CoS 0 of this TM block"
		::=  {  nptIfTMDFSRVEntry  12  }
		
	nptIfTMDFSRVWREDCoS0DiscardOctets	OBJECT-TYPE	
		SYNTAX			Counter64
		MAX-ACCESS		read-only
		STATUS			current
		DESCRIPTION		"Number of octets discarded by WRED on CoS 0 of this TM block "
		::=  {  nptIfTMDFSRVEntry  13  }

	nptIfTMDFSRVWREDCoS0DiscardPkts	OBJECT-TYPE	
		SYNTAX			Counter64
		MAX-ACCESS		read-only
		STATUS			current
		DESCRIPTION		"Number of packets discarded by WRED on CoS 0 of this TM block "
		::=  {  nptIfTMDFSRVEntry  14  }

    nptIfTMDFSRVCoS1PassOctets	OBJECT-TYPE	
		SYNTAX			Counter64
		MAX-ACCESS		read-only
		STATUS			current
		DESCRIPTION		"Number of bytes passed by CoS 1 of this TM block"
		::=  {  nptIfTMDFSRVEntry  15  }
		
	nptIfTMDFSRVCoS1PassPkts	OBJECT-TYPE	
		SYNTAX			Counter64
		MAX-ACCESS		read-only
		STATUS			current
		DESCRIPTION		"Number of packets passed by CoS 1 of this TM block"
		::=  {  nptIfTMDFSRVEntry  16  }
		
	nptIfTMDFSRVWREDCoS1DiscardOctets	OBJECT-TYPE	
		SYNTAX			Counter64
		MAX-ACCESS		read-only
		STATUS			current
		DESCRIPTION		"Number of octets discarded by WRED on CoS 1 of this TM block"
		::=  {  nptIfTMDFSRVEntry  17  }

	nptIfTMDFSRVWREDCoS1DiscardPkts	OBJECT-TYPE	
		SYNTAX			Counter64
		MAX-ACCESS		read-only
		STATUS			current
		DESCRIPTION		"Number of packets discarded by WRED on CoS 1 of this TM block"
		::=  {  nptIfTMDFSRVEntry  18  }

    nptIfTMDFSRVCoS2PassOctets	OBJECT-TYPE	
		SYNTAX			Counter64
		MAX-ACCESS		read-only
		STATUS			current
		DESCRIPTION		"Number of bytes passed by CoS 2 of this TM block"
		::=  {  nptIfTMDFSRVEntry  19  }
		
	nptIfTMDFSRVCoS2PassPkts	OBJECT-TYPE	
		SYNTAX			Counter64
		MAX-ACCESS		read-only
		STATUS			current
		DESCRIPTION		"Number of packets passed by CoS 2 of this TM block"
		::=  {  nptIfTMDFSRVEntry  20  }
		
	nptIfTMDFSRVWREDCoS2DiscardOctets	OBJECT-TYPE	
		SYNTAX			Counter64
		MAX-ACCESS		read-only
		STATUS			current
		DESCRIPTION		"Number of octets discarded by WRED on CoS 2 of this TM block"
		::=  {  nptIfTMDFSRVEntry  21  }

	nptIfTMDFSRVWREDCoS2DiscardPkts	OBJECT-TYPE	
		SYNTAX			Counter64
		MAX-ACCESS		read-only
		STATUS			current
		DESCRIPTION		"Number of packets discarded by WRED on CoS 2 of this TM block"
		::=  {  nptIfTMDFSRVEntry  22  }

    nptIfTMDFSRVCoS3PassOctets	OBJECT-TYPE	
		SYNTAX			Counter64
		MAX-ACCESS		read-only
		STATUS			current
		DESCRIPTION		"Number of bytes passed by CoS 3 of this TM block"
		::=  {  nptIfTMDFSRVEntry  23  }
		
	nptIfTMDFSRVCoS3PassPkts	OBJECT-TYPE	
		SYNTAX			Counter64
		MAX-ACCESS		read-only
		STATUS			current
		DESCRIPTION		"Number of packets passed by CoS 3 of this TM block"
		::=  {  nptIfTMDFSRVEntry  24  }
		
	nptIfTMDFSRVWREDCoS3DiscardOctets	OBJECT-TYPE	
		SYNTAX			Counter64
		MAX-ACCESS		read-only
		STATUS			current
		DESCRIPTION		"Number of octets discarded by WRED on CoS 3 of this TM block"
		::=  {  nptIfTMDFSRVEntry  25  }

	nptIfTMDFSRVWREDCoS3DiscardPkts	OBJECT-TYPE	
		SYNTAX			Counter64
		MAX-ACCESS		read-only
		STATUS			current
		DESCRIPTION		"Number of packets discarded by WRED on CoS 3 of this TM block"
		::=  {  nptIfTMDFSRVEntry  26  }

    nptIfTMDFSRVCoS4PassOctets	OBJECT-TYPE	
		SYNTAX			Counter64
		MAX-ACCESS		read-only
		STATUS			current
		DESCRIPTION		"Number of bytes passed by CoS 4 of this TM block"
		::=  {  nptIfTMDFSRVEntry  27  }
		
	nptIfTMDFSRVCoS4PassPkts	OBJECT-TYPE	
		SYNTAX			Counter64
		MAX-ACCESS		read-only
		STATUS			current
		DESCRIPTION		"Number of packets passed by CoS 4 of this TM block"
		::=  {  nptIfTMDFSRVEntry  28  }
		
	nptIfTMDFSRVWREDCoS4DiscardOctets	OBJECT-TYPE	
		SYNTAX			Counter64
		MAX-ACCESS		read-only
		STATUS			current
		DESCRIPTION		"Number of octets discarded by WRED on CoS 4 of this TM block"
		::=  {  nptIfTMDFSRVEntry  29  }

	nptIfTMDFSRVWREDCoS4DiscardPkts	OBJECT-TYPE	
		SYNTAX			Counter64
		MAX-ACCESS		read-only
		STATUS			current
		DESCRIPTION		"Number of packets discarded by WRED on CoS 4 of this TM block"
		::=  {  nptIfTMDFSRVEntry  30  }

    nptIfTMDFSRVCoS5PassOctets	OBJECT-TYPE	
		SYNTAX			Counter64
		MAX-ACCESS		read-only
		STATUS			current
		DESCRIPTION		"Number of bytes passed by CoS 5 of this TM block"
		::=  {  nptIfTMDFSRVEntry  31  }
		
	nptIfTMDFSRVCoS5PassPkts	OBJECT-TYPE	
		SYNTAX			Counter64
		MAX-ACCESS		read-only
		STATUS			current
		DESCRIPTION		"Number of packets passed by CoS 5 of this TM block"
		::=  {  nptIfTMDFSRVEntry  32  }
		
	nptIfTMDFSRVWREDCoS5DiscardOctets	OBJECT-TYPE	
		SYNTAX			Counter64
		MAX-ACCESS		read-only
		STATUS			current
		DESCRIPTION		"Number of octets discarded by WRED on CoS 5 of this TM block"
		::=  {  nptIfTMDFSRVEntry  33  }

	nptIfTMDFSRVWREDCoS5DiscardPkts	OBJECT-TYPE	
		SYNTAX			Counter64
		MAX-ACCESS		read-only
		STATUS			current
		DESCRIPTION		"Number of packets discarded by WRED on CoS 5 of this TM block"
		::=  {  nptIfTMDFSRVEntry  34  }

    nptIfTMDFSRVCoS6PassOctets	OBJECT-TYPE	
		SYNTAX			Counter64
		MAX-ACCESS		read-only
		STATUS			current
		DESCRIPTION		"Number of bytes passed by CoS 6 of this TM block"
		::=  {  nptIfTMDFSRVEntry  35  }
		
	nptIfTMDFSRVCoS6PassPkts	OBJECT-TYPE	
		SYNTAX			Counter64
		MAX-ACCESS		read-only
		STATUS			current
		DESCRIPTION		"Number of packets passed by CoS 6 of this TM block"
		::=  {  nptIfTMDFSRVEntry  36  }
		
	nptIfTMDFSRVWREDCoS6DiscardOctets	OBJECT-TYPE	
		SYNTAX			Counter64
		MAX-ACCESS		read-only
		STATUS			current
		DESCRIPTION		"Number of octets discarded by WRED on CoS 6 of this TM block"
		::=  {  nptIfTMDFSRVEntry  37  }

	nptIfTMDFSRVWREDCoS6DiscardPkts	OBJECT-TYPE	
		SYNTAX			Counter64
		MAX-ACCESS		read-only
		STATUS			current
		DESCRIPTION		"Number of packets discarded by WRED on CoS 6 of this TM block"
		::=  {  nptIfTMDFSRVEntry  38  }

    nptIfTMDFSRVCoS7PassOctets	OBJECT-TYPE	
		SYNTAX			Counter64
		MAX-ACCESS		read-only
		STATUS			current
		DESCRIPTION		"Number of bytes passed by CoS 7 of this TM block"
		::=  {  nptIfTMDFSRVEntry  39  }
		
	nptIfTMDFSRVCoS7PassPkts	OBJECT-TYPE	
		SYNTAX			Counter64
		MAX-ACCESS		read-only
		STATUS			current
		DESCRIPTION		"Number of packets passed by CoS 7 of this TM block"
		::=  {  nptIfTMDFSRVEntry  40  }
		
	nptIfTMDFSRVWREDCoS7DiscardOctets	OBJECT-TYPE	
		SYNTAX			Counter64
		MAX-ACCESS		read-only
		STATUS			current
		DESCRIPTION		"Number of octets discarded by WRED on CoS 7 of this TM block"
		::=  {  nptIfTMDFSRVEntry  41  }

	nptIfTMDFSRVWREDCoS7DiscardPkts	OBJECT-TYPE	
		SYNTAX			Counter64
		MAX-ACCESS		read-only
		STATUS			current
		DESCRIPTION		"Number of packets discarded by WRED on CoS 7 of this TM block"
		::=  {  nptIfTMDFSRVEntry  42  }

		
	nptIfTMFRRTable	OBJECT-TYPE
		SYNTAX		SEQUENCE  OF  NptIfTMFRREntry
		MAX-ACCESS	not-accessible
		STATUS		current
		DESCRIPTION	"nptIfTMFRRTable is a MIB item that contains information about the TM FRR. Each entry in the table contains TM FRR block parameters. nptIfTMFRRTable is a read-write MIB table and can be used to monitor the TM FRR statistics for interface on the device. nptIfTMFRRTable is part of nptInterfaceIfGroup."
		::=  { nptIfTMFRR  1 }

	nptIfTMFRREntry	OBJECT-TYPE
		SYNTAX		NptIfTMFRREntry
		MAX-ACCESS	not-accessible
		STATUS		current
		DESCRIPTION	"nptIfTMFRREntry is a MIB item that represents a single entry in the nptIfTMFRRTable. Each entry contains information about its associated parameters."
		INDEX		{  nptIfTMFRRIndex  }
		::=  { nptIfTMFRRTable 1 }

	NptIfTMFRREntry  ::=  SEQUENCE {
	    nptIfTMFRRIndex  Integer32,
        nptIfTMFRRIfName  DisplayString,
        nptIfTMFRRDisContinuityTime  DisplayString,
        nptIfTMFRRElapsed DisplayString,
        nptIfTMFRREnabled  Integer32,
        nptIfTMFRRPmState  Integer32,
		nptIfTMFRRPassOctets Counter64,
		nptIfTMFRRPassPkts Counter64,
		nptIfTMFRRWREDDiscardOctets Counter64,
		nptIfTMFRRWREDDiscardPkts Counter64
		}

	nptIfTMFRRIndex	OBJECT-TYPE	
		SYNTAX			Integer32  ( -2147483648 .. 2147483647  ) 
		MAX-ACCESS		read-only
		STATUS			current
		DESCRIPTION		"The index value for a TM-FRR interface . Each entry in the nptIfTMFRRTable has a unique index value assigned to it. The nptIfTMFRRIndex can be used to identify and locate specific TM FRR block in the nptIfTMFRRTable. The index value is a positive integer."
		::=  {  nptIfTMFRREntry  1  }

    nptIfTMFRRIfName	OBJECT-TYPE	
		SYNTAX			DisplayString 
		MAX-ACCESS		read-only
		STATUS			current
		DESCRIPTION		"The name of an interface in the nptIfTMDFSRVTable, used for identifying specific interface"
		::=  {  nptIfTMFRREntry  2  }

    nptIfTMFRRDisContinuityTime	OBJECT-TYPE	
		SYNTAX			DisplayString
		MAX-ACCESS		read-only
		STATUS			current
		DESCRIPTION		"The time when the operational status of a port on a network device last changed. This MIB item is used to detect when a interface has been disconnected or reconnected, and can be used to trigger an alarm or notification."
		::=  {  nptIfTMFRREntry  3  }

    nptIfTMFRRElapsed	OBJECT-TYPE	
		SYNTAX			DisplayString 
		MAX-ACCESS		read-only
		STATUS			current
		DESCRIPTION		"The elapsed time since the last counter reset. This MIB item is used to monitor the uptime of individual interface on the device and can be used to detect potential issues or failures. Foramt is dd:hh:mm:ss"
		::=  {  nptIfTMFRREntry  4  }


    nptIfTMFRREnabled	OBJECT-TYPE	
		SYNTAX			Integer32
		MAX-ACCESS		read-only
		STATUS			current
		DESCRIPTION		"The admin status of a TM FRR block in the nptIfTMDFSRVTable. 0 means disabled, 1 means enabled."
		::=  {  nptIfTMFRREntry  5  }

    nptIfTMFRRPmState	OBJECT-TYPE	
		SYNTAX			Integer32
		MAX-ACCESS		read-only
		STATUS			current
		DESCRIPTION		"The operational state of a TM FRR block. 0 means no, 1 mean yes."
		::=  {  nptIfTMFRREntry  6  }

    nptIfTMFRRPassOctets	OBJECT-TYPE	
		SYNTAX			Counter64
		MAX-ACCESS		read-only
		STATUS			current
		DESCRIPTION		"Number of bytes passed by this TM block"
		::=  {  nptIfTMFRREntry  7  }

    nptIfTMFRRPassPkts	OBJECT-TYPE	
		SYNTAX			Counter64
		MAX-ACCESS		read-only
		STATUS			current
		DESCRIPTION		"Number of packets passed by this TM block"
		::=  {  nptIfTMFRREntry  8  }

    nptIfTMFRRWREDDiscardOctets	OBJECT-TYPE	
		SYNTAX			Counter64
		MAX-ACCESS		read-only
		STATUS			current
		DESCRIPTION		"Number of octets discarded by WRED on this TM block "
		::=  {  nptIfTMFRREntry  9  }

    nptIfTMFRRWREDDiscardPkts	OBJECT-TYPE	
		SYNTAX			Counter64
		MAX-ACCESS		read-only
		STATUS			current
		DESCRIPTION		"Number of packets discarded by WRED on this TM block "
		::=  {  nptIfTMFRREntry  10  }
		
	nptIfRxTable	OBJECT-TYPE
		SYNTAX		SEQUENCE  OF  NptIfRxEntry
		MAX-ACCESS	not-accessible
		STATUS		current
		DESCRIPTION	"The IfRxTable is a SNMP MIB table that provides statistics related to the incoming traffic on network interfaces. This table tracks the number of packets, octets, and errors received by each interface. The statistics in this table are useful for monitoring network performance and identifying potential issues with network interfaces that are receiving traffic or experiencing errors. The IfRxTable is an important tool for network administrators to assess the health and efficiency of their network infrastructure."
		::=  { nptIfRx  1 }

	nptIfRxEntry	OBJECT-TYPE
		SYNTAX		NptIfRxEntry
		MAX-ACCESS	not-accessible
		STATUS		current
		DESCRIPTION	"Represents an entry in the IfRxTable, containing detailed statistics related to incoming traffic on a specific network interface for troubleshooting and optimization of network performance."
		INDEX		{  nptIfRxIndex  }
		::=  { nptIfRxTable 1 }

	NptIfRxEntry  ::=  SEQUENCE {
	    nptIfRxIndex  Integer32,
        nptIfRxIfName  DisplayString,
        nptIfRxDisContinuityTime  DisplayString,
        nptIfRxElapsed DisplayString,
        nptIfRxPm  Integer32,
		nptIfRxOctetsPassG Counter64,
		nptIfRxOctetsPassY Counter64,
		nptIfRxOctetsPassSum Counter64,
		nptIfRxOctetsDiscardGY Counter64,
		nptIfRxOctetsDiscardR Counter64,
		nptIfRxOctetsDiscardSum Counter64,
		nptIfRxPacketsPassG Counter64,
		nptIfRxPacketsPassY Counter64,
		nptIfRxPacketsPassSum Counter64,
		nptIfRxPacketsDiscardGY Counter64,
		nptIfRxPacketsDiscardR Counter64,
		nptIfRxPacketsDiscardSum Counter64
		}


	nptIfRxIndex	OBJECT-TYPE	
		SYNTAX			Integer32  ( -2147483648 .. 2147483647  ) 
		MAX-ACCESS		read-only
		STATUS			current
		DESCRIPTION		"The index value of the interface. Each entry in the table has a unique index value assigned to it. The index can be used to identify and locate specific interface in the table. The index value is a positive integer."
		::=  {  nptIfRxEntry  1  }

    nptIfRxIfName	OBJECT-TYPE	
		SYNTAX			DisplayString 
		MAX-ACCESS		read-only
		STATUS			current
		DESCRIPTION		"The name of the interface in the table, used for identifying specific interface"
		::=  {  nptIfRxEntry  2  }

    nptIfRxDisContinuityTime	OBJECT-TYPE	
		SYNTAX			DisplayString
		MAX-ACCESS		read-only
		STATUS			current
		DESCRIPTION		"The time when the operational status of a physical port on a network device last changed. This MIB item is used to detect when a interface has been disconnected or reconnected, and can be used to trigger an alarm or notification."
		::=  {  nptIfRxEntry  3  }

    nptIfRxElapsed	OBJECT-TYPE	
		SYNTAX			DisplayString 
		MAX-ACCESS		read-only
		STATUS			current
		DESCRIPTION		"The elapsed time since the last counter reset. This MIB item is used to monitor the uptime/counter reset time of individual interface on the device and can be used to detect potential issues or failures. Format is dd:hh:mm:ss"
		::=  {  nptIfRxEntry  4  }

    nptIfRxPm	OBJECT-TYPE	
		SYNTAX			Integer32
		MAX-ACCESS		read-only
		STATUS			current
		DESCRIPTION		"Indicates the operational state of the interfaca. 0 means no,1 mean yes."
		::=  {  nptIfRxEntry  5  }

    nptIfRxOctetsPassG	OBJECT-TYPE	
		SYNTAX			Counter64
		MAX-ACCESS		read-only
		STATUS			current
		DESCRIPTION		"Passed total number of green bytes received from this interface"
		::=  {  nptIfRxEntry  6  }

    nptIfRxOctetsPassY	OBJECT-TYPE	
		SYNTAX			Counter64
		MAX-ACCESS		read-only
		STATUS			current
		DESCRIPTION		"Passed total number of yellow bytes received from this interface"
		::=  {  nptIfRxEntry  7  }

    nptIfRxOctetsPassSum	OBJECT-TYPE	
		SYNTAX			Counter64
		MAX-ACCESS		read-only
		STATUS			current
		DESCRIPTION		"IfRxOctetsPassG + IfRxOctetsPassY"
		::=  {  nptIfRxEntry  8  }

    nptIfRxOctetsDiscardGY	OBJECT-TYPE	
		SYNTAX			Counter64
		MAX-ACCESS		read-only
		STATUS			current
		DESCRIPTION		"Discarded total number of green or yellow bytes received from this interface"
		::=  {  nptIfRxEntry  9  }

    nptIfRxOctetsDiscardR	OBJECT-TYPE	
		SYNTAX			Counter64
		MAX-ACCESS		read-only
		STATUS			current
		DESCRIPTION		"Discarded total number of red bytes received from this interface"
		::=  {  nptIfRxEntry  10  }

    nptIfRxOctetsDiscardSum	OBJECT-TYPE	
		SYNTAX			Counter64
		MAX-ACCESS		read-only
		STATUS			current
		DESCRIPTION		"IfRxOctetsDiscardGY + IfRxOctetsDiscardR"
		::=  {  nptIfRxEntry  11  }

    nptIfRxPacketsPassG	OBJECT-TYPE	
		SYNTAX			Counter64
		MAX-ACCESS		read-only
		STATUS			current
		DESCRIPTION		"Passed total number of green packets received from this interface"
		::=  {  nptIfRxEntry  12  }

    nptIfRxPacketsPassY	OBJECT-TYPE	
		SYNTAX			Counter64
		MAX-ACCESS		read-only
		STATUS			current
		DESCRIPTION		"Passed total number of yellow packets received from this interface"
		::=  {  nptIfRxEntry  13  }

    nptIfRxPacketsPassSum	OBJECT-TYPE	
		SYNTAX			Counter64
		MAX-ACCESS		read-only
		STATUS			current
		DESCRIPTION		"IfRxPacketsPassG + IfRxPacketsPassY"
		::=  {  nptIfRxEntry  14  }

    nptIfRxPacketsDiscardGY	OBJECT-TYPE	
		SYNTAX			Counter64
		MAX-ACCESS		read-only
		STATUS			current
		DESCRIPTION		"Discarded total number of green or yellow packets received from this interface"
		::=  {  nptIfRxEntry  15  }

    nptIfRxPacketsDiscardR	OBJECT-TYPE	
		SYNTAX			Counter64
		MAX-ACCESS		read-only
		STATUS			current
		DESCRIPTION		"Discarded total number of red packets received from this interface"
		::=  {  nptIfRxEntry  16  }

    nptIfRxPacketsDiscardSum	OBJECT-TYPE	
		SYNTAX			Counter64
		MAX-ACCESS		read-only
		STATUS			current
		DESCRIPTION		"IfRxPacketsDiscardGY + IfRxPacketsDiscardR"
		::=  {  nptIfRxEntry  17  }
		
		
    
	nptIfTxTable	OBJECT-TYPE
		SYNTAX		SEQUENCE  OF  NptIfTxEntry
		MAX-ACCESS	not-accessible
		STATUS		current
		DESCRIPTION	"The IfTxTable is a SNMP MIB table that provides statistics related to the outgoing traffic on network interfaces. This table tracks the number of packets, octets, and errors transmitted by each interface. The statistics in this table are useful for monitoring network performance and identifying potential issues with network interfaces that are transmitting traffic or experiencing errors. The IfTxTable is an important tool for network administrators to assess the health and efficiency of their network infrastructure."
		::=  { nptIfTx  1 }

	nptIfTxEntry	OBJECT-TYPE
		SYNTAX		NptIfTxEntry
		MAX-ACCESS	not-accessible
		STATUS		current
		DESCRIPTION	"Represents an entry in the IfTxTable, containing detailed statistics related to outcoming traffic on a specific network interface for troubleshooting and optimization of network performance."
		INDEX		{  nptIfTxIndex  }
		::=  { nptIfTxTable 1 }

	NptIfTxEntry  ::=  SEQUENCE {
	    nptIfTxIndex  Integer32,
        nptIfTxIfName  DisplayString,
        nptIfTxDisContinuityTime  DisplayString,
        nptIfTxElapsed DisplayString,
        nptIfTxPm  Integer32,
		nptIfTxOctetsPassG Counter64,
		nptIfTxOctetsPassY Counter64,
		nptIfTxOctetsPassSum Counter64,
		nptIfTxOctetsDiscardGY Counter64,
		nptIfTxOctetsDiscardR Counter64,
		nptIfTxOctetsDiscardSum Counter64,
		nptIfTxPacketsPassG Counter64,
		nptIfTxPacketsPassY Counter64,
		nptIfTxPacketsPassSum Counter64,
		nptIfTxPacketsDiscardGY Counter64,
		nptIfTxPacketsDiscardR Counter64,
		nptIfTxPacketsDiscardSum Counter64
		}


	nptIfTxIndex	OBJECT-TYPE	
		SYNTAX			Integer32  ( -2147483648 .. 2147483647  ) 
		MAX-ACCESS		read-only
		STATUS			current
		DESCRIPTION		"The index value for IfTxTable. Each entry in the table has a unique index value assigned to it. The index can be used to identify and locate specific interface in the table. The index value is a positive integer."
		::=  {  nptIfTxEntry  1  }

    nptIfTxIfName	OBJECT-TYPE	
		SYNTAX			DisplayString 
		MAX-ACCESS		read-only
		STATUS			current
		DESCRIPTION		"The name of the interface in the table, used for identifying specific interface"
		::=  {  nptIfTxEntry  2  }

    nptIfTxDisContinuityTime	OBJECT-TYPE	
		SYNTAX			DisplayString
		MAX-ACCESS		read-only
		STATUS			current
		DESCRIPTION		"The time when the operational status of a port on a network device last changed. This MIB item is used to detect when a interface has been disconnected or reconnected, and can be used to trigger an alarm or notification."
		::=  {  nptIfTxEntry  3  }

    nptIfTxElapsed	OBJECT-TYPE	
		SYNTAX			DisplayString 
		MAX-ACCESS		read-only
		STATUS			current
		DESCRIPTION		"The elapsed time since the last counter reset. This MIB item is used to monitor the uptime/counter reset time of individual interface on the device and can be used to detect potential issues or failures. Format is dd:hh:mm:ss"
		::=  {  nptIfTxEntry  4  }

    nptIfTxPm	OBJECT-TYPE	
		SYNTAX			Integer32
		MAX-ACCESS		read-only
		STATUS			current
		DESCRIPTION		"Indicates the operational state of the interfaca. 0 means no,1 mean yes."
		::=  {  nptIfTxEntry  5  }

    nptIfTxOctetsPassG	OBJECT-TYPE	
		SYNTAX			Counter64
		MAX-ACCESS		read-only
		STATUS			current
		DESCRIPTION		"Passed total number of green bytes transmitted from this interface"
		::=  {  nptIfTxEntry  6  }

    nptIfTxOctetsPassY	OBJECT-TYPE	
		SYNTAX			Counter64
		MAX-ACCESS		read-only
		STATUS			current
		DESCRIPTION		"Passed total number of yellow bytes transmitted from this interface"
		::=  {  nptIfTxEntry  7  }

    nptIfTxOctetsPassSum	OBJECT-TYPE	
		SYNTAX			Counter64
		MAX-ACCESS		read-only
		STATUS			current
		DESCRIPTION		"IfTxOctetsPassG + IfTxOctetsPassY"
		::=  {  nptIfTxEntry  8  }

    nptIfTxOctetsDiscardGY	OBJECT-TYPE	
		SYNTAX			Counter64
		MAX-ACCESS		read-only
		STATUS			current
		DESCRIPTION		"Discarded total number of green bytes transmitted from this interface"
		::=  {  nptIfTxEntry  9  }

    nptIfTxOctetsDiscardR	OBJECT-TYPE	
		SYNTAX			Counter64
		MAX-ACCESS		read-only
		STATUS			current
		DESCRIPTION		"Discarded total number of yellow or red bytes transmitted from this interface"
		::=  {  nptIfTxEntry  10  }

    nptIfTxOctetsDiscardSum	OBJECT-TYPE	
		SYNTAX			Counter64
		MAX-ACCESS		read-only
		STATUS			current
		DESCRIPTION		"IfTxOctetsDiscardGY + IfTxOctetsDiscardR"
		::=  {  nptIfTxEntry  11  }

    nptIfTxPacketsPassG	OBJECT-TYPE	
		SYNTAX			Counter64
		MAX-ACCESS		read-only
		STATUS			current
		DESCRIPTION		"Passed total number of green packets transmitted from this interface"
		::=  {  nptIfTxEntry  12  }

    nptIfTxPacketsPassY	OBJECT-TYPE	
		SYNTAX			Counter64
		MAX-ACCESS		read-only
		STATUS			current
		DESCRIPTION		"Passed total number of yellow packets transmitted from this interface"
		::=  {  nptIfTxEntry  13  }

    nptIfTxPacketsPassSum	OBJECT-TYPE	
		SYNTAX			Counter64
		MAX-ACCESS		read-only
		STATUS			current
		DESCRIPTION		"TxPacketsPassG + TxPacketsPassY"
		::=  {  nptIfTxEntry  14  }

    nptIfTxPacketsDiscardGY	OBJECT-TYPE	
		SYNTAX			Counter64
		MAX-ACCESS		read-only
		STATUS			current
		DESCRIPTION		"Discarded total number of green or yellow packets transmitted from this interface"
		::=  {  nptIfTxEntry  15  }

    nptIfTxPacketsDiscardR	OBJECT-TYPE	
		SYNTAX			Counter64
		MAX-ACCESS		read-only
		STATUS			current
		DESCRIPTION		"Discarded total number of yellow or red packets transmitted from this interface"
		::=  {  nptIfTxEntry  16  }

    nptIfTxPacketsDiscardSum	OBJECT-TYPE	
		SYNTAX			Counter64
		MAX-ACCESS		read-only
		STATUS			current
		DESCRIPTION		"IfTxPacketsDiscardGY + IfTxPacketsDiscardR"
		::=  {  nptIfTxEntry  17  }
		
    
	nptLifTable	OBJECT-TYPE
		SYNTAX		SEQUENCE  OF  NptLifEntry
		MAX-ACCESS	not-accessible
		STATUS		current
		DESCRIPTION	"The LifTable is a SNMP MIB table that provides a table of information related to Logical Interface (LIF) traffic. A LIF is a virtual interface that represents a network connection on the device. The LifTable stores information about the LIFs on NE, including their names, operational status and traffic. This MIB item is useful for monitoring the LIFs traffic on NE, enabling network administrators to troubleshoot connectivity issues and optimize network performance."
		::=  { nptLif  1 }

	nptLifEntry	OBJECT-TYPE
		SYNTAX		NptLifEntry
		MAX-ACCESS	not-accessible
		STATUS		current
		DESCRIPTION	"Represents an entry in the LifTable, containing detailed statistics related to outcoming and incoming traffic on LIF for troubleshooting and optimization of network performance."
		INDEX		{  nptLifIndex  }
		::=  { nptLifTable 1 }

	NptLifEntry  ::=  SEQUENCE {
	    nptLifIndex  Integer32,
        nptLifName  DisplayString,
        nptLifUnit  Integer32,
        nptLifDisContinuityTime  DisplayString,
        nptLifElapsed DisplayString,
        nptLifPmState  Integer32,
		nptLifRxPassOctets Counter64,
		nptLifRxPassPkts Counter64,
		nptLifRxDiscardOctets Counter64,
		nptLifRxDiscardPkts Counter64,
		nptLifTxPassOctets Counter64,
		nptLifTxPassPkts Counter64,
		nptLifTxDiscardOctets Counter64,
		nptLifTxDiscardPkts Counter64,
		nptLifInBitsPerSec Counter64,
		nptLifInPktsPerSec Counter64,
		nptLifOutBitsPerSec Counter64,
		nptLifOutPktsPerSec Counter64
		}


	nptLifIndex	OBJECT-TYPE	
		SYNTAX			Integer32  ( -2147483648 .. 2147483647  ) 
		MAX-ACCESS		read-only
		STATUS			current
		DESCRIPTION		"The index value for Lif. Each entry in the table has a unique index value assigned to it.The index can be used to identify and locate specific Lif in the table. The index value is a positive integer."
		::=  {  nptLifEntry  1  }

    nptLifName	OBJECT-TYPE	
		SYNTAX			DisplayString 
		MAX-ACCESS		read-only
		STATUS			current
		DESCRIPTION		"The name of the logical interface in the table, used for identifying specific logical interface"
		::=  {  nptLifEntry  2  }

    nptLifUnit	OBJECT-TYPE	
		SYNTAX			Integer32
		MAX-ACCESS		read-only
		STATUS			current
		DESCRIPTION		"Specify the unit of lif"
		::=  {  nptLifEntry  3  }

    nptLifDisContinuityTime	OBJECT-TYPE	
		SYNTAX			DisplayString
		MAX-ACCESS		read-only
		STATUS			current
		DESCRIPTION		"The time when the operational status of the LIF on a network device last changed. This MIB item is used to detect when a LIF has been disconnected or reconnected, and can be used to trigger an alarm or notification."
		::=  {  nptLifEntry  4  }

    nptLifElapsed	OBJECT-TYPE	
		SYNTAX			DisplayString 
		MAX-ACCESS		read-only
		STATUS			current
		DESCRIPTION		"The elapsed time since the last counter reset. This MIB item is used to monitor the uptime/counter reset time of individual interface on the device and can be used to detect potential issues or failures. Format is dd:hh:mm:ss"
		::=  {  nptLifEntry  5  }

    nptLifPmState	OBJECT-TYPE	
		SYNTAX			Integer32
		MAX-ACCESS		read-only
		STATUS			current
		DESCRIPTION		"The status of a lif in the nptLifTable. 0 means disabled,1 means enabled."
		::=  {  nptLifEntry  6  }

    nptLifRxPassOctets	OBJECT-TYPE	
		SYNTAX			Counter64
		MAX-ACCESS		read-only
		STATUS			current
		DESCRIPTION		"Received total number of bytes passed from this LIF"
		::=  {  nptLifEntry  7  }

    nptLifRxPassPkts	OBJECT-TYPE	
		SYNTAX			Counter64
		MAX-ACCESS		read-only
		STATUS			current
		DESCRIPTION		"Received total number of packets passed from this LIF"
		::=  {  nptLifEntry  8  }

    nptLifRxDiscardOctets	OBJECT-TYPE	
		SYNTAX			Counter64
		MAX-ACCESS		read-only
		STATUS			current
		DESCRIPTION		"Discarded total number of bytes ingressed to this LIF"
		::=  {  nptLifEntry  9  }

    nptLifRxDiscardPkts	OBJECT-TYPE	
		SYNTAX			Counter64
		MAX-ACCESS		read-only
		STATUS			current
		DESCRIPTION		"Discarded total number of packets ingressed to this LIF"
		::=  {  nptLifEntry  10  }

    nptLifTxPassOctets	OBJECT-TYPE	
		SYNTAX			Counter64
		MAX-ACCESS		read-only
		STATUS			current
		DESCRIPTION		"Transmited total number of bytes."
		::=  {  nptLifEntry  11  }

    nptLifTxPassPkts	OBJECT-TYPE	
		SYNTAX			Counter64
		MAX-ACCESS		read-only
		STATUS			current
		DESCRIPTION		"Transmited total number of good packets (Unicast+Multicast+Broadcast)."
		::=  {  nptLifEntry  12  }

    nptLifTxDiscardOctets	OBJECT-TYPE	
		SYNTAX			Counter64
		MAX-ACCESS		read-only
		STATUS			current
		DESCRIPTION		"Number of bytes dropped for this LIF before transmitting"
		::=  {  nptLifEntry  13  }

    nptLifTxDiscardPkts	OBJECT-TYPE	
		SYNTAX			Counter64
		MAX-ACCESS		read-only
		STATUS			current
		DESCRIPTION		"Number of packets dropped for this LIF before transmitting"
		::=  {  nptLifEntry  14  }
		
    nptLifInBitsPerSec	OBJECT-TYPE	
		SYNTAX			Counter64
		MAX-ACCESS		read-only
		STATUS			current
		DESCRIPTION		"Received passed average bit rate under recent interval from this LIF"
		::=  {  nptLifEntry  15  }

    nptLifInPktsPerSec	OBJECT-TYPE	
		SYNTAX			Counter64
		MAX-ACCESS		read-only
		STATUS			current
		DESCRIPTION		"Received passed average packet rate under recent interval from this LIF"
		::=  {  nptLifEntry  16  }

    nptLifOutBitsPerSec	OBJECT-TYPE	
		SYNTAX			Counter64
		MAX-ACCESS		read-only
		STATUS			current
		DESCRIPTION		"Transmitted passed average bit rate under recent interval from this LIF"
		::=  {  nptLifEntry  17  }

    nptLifOutPktsPerSec	OBJECT-TYPE	
		SYNTAX			Counter64
		MAX-ACCESS		read-only
		STATUS			current
		DESCRIPTION		"Transmitted passed average packet rate under recent interval from this LIF"
		::=  {  nptLifEntry  18  }
        

		
		
	nptTunnelRxTable	OBJECT-TYPE
		SYNTAX		SEQUENCE  OF  NptTunnelRxEntry
		MAX-ACCESS	not-accessible
		STATUS		current
		DESCRIPTION	"Description"
		::=  { nptTunnelRx  1 }

	nptTunnelRxEntry	OBJECT-TYPE
		SYNTAX		NptTunnelRxEntry
		MAX-ACCESS	not-accessible
		STATUS		current
		DESCRIPTION	"Row Description"
		INDEX		{  nptTunnelRxIndex  }
		::=  { nptTunnelRxTable 1 }

	NptTunnelRxEntry  ::=  SEQUENCE {
	    nptTunnelRxIndex  Integer32,
        nptTunnelRxTunnelName  DisplayString,
        nptTunnelRxTunnelType  Integer32,
        nptTunnelRxLSP  DisplayString,
        nptTunnelRxDirection  DisplayString,
        nptTunnelRxEnable  Integer32,
        nptTunnelRxLifName  DisplayString,
        nptTunnelRxDisContinuityTime  DisplayString,
        nptTunnelRxElapsed DisplayString,
		nptTunnelRxOctetsPassG Counter64,
		nptTunnelRxOctetsPassY Counter64,
		nptTunnelRxOctetsPassSum Counter64,
		nptTunnelRxOctetsDiscardGY Counter64,
		nptTunnelRxOctetsDiscardR Counter64,
		nptTunnelRxOctetsDiscardSum Counter64,
		nptTunnelRxPacketsPassG Counter64,
		nptTunnelRxPacketsPassY Counter64,
		nptTunnelRxPacketsPassSum Counter64,
		nptTunnelRxPacketsDiscardGY Counter64,
		nptTunnelRxPacketsDiscardR Counter64,
		nptTunnelRxPacketsDiscardSum Counter64
		}


	nptTunnelRxIndex	OBJECT-TYPE	
		SYNTAX			Integer32  ( -2147483648 .. 2147483647  ) 
		MAX-ACCESS		read-only
		STATUS			current
		DESCRIPTION		"Column Description"
		::=  {  nptTunnelRxEntry  1  }

    nptTunnelRxTunnelName	OBJECT-TYPE	
		SYNTAX			DisplayString 
		MAX-ACCESS		read-only
		STATUS			current
		DESCRIPTION		"tunnel Name"
		::=  {  nptTunnelRxEntry  2  }

    nptTunnelRxTunnelType	OBJECT-TYPE	
		SYNTAX			Integer32
		MAX-ACCESS		read-only
		STATUS			current
		DESCRIPTION		"tunnel type"
		::=  {  nptTunnelRxEntry  3  }

    nptTunnelRxLSP	OBJECT-TYPE	
		SYNTAX			DisplayString 
		MAX-ACCESS		read-only
		STATUS			current
		DESCRIPTION		"LSP"
		::=  {  nptTunnelRxEntry  4  }

    nptTunnelRxDirection	OBJECT-TYPE	
		SYNTAX			DisplayString 
		MAX-ACCESS		read-only
		STATUS			current
		DESCRIPTION		"Direction"
		::=  {  nptTunnelRxEntry  5  }

    nptTunnelRxEnable	OBJECT-TYPE	
		SYNTAX			Integer32
		MAX-ACCESS		read-only
		STATUS			current
		DESCRIPTION		"Enable/Disable"
		::=  {  nptTunnelRxEntry  6  }

    nptTunnelRxLifName	OBJECT-TYPE	
		SYNTAX			DisplayString 
		MAX-ACCESS		read-only
		STATUS			current
		DESCRIPTION		"Lif Name"
		::=  {  nptTunnelRxEntry  7  }

    nptTunnelRxDisContinuityTime	OBJECT-TYPE	
		SYNTAX			DisplayString
		MAX-ACCESS		read-only
		STATUS			current
		DESCRIPTION		"DisContinuity Time"
		::=  {  nptTunnelRxEntry  8  }

    nptTunnelRxElapsed	OBJECT-TYPE	
		SYNTAX			DisplayString 
		MAX-ACCESS		read-only
		STATUS			current
		DESCRIPTION		"Elapsed time output-dd:hh:mm:ss"
		::=  {  nptTunnelRxEntry  9  }


    nptTunnelRxOctetsPassG	OBJECT-TYPE	
		SYNTAX			Counter64
		MAX-ACCESS		read-only
		STATUS			current
		DESCRIPTION		"Passed total number of green bytes transmitted from this XC out-segment"
		::=  {  nptTunnelRxEntry  10  }

    nptTunnelRxOctetsPassY	OBJECT-TYPE	
		SYNTAX			Counter64
		MAX-ACCESS		read-only
		STATUS			current
		DESCRIPTION		"Passed total number of yellow bytes transmitted from this XC out-segment"
		::=  {  nptTunnelRxEntry  11  }

    nptTunnelRxOctetsPassSum	OBJECT-TYPE	
		SYNTAX			Counter64
		MAX-ACCESS		read-only
		STATUS			current
		DESCRIPTION		"TunnelRxOctetsPassG + TunnelRxOctetsPassY"
		::=  {  nptTunnelRxEntry  12  }

    nptTunnelRxOctetsDiscardGY	OBJECT-TYPE	
		SYNTAX			Counter64
		MAX-ACCESS		read-only
		STATUS			current
		DESCRIPTION		"Discarded total number of green or yellow bytes transmitted from this XC out-segment"
		::=  {  nptTunnelRxEntry  13  }

    nptTunnelRxOctetsDiscardR	OBJECT-TYPE	
		SYNTAX			Counter64
		MAX-ACCESS		read-only
		STATUS			current
		DESCRIPTION		"Discarded total number of red bytes transmitted from this XC out-segment"
		::=  {  nptTunnelRxEntry  14  }

    nptTunnelRxOctetsDiscardSum	OBJECT-TYPE	
		SYNTAX			Counter64
		MAX-ACCESS		read-only
		STATUS			current
		DESCRIPTION		"TunnelRxOctetsDiscardGY + TunnelRxOctetsDiscardR"
		::=  {  nptTunnelRxEntry  15  }

    nptTunnelRxPacketsPassG	OBJECT-TYPE	
		SYNTAX			Counter64
		MAX-ACCESS		read-only
		STATUS			current
		DESCRIPTION		"Passed total number of green packets transmitted from this XC out-segment"
		::=  {  nptTunnelRxEntry  16  }

    nptTunnelRxPacketsPassY	OBJECT-TYPE	
		SYNTAX			Counter64
		MAX-ACCESS		read-only
		STATUS			current
		DESCRIPTION		"Passed total number of yellow packets transmitted from this XC out-segment"
		::=  {  nptTunnelRxEntry  17  }

    nptTunnelRxPacketsPassSum	OBJECT-TYPE	
		SYNTAX			Counter64
		MAX-ACCESS		read-only
		STATUS			current
		DESCRIPTION		"TunnelRxPacketsPassG + TunnelRxPacketsPassY"
		::=  {  nptTunnelRxEntry  18  }

    nptTunnelRxPacketsDiscardGY	OBJECT-TYPE	
		SYNTAX			Counter64
		MAX-ACCESS		read-only
		STATUS			current
		DESCRIPTION		"Discarded total number of green or yellow packets transmitted from this XC out-segment"
		::=  {  nptTunnelRxEntry  19  }

    nptTunnelRxPacketsDiscardR	OBJECT-TYPE	
		SYNTAX			Counter64
		MAX-ACCESS		read-only
		STATUS			current
		DESCRIPTION		"Discarded total number of yellow or red packets transmitted from this XC out-segment"
		::=  {  nptTunnelRxEntry  20  }

    nptTunnelRxPacketsDiscardSum	OBJECT-TYPE	
		SYNTAX			Counter64
		MAX-ACCESS		read-only
		STATUS			current
		DESCRIPTION		"TunnelRxPacketsDiscardGY + TunnelRxPacketsDiscardR"
		::=  {  nptTunnelRxEntry  21  }
		
	nptTunnelRxCoSTable	OBJECT-TYPE
		SYNTAX		SEQUENCE  OF  NptTunnelRxCoSEntry
		MAX-ACCESS	not-accessible
		STATUS		current
		DESCRIPTION	"nptTunnelRxCoSTable"
		::=  { nptTunnelRxCoS  1 }

	nptTunnelRxCoSEntry	OBJECT-TYPE
		SYNTAX		NptTunnelRxCoSEntry
		MAX-ACCESS	not-accessible
		STATUS		current
		DESCRIPTION	"Row Description"
		INDEX		{  nptTunnelRxCoSIndex  }
		::=  { nptTunnelRxCoSTable 1 }

	NptTunnelRxCoSEntry  ::=  SEQUENCE {
	    nptTunnelRxCoSIndex  Integer32,
        nptTunnelRxCoSTunnelName  DisplayString,
        nptTunnelRxCoSTunnelType  Integer32,
        nptTunnelRxCoSLSP  DisplayString,
        nptTunnelRxCoSDirection  DisplayString,
        nptTunnelRxCoSID  Integer32,
        nptTunnelRxCoSPM  Integer32,
        nptTunnelRxCoSLifName  DisplayString,
        nptTunnelRxCoSDisContinuityTime  DisplayString,
        nptTunnelRxCoSElapsed DisplayString,
		nptTunnelRxCoSOctetsPassG Counter64,
		nptTunnelRxCoSOctetsPassY Counter64,
		nptTunnelRxCoSOctetsPassSum Counter64,
		nptTunnelRxCoSOctetsDiscardGY Counter64,
		nptTunnelRxCoSOctetsDiscardR Counter64,
		nptTunnelRxCoSOctetsDiscardSum Counter64,
		nptTunnelRxCoSPacketsPassG Counter64,
		nptTunnelRxCoSPacketsPassY Counter64,
		nptTunnelRxCoSPacketsPassSum Counter64,
		nptTunnelRxCoSPacketsDiscardGY Counter64,
		nptTunnelRxCoSPacketsDiscardR Counter64,
		nptTunnelRxCoSPacketsDiscardSum Counter64
		}


	nptTunnelRxCoSIndex	OBJECT-TYPE	
		SYNTAX			Integer32  ( -2147483648 .. 2147483647  ) 
		MAX-ACCESS		read-only
		STATUS			current
		DESCRIPTION		"Index"
		::=  {  nptTunnelRxCoSEntry  1  }

    nptTunnelRxCoSTunnelName	OBJECT-TYPE	
		SYNTAX			DisplayString 
		MAX-ACCESS		read-only
		STATUS			current
		DESCRIPTION		"tunnel Name"
		::=  {  nptTunnelRxCoSEntry  2  }

    nptTunnelRxCoSTunnelType	OBJECT-TYPE	
		SYNTAX			Integer32
		MAX-ACCESS		read-only
		STATUS			current
		DESCRIPTION		"tunnel type"
		::=  {  nptTunnelRxCoSEntry  3  }

    nptTunnelRxCoSLSP	OBJECT-TYPE	
		SYNTAX			DisplayString 
		MAX-ACCESS		read-only
		STATUS			current
		DESCRIPTION		"LSP"
		::=  {  nptTunnelRxCoSEntry  4  }

    nptTunnelRxCoSDirection	OBJECT-TYPE	
		SYNTAX			DisplayString 
		MAX-ACCESS		read-only
		STATUS			current
		DESCRIPTION		"Direction"
		::=  {  nptTunnelRxCoSEntry  5  }

    nptTunnelRxCoSID	OBJECT-TYPE	
		SYNTAX			Integer32
		MAX-ACCESS		read-only
		STATUS			current
		DESCRIPTION		"Cos ID"
		::=  {  nptTunnelRxCoSEntry  6  }

    nptTunnelRxCoSPM	OBJECT-TYPE	
		SYNTAX			Integer32
		MAX-ACCESS		read-only
		STATUS			current
		DESCRIPTION		"PM"
		::=  {  nptTunnelRxCoSEntry  7  }

    nptTunnelRxCoSLifName	OBJECT-TYPE	
		SYNTAX			DisplayString 
		MAX-ACCESS		read-only
		STATUS			current
		DESCRIPTION		"Lif Name"
		::=  {  nptTunnelRxCoSEntry  8  }

    nptTunnelRxCoSDisContinuityTime	OBJECT-TYPE	
		SYNTAX			DisplayString
		MAX-ACCESS		read-only
		STATUS			current
		DESCRIPTION		"DisContinuity Time"
		::=  {  nptTunnelRxCoSEntry  9  }

    nptTunnelRxCoSElapsed	OBJECT-TYPE	
		SYNTAX			DisplayString 
		MAX-ACCESS		read-only
		STATUS			current
		DESCRIPTION		"Elapsed time output-dd:hh:mm:ss"
		::=  {  nptTunnelRxCoSEntry  10  }


    nptTunnelRxCoSOctetsPassG	OBJECT-TYPE	
		SYNTAX			Counter64
		MAX-ACCESS		read-only
		STATUS			current
		DESCRIPTION		"Passed total number of green bytes received from the CoS/CoS Group of this XC in-segment"
		::=  {  nptTunnelRxCoSEntry  11  }

    nptTunnelRxCoSOctetsPassY	OBJECT-TYPE	
		SYNTAX			Counter64
		MAX-ACCESS		read-only
		STATUS			current
		DESCRIPTION		"Passed total number of yellow bytes received from the CoS/CoS Group of this XC in-segment"
		::=  {  nptTunnelRxCoSEntry  12  }

    nptTunnelRxCoSOctetsPassSum	OBJECT-TYPE	
		SYNTAX			Counter64
		MAX-ACCESS		read-only
		STATUS			current
		DESCRIPTION		"Passed total number of bytes(green+yellow) received from the CoS/CoS Group of this XC in-segment"
		::=  {  nptTunnelRxCoSEntry  13  }

    nptTunnelRxCoSOctetsDiscardGY	OBJECT-TYPE	
		SYNTAX			Counter64
		MAX-ACCESS		read-only
		STATUS			current
		DESCRIPTION		"Discarded total number of green or yellow bytes received from the CoS/CoS Group of this XC in-segment"
		::=  {  nptTunnelRxCoSEntry  14  }

    nptTunnelRxCoSOctetsDiscardR	OBJECT-TYPE	
		SYNTAX			Counter64
		MAX-ACCESS		read-only
		STATUS			current
		DESCRIPTION		"Discarded total number of yellow or red bytes received from the CoS/CoS Group of this XC in-segment"
		::=  {  nptTunnelRxCoSEntry  15  }

    nptTunnelRxCoSOctetsDiscardSum	OBJECT-TYPE	
		SYNTAX			Counter64
		MAX-ACCESS		read-only
		STATUS			current
		DESCRIPTION		"Discarded total number of bytes received from the CoS/CoS Group of this XC in-segment"
		::=  {  nptTunnelRxCoSEntry  16  }

    nptTunnelRxCoSPacketsPassG	OBJECT-TYPE	
		SYNTAX			Counter64
		MAX-ACCESS		read-only
		STATUS			current
		DESCRIPTION		"Passed total number of green packets received from the CoS/CoS Group of this XC in-segment"
		::=  {  nptTunnelRxCoSEntry  17  }

    nptTunnelRxCoSPacketsPassY	OBJECT-TYPE	
		SYNTAX			Counter64
		MAX-ACCESS		read-only
		STATUS			current
		DESCRIPTION		"Passed total number of yellow packets received from the CoS/CoS Group of this XC in-segment"
		::=  {  nptTunnelRxCoSEntry  18  }

    nptTunnelRxCoSPacketsPassSum	OBJECT-TYPE	
		SYNTAX			Counter64
		MAX-ACCESS		read-only
		STATUS			current
		DESCRIPTION		"Passed total number of packets(green+yellow) received from the CoS/CoS Group of this XC in-segment"
		::=  {  nptTunnelRxCoSEntry  19  }

    nptTunnelRxCoSPacketsDiscardGY	OBJECT-TYPE	
		SYNTAX			Counter64
		MAX-ACCESS		read-only
		STATUS			current
		DESCRIPTION		"Discarded total number of green or yellow packets received from the CoS/CoS Group of this XC in-segment"
		::=  {  nptTunnelRxCoSEntry  20  }

    nptTunnelRxCoSPacketsDiscardR	OBJECT-TYPE	
		SYNTAX			Counter64
		MAX-ACCESS		read-only
		STATUS			current
		DESCRIPTION		"Discarded total number of yellow or red packets received from the CoS/CoS Group of this XC in-segment"
		::=  {  nptTunnelRxCoSEntry  21  }

    nptTunnelRxCoSPacketsDiscardSum	OBJECT-TYPE	
		SYNTAX			Counter64
		MAX-ACCESS		read-only
		STATUS			current
		DESCRIPTION		"Discarded total number of packets received from the CoS/CoS Group of this XC in-segment"
		::=  {  nptTunnelRxCoSEntry  22  }
		
	nptTunnelTxTable	OBJECT-TYPE
		SYNTAX		SEQUENCE  OF  NptTunnelTxEntry
		MAX-ACCESS	not-accessible
		STATUS		current
		DESCRIPTION	"nptTunnelTxTable"
		::=  { nptTunnelTx  1 }

	nptTunnelTxEntry	OBJECT-TYPE
		SYNTAX		NptTunnelTxEntry
		MAX-ACCESS	not-accessible
		STATUS		current
		DESCRIPTION	"nptTunnelTxEntry"
		INDEX		{  nptTunnelTxIndex  }
		::=  { nptTunnelTxTable 1 }

	NptTunnelTxEntry  ::=  SEQUENCE {
	    nptTunnelTxIndex  Integer32,
        nptTunnelTxTunnelName  DisplayString,
        nptTunnelTxTunnelType  Integer32,
        nptTunnelTxLSP  DisplayString,
        nptTunnelTxDirection  DisplayString,
        nptTunnelTxEnable  Integer32,
        nptTunnelTxLifName  DisplayString,
        nptTunnelTxDisContinuityTime  DisplayString,
        nptTunnelTxElapsed DisplayString,
		nptTunnelTxOctetsPassG Counter64,
		nptTunnelTxOctetsPassY Counter64,
		nptTunnelTxOctetsPassSum Counter64,
		nptTunnelTxOctetsDiscardGY Counter64,
		nptTunnelTxOctetsDiscardR Counter64,
		nptTunnelTxOctetsDiscardSum Counter64,
		nptTunnelTxPacketsPassG Counter64,
		nptTunnelTxPacketsPassY Counter64,
		nptTunnelTxPacketsPassSum Counter64,
		nptTunnelTxPacketsDiscardGY Counter64,
		nptTunnelTxPacketsDiscardR Counter64,
		nptTunnelTxPacketsDiscardSum Counter64
		}


	nptTunnelTxIndex	OBJECT-TYPE	
		SYNTAX			Integer32  ( -2147483648 .. 2147483647  ) 
		MAX-ACCESS		read-only
		STATUS			current
		DESCRIPTION		"Index"
		::=  {  nptTunnelTxEntry  1  }

    nptTunnelTxTunnelName	OBJECT-TYPE	
		SYNTAX			DisplayString 
		MAX-ACCESS		read-only
		STATUS			current
		DESCRIPTION		"tunnel Name"
		::=  {  nptTunnelTxEntry  2  }

    nptTunnelTxTunnelType	OBJECT-TYPE	
		SYNTAX			Integer32
		MAX-ACCESS		read-only
		STATUS			current
		DESCRIPTION		"tunnel type"
		::=  {  nptTunnelTxEntry  3  }

    nptTunnelTxLSP	OBJECT-TYPE	
		SYNTAX			DisplayString 
		MAX-ACCESS		read-only
		STATUS			current
		DESCRIPTION		"LSP"
		::=  {  nptTunnelTxEntry  4  }

    nptTunnelTxDirection	OBJECT-TYPE	
		SYNTAX			DisplayString 
		MAX-ACCESS		read-only
		STATUS			current
		DESCRIPTION		"Direction"
		::=  {  nptTunnelTxEntry  5  }

    nptTunnelTxEnable	OBJECT-TYPE	
		SYNTAX			Integer32
		MAX-ACCESS		read-only
		STATUS			current
		DESCRIPTION		"Enable/Disable"
		::=  {  nptTunnelTxEntry  6  }

    nptTunnelTxLifName	OBJECT-TYPE	
		SYNTAX			DisplayString 
		MAX-ACCESS		read-only
		STATUS			current
		DESCRIPTION		"Lif Name"
		::=  {  nptTunnelTxEntry  7  }

    nptTunnelTxDisContinuityTime	OBJECT-TYPE	
		SYNTAX			DisplayString
		MAX-ACCESS		read-only
		STATUS			current
		DESCRIPTION		"DisContinuity Time"
		::=  {  nptTunnelTxEntry  8  }

    nptTunnelTxElapsed	OBJECT-TYPE	
		SYNTAX			DisplayString 
		MAX-ACCESS		read-only
		STATUS			current
		DESCRIPTION		"Elapsed time output-dd:hh:mm:ss"
		::=  {  nptTunnelTxEntry  9  }


    nptTunnelTxOctetsPassG	OBJECT-TYPE	
		SYNTAX			Counter64
		MAX-ACCESS		read-only
		STATUS			current
		DESCRIPTION		"Passed total number of green bytes transmitted from this XC out-segment"
		::=  {  nptTunnelTxEntry  10  }

    nptTunnelTxOctetsPassY	OBJECT-TYPE	
		SYNTAX			Counter64
		MAX-ACCESS		read-only
		STATUS			current
		DESCRIPTION		"Passed total number of yellow bytes transmitted from this XC out-segment"
		::=  {  nptTunnelTxEntry  11  }

    nptTunnelTxOctetsPassSum	OBJECT-TYPE	
		SYNTAX			Counter64
		MAX-ACCESS		read-only
		STATUS			current
		DESCRIPTION		"Passed total number of bytes(green+yellow) transmitted from this XC out-segment"
		::=  {  nptTunnelTxEntry  12  }

    nptTunnelTxOctetsDiscardGY	OBJECT-TYPE	
		SYNTAX			Counter64
		MAX-ACCESS		read-only
		STATUS			current
		DESCRIPTION		"Discarded total number of green or yellow bytes transmitted from this XC out-segment"
		::=  {  nptTunnelTxEntry  13  }

    nptTunnelTxOctetsDiscardR	OBJECT-TYPE	
		SYNTAX			Counter64
		MAX-ACCESS		read-only
		STATUS			current
		DESCRIPTION		"Discarded total number of red bytes transmitted from this XC out-segment"
		::=  {  nptTunnelTxEntry  14  }

    nptTunnelTxOctetsDiscardSum	OBJECT-TYPE	
		SYNTAX			Counter64
		MAX-ACCESS		read-only
		STATUS			current
		DESCRIPTION		"Discarded total number of bytes transmitted from this XC out-segment"
		::=  {  nptTunnelTxEntry  15  }

    nptTunnelTxPacketsPassG	OBJECT-TYPE	
		SYNTAX			Counter64
		MAX-ACCESS		read-only
		STATUS			current
		DESCRIPTION		"Passed total number of green packets transmitted from this XC out-segment"
		::=  {  nptTunnelTxEntry  16  }

    nptTunnelTxPacketsPassY	OBJECT-TYPE	
		SYNTAX			Counter64
		MAX-ACCESS		read-only
		STATUS			current
		DESCRIPTION		"Passed total number of yellow packets transmitted from this XC out-segment"
		::=  {  nptTunnelTxEntry  17  }

    nptTunnelTxPacketsPassSum	OBJECT-TYPE	
		SYNTAX			Counter64
		MAX-ACCESS		read-only
		STATUS			current
		DESCRIPTION		"Passed total number of packets(green+yellow) received from this XC in-segment"
		::=  {  nptTunnelTxEntry  18  }

    nptTunnelTxPacketsDiscardGY	OBJECT-TYPE	
		SYNTAX			Counter64
		MAX-ACCESS		read-only
		STATUS			current
		DESCRIPTION		"Discarded total number of green or yellow packets received from this XC in-segment"
		::=  {  nptTunnelTxEntry  19  }

    nptTunnelTxPacketsDiscardR	OBJECT-TYPE	
		SYNTAX			Counter64
		MAX-ACCESS		read-only
		STATUS			current
		DESCRIPTION		"Discarded total number of red packets received from this XC in-segment"
		::=  {  nptTunnelTxEntry  20  }

    nptTunnelTxPacketsDiscardSum	OBJECT-TYPE	
		SYNTAX			Counter64
		MAX-ACCESS		read-only
		STATUS			current
		DESCRIPTION		"Discarded total number of packets received from this XC in-segment"
		::=  {  nptTunnelTxEntry  21  }
		
	nptTunnelTxCoSTable	OBJECT-TYPE
		SYNTAX		SEQUENCE  OF  NptTunnelTxCoSEntry
		MAX-ACCESS	not-accessible
		STATUS		current
		DESCRIPTION	"nptTunnelTxCoSTable"
		::=  { nptTunnelTxCoS  1 }

	nptTunnelTxCoSEntry	OBJECT-TYPE
		SYNTAX		NptTunnelTxCoSEntry
		MAX-ACCESS	not-accessible
		STATUS		current
		DESCRIPTION	"nptTunnelTxCoSEntry"
		INDEX		{  nptTunnelTxCoSIndex  }
		::=  { nptTunnelTxCoSTable 1 }

	NptTunnelTxCoSEntry  ::=  SEQUENCE {
	    nptTunnelTxCoSIndex  Integer32,
        nptTunnelTxCoSTunnelName  DisplayString,
        nptTunnelTxCoSTunnelType  Integer32,
        nptTunnelTxCoSLSP  DisplayString,
        nptTunnelTxCoSDirection  DisplayString,
        nptTunnelTxCoSID  Integer32,
        nptTunnelTxCoSPM  Integer32,
        nptTunnelTxCoSLifName  DisplayString,
        nptTunnelTxCoSDisContinuityTime  DisplayString,
        nptTunnelTxCoSElapsed DisplayString,
		nptTunnelTxCoSOctetsPassG Counter64,
		nptTunnelTxCoSOctetsPassY Counter64,
		nptTunnelTxCoSOctetsPassSum Counter64,
		nptTunnelTxCoSOctetsDiscardGY Counter64,
		nptTunnelTxCoSOctetsDiscardR Counter64,
		nptTunnelTxCoSOctetsDiscardSum Counter64,
		nptTunnelTxCoSPacketsPassG Counter64,
		nptTunnelTxCoSPacketsPassY Counter64,
		nptTunnelTxCoSPacketsPassSum Counter64,
		nptTunnelTxCoSPacketsDiscardGY Counter64,
		nptTunnelTxCoSPacketsDiscardR Counter64,
		nptTunnelTxCoSPacketsDiscardSum Counter64
		}


	nptTunnelTxCoSIndex	OBJECT-TYPE	
		SYNTAX			Integer32  ( -2147483648 .. 2147483647  ) 
		MAX-ACCESS		read-only
		STATUS			current
		DESCRIPTION		"Index"
		::=  {  nptTunnelTxCoSEntry  1  }

    nptTunnelTxCoSTunnelName	OBJECT-TYPE	
		SYNTAX			DisplayString 
		MAX-ACCESS		read-only
		STATUS			current
		DESCRIPTION		"tunnel Name"
		::=  {  nptTunnelTxCoSEntry  2  }

    nptTunnelTxCoSTunnelType	OBJECT-TYPE	
		SYNTAX			Integer32
		MAX-ACCESS		read-only
		STATUS			current
		DESCRIPTION		"tunnel type"
		::=  {  nptTunnelTxCoSEntry  3  }

    nptTunnelTxCoSLSP	OBJECT-TYPE	
		SYNTAX			DisplayString 
		MAX-ACCESS		read-only
		STATUS			current
		DESCRIPTION		"LSP"
		::=  {  nptTunnelTxCoSEntry  4  }

    nptTunnelTxCoSDirection	OBJECT-TYPE	
		SYNTAX			DisplayString 
		MAX-ACCESS		read-only
		STATUS			current
		DESCRIPTION		"Direction"
		::=  {  nptTunnelTxCoSEntry  5  }

    nptTunnelTxCoSID	OBJECT-TYPE	
		SYNTAX			Integer32
		MAX-ACCESS		read-only
		STATUS			current
		DESCRIPTION		"CoS ID"
		::=  {  nptTunnelTxCoSEntry  6  }

    nptTunnelTxCoSPM	OBJECT-TYPE	
		SYNTAX			Integer32
		MAX-ACCESS		read-only
		STATUS			current
		DESCRIPTION		"PM"
		::=  {  nptTunnelTxCoSEntry  7  }

    nptTunnelTxCoSLifName	OBJECT-TYPE	
		SYNTAX			DisplayString 
		MAX-ACCESS		read-only
		STATUS			current
		DESCRIPTION		"Lif Name"
		::=  {  nptTunnelTxCoSEntry  8  }

    nptTunnelTxCoSDisContinuityTime	OBJECT-TYPE	
		SYNTAX			DisplayString
		MAX-ACCESS		read-only
		STATUS			current
		DESCRIPTION		"DisContinuity Time"
		::=  {  nptTunnelTxCoSEntry  9  }

    nptTunnelTxCoSElapsed	OBJECT-TYPE	
		SYNTAX			DisplayString 
		MAX-ACCESS		read-only
		STATUS			current
		DESCRIPTION		"Elapsed time output-dd:hh:mm:ss"
		::=  {  nptTunnelTxCoSEntry  10  }


    nptTunnelTxCoSOctetsPassG	OBJECT-TYPE	
		SYNTAX			Counter64
		MAX-ACCESS		read-only
		STATUS			current
		DESCRIPTION		"Passed total number of green bytes transmitted from the CoS of this XC out-segment"
		::=  {  nptTunnelTxCoSEntry  11  }

    nptTunnelTxCoSOctetsPassY	OBJECT-TYPE	
		SYNTAX			Counter64
		MAX-ACCESS		read-only
		STATUS			current
		DESCRIPTION		"Passed total number of yellow bytes transmitted from the CoS of this XC out-segment"
		::=  {  nptTunnelTxCoSEntry  12  }

    nptTunnelTxCoSOctetsPassSum	OBJECT-TYPE	
		SYNTAX			Counter64
		MAX-ACCESS		read-only
		STATUS			current
		DESCRIPTION		"Passed total number of bytes(green+yellow) transmitted from the CoS of this XC out-segment"
		::=  {  nptTunnelTxCoSEntry  13  }

    nptTunnelTxCoSOctetsDiscardGY	OBJECT-TYPE	
		SYNTAX			Counter64
		MAX-ACCESS		read-only
		STATUS			current
		DESCRIPTION		"Discarded total number of green or yellow bytes transmitted from the CoS of this XC out-segment"
		::=  {  nptTunnelTxCoSEntry  14  }

    nptTunnelTxCoSOctetsDiscardR	OBJECT-TYPE	
		SYNTAX			Counter64
		MAX-ACCESS		read-only
		STATUS			current
		DESCRIPTION		"Discarded total number of yellow or red bytes transmitted from the CoS of this XC out-segment"
		::=  {  nptTunnelTxCoSEntry  15  }

    nptTunnelTxCoSOctetsDiscardSum	OBJECT-TYPE	
		SYNTAX			Counter64
		MAX-ACCESS		read-only
		STATUS			current
		DESCRIPTION		"Discarded total number of bytes transmitted from the CoS of this XC out-segment"
		::=  {  nptTunnelTxCoSEntry  16  }

    nptTunnelTxCoSPacketsPassG	OBJECT-TYPE	
		SYNTAX			Counter64
		MAX-ACCESS		read-only
		STATUS			current
		DESCRIPTION		"Passed total number of green packets transmitted from the CoS of this XC out-segment"
		::=  {  nptTunnelTxCoSEntry  17  }

    nptTunnelTxCoSPacketsPassY	OBJECT-TYPE	
		SYNTAX			Counter64
		MAX-ACCESS		read-only
		STATUS			current
		DESCRIPTION		"Passed total number of yellow packets transmitted from the CoS of this XC out-segment"
		::=  {  nptTunnelTxCoSEntry  18  }

    nptTunnelTxCoSPacketsPassSum	OBJECT-TYPE	
		SYNTAX			Counter64
		MAX-ACCESS		read-only
		STATUS			current
		DESCRIPTION		"Passed total number of packets(green+yellow) transmitted from the CoS of this XC out-segment"
		::=  {  nptTunnelTxCoSEntry  19  }

    nptTunnelTxCoSPacketsDiscardGY	OBJECT-TYPE	
		SYNTAX			Counter64
		MAX-ACCESS		read-only
		STATUS			current
		DESCRIPTION		"Discarded total number of green or yellow packets transmitted from the CoS of this XC out-segment"
		::=  {  nptTunnelTxCoSEntry  20  }

    nptTunnelTxCoSPacketsDiscardR	OBJECT-TYPE	
		SYNTAX			Counter64
		MAX-ACCESS		read-only
		STATUS			current
		DESCRIPTION		"Discarded total number of yellow or red packets transmitted from the CoS of this XC out-segment"
		::=  {  nptTunnelTxCoSEntry  21  }

    nptTunnelTxCoSPacketsDiscardSum	OBJECT-TYPE	
		SYNTAX			Counter64
		MAX-ACCESS		read-only
		STATUS			current
		DESCRIPTION		"Discarded total number of packets transmitted from the CoS of this XC out-segment"
		::=  {  nptTunnelTxCoSEntry  22  }
		
	nptTunnelTMFBTable	OBJECT-TYPE
		SYNTAX		SEQUENCE  OF  NptTunnelTMFBEntry
		MAX-ACCESS	not-accessible
		STATUS		current
		DESCRIPTION	"Description"
		::=  { nptTunnelTMFB  1 }

	nptTunnelTMFBEntry	OBJECT-TYPE
		SYNTAX		NptTunnelTMFBEntry
		MAX-ACCESS	not-accessible
		STATUS		current
		DESCRIPTION	"Row Description"
		INDEX		{  nptTunnelTMFBIndex  }
		::=  { nptTunnelTMFBTable 1 }

	NptTunnelTMFBEntry  ::=  SEQUENCE {
	    nptTunnelTMFBIndex  Integer32,
        nptTunnelTMFBTunnelName  DisplayString,
        nptTunnelTMFBTunnelType  Integer32,
        nptTunnelTMFBLSP  DisplayString,
        nptTunnelTMFBDirection  DisplayString,
        nptTunnelTMFBDisContinuityTime  DisplayString,
        nptTunnelTMFBElapsed DisplayString,
		nptTunnelTMFBPassOctets Counter64,
		nptTunnelTMFBPassPkts Counter64,
		nptTunnelTMFBWREDDiscardOctets Counter64,
		nptTunnelTMFBWREDDiscardPkts Counter64
		}


	nptTunnelTMFBIndex	OBJECT-TYPE	
		SYNTAX			Integer32  ( -2147483648 .. 2147483647  ) 
		MAX-ACCESS		read-only
		STATUS			current
		DESCRIPTION		"Column Description"
		::=  {  nptTunnelTMFBEntry  1  }

    nptTunnelTMFBTunnelName	OBJECT-TYPE	
		SYNTAX			DisplayString 
		MAX-ACCESS		read-only
		STATUS			current
		DESCRIPTION		"tunnel Name"
		::=  {  nptTunnelTMFBEntry  2  }

    nptTunnelTMFBTunnelType	OBJECT-TYPE	
		SYNTAX			Integer32
		MAX-ACCESS		read-only
		STATUS			current
		DESCRIPTION		"tunnel type"
		::=  {  nptTunnelTMFBEntry  3  }

    nptTunnelTMFBLSP	OBJECT-TYPE	
		SYNTAX			DisplayString 
		MAX-ACCESS		read-only
		STATUS			current
		DESCRIPTION		"LSP"
		::=  {  nptTunnelTMFBEntry  4  }

    nptTunnelTMFBDirection	OBJECT-TYPE	
		SYNTAX			DisplayString 
		MAX-ACCESS		read-only
		STATUS			current
		DESCRIPTION		"Direction"
		::=  {  nptTunnelTMFBEntry  5  }

    nptTunnelTMFBDisContinuityTime	OBJECT-TYPE	
		SYNTAX			DisplayString
		MAX-ACCESS		read-only
		STATUS			current
		DESCRIPTION		"DisContinuity Time"
		::=  {  nptTunnelTMFBEntry  6  }

    nptTunnelTMFBElapsed	OBJECT-TYPE	
		SYNTAX			DisplayString 
		MAX-ACCESS		read-only
		STATUS			current
		DESCRIPTION		"dd:hh:mm:ss"
		::=  {  nptTunnelTMFBEntry  7  }


    nptTunnelTMFBPassOctets	OBJECT-TYPE	
		SYNTAX			Counter64
		MAX-ACCESS		read-only
		STATUS			current
		DESCRIPTION		"Description"
		::=  {  nptTunnelTMFBEntry  8  }

    nptTunnelTMFBPassPkts	OBJECT-TYPE	
		SYNTAX			Counter64
		MAX-ACCESS		read-only
		STATUS			current
		DESCRIPTION		"Description"
		::=  {  nptTunnelTMFBEntry  9  }

    nptTunnelTMFBWREDDiscardOctets	OBJECT-TYPE	
		SYNTAX			Counter64
		MAX-ACCESS		read-only
		STATUS			current
		DESCRIPTION		"Description"
		::=  {  nptTunnelTMFBEntry  10  }

    nptTunnelTMFBWREDDiscardPkts	OBJECT-TYPE	
		SYNTAX			Counter64
		MAX-ACCESS		read-only
		STATUS			current
		DESCRIPTION		"Description"
		::=  {  nptTunnelTMFBEntry  11  }
		
	nptSrteTunnelTable	OBJECT-TYPE
		SYNTAX		SEQUENCE  OF  NptSrteTunnelEntry
		MAX-ACCESS	not-accessible
		STATUS		current
		DESCRIPTION	"Description"
		::=  { nptSrteTunnel  1 }
        
	nptSrteTunnelEntry	OBJECT-TYPE
		SYNTAX		NptSrteTunnelEntry
		MAX-ACCESS	not-accessible
		STATUS		current
		DESCRIPTION	"Row Description"
		INDEX		{  nptSrteTunnelIndex  }
		::=  { nptSrteTunnelTable 1 }

	NptSrteTunnelEntry  ::=  SEQUENCE {
	    nptSrteTunnelIndex  Integer32,
        nptSrteTunnelTunnelName  DisplayString,
        nptSrteTunnelLspId  Integer32,
        nptSrteTunnelLspType  Integer32,
        nptSrteTunnelDiscTime  DisplayString,
        nptSrteTunnelElapsedTime  Integer32,
        nptSrteTunnelOctetsPassG  Counter64,
        nptSrteTunnelOctetsPassY  Counter64,
        nptSrteTunnelOctetsPassSum Counter64,
		nptSrteTunnelOctetsDiscardGY Counter64,
		nptSrteTunnelOctetsDiscardR Counter64,
		nptSrteTunnelOctetsDiscardSum Counter64,
		nptSrteTunnelPacketsPassG Counter64,
		nptSrteTunnelPacketsPassY Counter64,
		nptSrteTunnelPacketsPassSum Counter64,
		nptSrteTunnelPacketsDiscardGY Counter64,
		nptSrteTunnelPacketsDiscardR Counter64,
		nptSrteTunnelPacketsDiscardSum Counter64
		}


	nptSrteTunnelIndex	OBJECT-TYPE	
		SYNTAX			Integer32  ( -2147483648 .. 2147483647  ) 
		MAX-ACCESS		read-only
		STATUS			current
		DESCRIPTION		"Column Description"
		::=  {  nptSrteTunnelEntry  1  }

    nptSrteTunnelTunnelName	OBJECT-TYPE	
		SYNTAX			DisplayString 
		MAX-ACCESS		read-only
		STATUS			current
		DESCRIPTION		"tunnel Name"
		::=  {  nptSrteTunnelEntry  2  }

    nptSrteTunnelLspId	OBJECT-TYPE	
		SYNTAX			Integer32
		MAX-ACCESS		read-only
		STATUS			current
		DESCRIPTION		"tunnel type"
		::=  {  nptSrteTunnelEntry  3  }

    nptSrteTunnelLspType	OBJECT-TYPE	
		SYNTAX			Integer32 
		MAX-ACCESS		read-only
		STATUS			current
		DESCRIPTION		"LSP"
		::=  {  nptSrteTunnelEntry  4  }

    nptSrteTunnelDiscTime	OBJECT-TYPE	
		SYNTAX			DisplayString 
		MAX-ACCESS		read-only
		STATUS			current
		DESCRIPTION		"Direction"
		::=  {  nptSrteTunnelEntry  5  }

    nptSrteTunnelElapsedTime	OBJECT-TYPE	
		SYNTAX			Integer32
		MAX-ACCESS		read-only
		STATUS			current
		DESCRIPTION		"CoS ID"
		::=  {  nptSrteTunnelEntry  6  }

    nptSrteTunnelOctetsPassG	OBJECT-TYPE	
		SYNTAX			Counter64
		MAX-ACCESS		read-only
		STATUS			current
		DESCRIPTION		"PM"
		::=  {  nptSrteTunnelEntry  7  }

    nptSrteTunnelOctetsPassY	OBJECT-TYPE	
		SYNTAX			Counter64
		MAX-ACCESS		read-only
		STATUS			current
		DESCRIPTION		"DisContinuity Time"
		::=  {  nptSrteTunnelEntry  8  }

    nptSrteTunnelOctetsPassSum	OBJECT-TYPE	
		SYNTAX			Counter64 
		MAX-ACCESS		read-only
		STATUS			current
		DESCRIPTION		"dd:hh:mm:ss"
		::=  {  nptSrteTunnelEntry  9  }


    nptSrteTunnelOctetsDiscardGY	OBJECT-TYPE	
		SYNTAX			Counter64
		MAX-ACCESS		read-only
		STATUS			current
		DESCRIPTION		"Description"
		::=  {  nptSrteTunnelEntry  10  }

    nptSrteTunnelOctetsDiscardR	OBJECT-TYPE	
		SYNTAX			Counter64
		MAX-ACCESS		read-only
		STATUS			current
		DESCRIPTION		"Description"
		::=  {  nptSrteTunnelEntry  11  }

    nptSrteTunnelOctetsDiscardSum	OBJECT-TYPE	
		SYNTAX			Counter64
		MAX-ACCESS		read-only
		STATUS			current
		DESCRIPTION		"Description"
		::=  {  nptSrteTunnelEntry  12  }

    nptSrteTunnelPacketsPassG	OBJECT-TYPE	
		SYNTAX			Counter64
		MAX-ACCESS		read-only
		STATUS			current
		DESCRIPTION		"Description"
		::=  {  nptSrteTunnelEntry  13  }

    nptSrteTunnelPacketsPassY	OBJECT-TYPE	
		SYNTAX			Counter64
		MAX-ACCESS		read-only
		STATUS			current
		DESCRIPTION		"Description"
		::=  {  nptSrteTunnelEntry  14  }

    nptSrteTunnelPacketsPassSum	OBJECT-TYPE	
		SYNTAX			Counter64
		MAX-ACCESS		read-only
		STATUS			current
		DESCRIPTION		"Description"
		::=  {  nptSrteTunnelEntry  15  }

    nptSrteTunnelPacketsDiscardGY	OBJECT-TYPE	
		SYNTAX			Counter64
		MAX-ACCESS		read-only
		STATUS			current
		DESCRIPTION		"Description"
		::=  {  nptSrteTunnelEntry  16  }

    nptSrteTunnelPacketsDiscardR	OBJECT-TYPE	
		SYNTAX			Counter64
		MAX-ACCESS		read-only
		STATUS			current
		DESCRIPTION		"Description"
		::=  {  nptSrteTunnelEntry  17  }

    nptSrteTunnelPacketsDiscardSum	OBJECT-TYPE	
		SYNTAX			Counter64
		MAX-ACCESS		read-only
		STATUS			current
		DESCRIPTION		"Description"
		::=  {  nptSrteTunnelEntry  18  }

	nptBGPLUTable	OBJECT-TYPE
		SYNTAX		SEQUENCE  OF  NptBGPLUEntry
		MAX-ACCESS	not-accessible
		STATUS		current
		DESCRIPTION	"Description"
		::=  { nptBGPLU  1 }
        
	nptBGPLUEntry	OBJECT-TYPE
		SYNTAX		NptBGPLUEntry
		MAX-ACCESS	not-accessible
		STATUS		current
		DESCRIPTION	"Row Description"
		INDEX		{  nptBGPLUIndex  }
		::=  { nptBGPLUTable 1 }

	NptBGPLUEntry  ::=  SEQUENCE {
	    nptBGPLUIndex  Integer32,
        nptBGPLUFec  DisplayString,
        nptBGPLULspType  DisplayString,
        nptBGPLUDiscTime  DisplayString,
        nptBGPLUElapsedTime  DisplayString,
        nptBGPLUOctetsPassG  Counter64,
        nptBGPLUOctetsPassY  Counter64,
        nptBGPLUOctetsPassSum Counter64,
		nptBGPLUOctetsDiscardGY Counter64,
		nptBGPLUOctetsDiscardR Counter64,
		nptBGPLUOctetsDiscardSum Counter64,
		nptBGPLUPacketsPassG Counter64,
		nptBGPLUPacketsPassY Counter64,
		nptBGPLUPacketsPassSum Counter64,
		nptBGPLUPacketsDiscardGY Counter64,
		nptBGPLUPacketsDiscardR Counter64,
		nptBGPLUPacketsDiscardSum Counter64
		}


	nptBGPLUIndex	OBJECT-TYPE	
		SYNTAX			Integer32  ( -2147483648 .. 2147483647  ) 
		MAX-ACCESS		read-only
		STATUS			current
		DESCRIPTION		"Description"
		::=  {  nptBGPLUEntry  1  }

    nptBGPLUFec	OBJECT-TYPE	
		SYNTAX			DisplayString 
		MAX-ACCESS		read-only
		STATUS			current
		DESCRIPTION		"Description"
		::=  {  nptBGPLUEntry  2  }

    nptBGPLULspType	OBJECT-TYPE	
		SYNTAX			DisplayString 
		MAX-ACCESS		read-only
		STATUS			current
		DESCRIPTION		"Description"
		::=  {  nptBGPLUEntry  4  }

    nptBGPLUDiscTime	OBJECT-TYPE	
		SYNTAX			DisplayString 
		MAX-ACCESS		read-only
		STATUS			current
		DESCRIPTION		"Description"
		::=  {  nptBGPLUEntry  5  }

    nptBGPLUElapsedTime	OBJECT-TYPE	
		SYNTAX			DisplayString
		MAX-ACCESS		read-only
		STATUS			current
		DESCRIPTION		"Description"
		::=  {  nptBGPLUEntry  6  }

    nptBGPLUOctetsPassG	OBJECT-TYPE	
		SYNTAX			Counter64
		MAX-ACCESS		read-only
		STATUS			current
		DESCRIPTION		"Description"
		::=  {  nptBGPLUEntry  7  }

    nptBGPLUOctetsPassY	OBJECT-TYPE	
		SYNTAX			Counter64
		MAX-ACCESS		read-only
		STATUS			current
		DESCRIPTION		"Description"
		::=  {  nptBGPLUEntry  8  }

    nptBGPLUOctetsPassSum	OBJECT-TYPE	
		SYNTAX			Counter64 
		MAX-ACCESS		read-only
		STATUS			current
		DESCRIPTION		"Description"
		::=  {  nptBGPLUEntry  9  }


    nptBGPLUOctetsDiscardGY	OBJECT-TYPE	
		SYNTAX			Counter64
		MAX-ACCESS		read-only
		STATUS			current
		DESCRIPTION		"Description"
		::=  {  nptBGPLUEntry  10  }

    nptBGPLUOctetsDiscardR	OBJECT-TYPE	
		SYNTAX			Counter64
		MAX-ACCESS		read-only
		STATUS			current
		DESCRIPTION		"Description"
		::=  {  nptBGPLUEntry  11  }

    nptBGPLUOctetsDiscardSum	OBJECT-TYPE	
		SYNTAX			Counter64
		MAX-ACCESS		read-only
		STATUS			current
		DESCRIPTION		"Description"
		::=  {  nptBGPLUEntry  12  }

    nptBGPLUPacketsPassG	OBJECT-TYPE	
		SYNTAX			Counter64
		MAX-ACCESS		read-only
		STATUS			current
		DESCRIPTION		"Description"
		::=  {  nptBGPLUEntry  13  }

    nptBGPLUPacketsPassY	OBJECT-TYPE	
		SYNTAX			Counter64
		MAX-ACCESS		read-only
		STATUS			current
		DESCRIPTION		"Description"
		::=  {  nptBGPLUEntry  14  }

    nptBGPLUPacketsPassSum	OBJECT-TYPE	
		SYNTAX			Counter64
		MAX-ACCESS		read-only
		STATUS			current
		DESCRIPTION		"Description"
		::=  {  nptBGPLUEntry  15  }

    nptBGPLUPacketsDiscardGY	OBJECT-TYPE	
		SYNTAX			Counter64
		MAX-ACCESS		read-only
		STATUS			current
		DESCRIPTION		"Description"
		::=  {  nptBGPLUEntry  16  }

    nptBGPLUPacketsDiscardR	OBJECT-TYPE	
		SYNTAX			Counter64
		MAX-ACCESS		read-only
		STATUS			current
		DESCRIPTION		"Description"
		::=  {  nptBGPLUEntry  17  }

    nptBGPLUPacketsDiscardSum	OBJECT-TYPE	
		SYNTAX			Counter64
		MAX-ACCESS		read-only
		STATUS			current
		DESCRIPTION		"Description"
		::=  {  nptBGPLUEntry  18  }

	nptSRBETable	OBJECT-TYPE
		SYNTAX		SEQUENCE  OF  NptSRBEEntry
		MAX-ACCESS	not-accessible
		STATUS		current
		DESCRIPTION	"Description"
		::=  { nptSRBE  1 }
        
	nptSRBEEntry	OBJECT-TYPE
		SYNTAX		NptSRBEEntry
		MAX-ACCESS	not-accessible
		STATUS		current
		DESCRIPTION	"Row Description"
		INDEX		{  nptSRBEIndex  }
		::=  { nptSRBETable 1 }

	NptSRBEEntry  ::=  SEQUENCE {
	    nptSRBEIndex  Integer32,
        nptSRBEFec  DisplayString,
        nptSRBEIpv4Adj  DisplayString,
        nptSRBELspType  DisplayString,
        nptSRBEDiscTime  DisplayString,
        nptSRBEElapsedTime  DisplayString,
        nptSRBEOctetsPassG  Counter64,
        nptSRBEOctetsPassY  Counter64,
        nptSRBEOctetsPassSum Counter64,
		nptSRBEOctetsDiscardGY Counter64,
		nptSRBEOctetsDiscardR Counter64,
		nptSRBEOctetsDiscardSum Counter64,
		nptSRBEPacketsPassG Counter64,
		nptSRBEPacketsPassY Counter64,
		nptSRBEPacketsPassSum Counter64,
		nptSRBEPacketsDiscardGY Counter64,
		nptSRBEPacketsDiscardR Counter64,
		nptSRBEPacketsDiscardSum Counter64
		}


	nptSRBEIndex	OBJECT-TYPE	
		SYNTAX			Integer32  ( -2147483648 .. 2147483647  ) 
		MAX-ACCESS		read-only
		STATUS			current
		DESCRIPTION		"Description"
		::=  {  nptSRBEEntry  1  }

    nptSRBEFec	OBJECT-TYPE	
		SYNTAX			DisplayString 
		MAX-ACCESS		read-only
		STATUS			current
		DESCRIPTION		"Description"
		::=  {  nptSRBEEntry  2  }

    nptSRBEIpv4Adj	OBJECT-TYPE	
		SYNTAX			DisplayString 
		MAX-ACCESS		read-only
		STATUS			current
		DESCRIPTION		"Description"
		::=  {  nptSRBEEntry  3  }

    nptSRBELspType	OBJECT-TYPE	
		SYNTAX			DisplayString 
		MAX-ACCESS		read-only
		STATUS			current
		DESCRIPTION		"Description"
		::=  {  nptSRBEEntry  4  }

    nptSRBEDiscTime	OBJECT-TYPE	
		SYNTAX			DisplayString 
		MAX-ACCESS		read-only
		STATUS			current
		DESCRIPTION		"Description"
		::=  {  nptSRBEEntry  5  }

    nptSRBEElapsedTime	OBJECT-TYPE	
		SYNTAX			DisplayString
		MAX-ACCESS		read-only
		STATUS			current
		DESCRIPTION		"Description"
		::=  {  nptSRBEEntry  6  }

    nptSRBEOctetsPassG	OBJECT-TYPE	
		SYNTAX			Counter64
		MAX-ACCESS		read-only
		STATUS			current
		DESCRIPTION		"Description"
		::=  {  nptSRBEEntry  7  }

    nptSRBEOctetsPassY	OBJECT-TYPE	
		SYNTAX			Counter64
		MAX-ACCESS		read-only
		STATUS			current
		DESCRIPTION		"Description"
		::=  {  nptSRBEEntry  8  }

    nptSRBEOctetsPassSum	OBJECT-TYPE	
		SYNTAX			Counter64 
		MAX-ACCESS		read-only
		STATUS			current
		DESCRIPTION		"Description"
		::=  {  nptSRBEEntry  9  }


    nptSRBEOctetsDiscardGY	OBJECT-TYPE	
		SYNTAX			Counter64
		MAX-ACCESS		read-only
		STATUS			current
		DESCRIPTION		"Description"
		::=  {  nptSRBEEntry  10  }

    nptSRBEOctetsDiscardR	OBJECT-TYPE	
		SYNTAX			Counter64
		MAX-ACCESS		read-only
		STATUS			current
		DESCRIPTION		"Description"
		::=  {  nptSRBEEntry  11  }

    nptSRBEOctetsDiscardSum	OBJECT-TYPE	
		SYNTAX			Counter64
		MAX-ACCESS		read-only
		STATUS			current
		DESCRIPTION		"Description"
		::=  {  nptSRBEEntry  12  }

    nptSRBEPacketsPassG	OBJECT-TYPE	
		SYNTAX			Counter64
		MAX-ACCESS		read-only
		STATUS			current
		DESCRIPTION		"Description"
		::=  {  nptSRBEEntry  13  }

    nptSRBEPacketsPassY	OBJECT-TYPE	
		SYNTAX			Counter64
		MAX-ACCESS		read-only
		STATUS			current
		DESCRIPTION		"Description"
		::=  {  nptSRBEEntry  14  }

    nptSRBEPacketsPassSum	OBJECT-TYPE	
		SYNTAX			Counter64
		MAX-ACCESS		read-only
		STATUS			current
		DESCRIPTION		"Description"
		::=  {  nptSRBEEntry  15  }

    nptSRBEPacketsDiscardGY	OBJECT-TYPE	
		SYNTAX			Counter64
		MAX-ACCESS		read-only
		STATUS			current
		DESCRIPTION		"Description"
		::=  {  nptSRBEEntry  16  }

    nptSRBEPacketsDiscardR	OBJECT-TYPE	
		SYNTAX			Counter64
		MAX-ACCESS		read-only
		STATUS			current
		DESCRIPTION		"Description"
		::=  {  nptSRBEEntry  17  }

    nptSRBEPacketsDiscardSum	OBJECT-TYPE	
		SYNTAX			Counter64
		MAX-ACCESS		read-only
		STATUS			current
		DESCRIPTION		"Description"
		::=  {  nptSRBEEntry  18  }
        
	nptVSIRxTable	OBJECT-TYPE
		SYNTAX		SEQUENCE  OF  NptVSIRxEntry
		MAX-ACCESS	not-accessible
		STATUS		current
		DESCRIPTION	"Description"
		::=  { nptVSIRx  1 }

	nptVSIRxEntry	OBJECT-TYPE
		SYNTAX		NptVSIRxEntry
		MAX-ACCESS	not-accessible
		STATUS		current
		DESCRIPTION	"Row Description"
		INDEX		{  nptVSIRxIndex  }
		::=  { nptVSIRxTable 1 }

	NptVSIRxEntry  ::=  SEQUENCE {
	    nptVSIRxIndex  Integer32,
        nptVSIRxInstanceName  DisplayString,
        nptVSIRxMACMoveEvents  Integer32,
        nptVSIRxRxPm  Integer32,
        nptVSIRxDisContinuityTime  DisplayString,
		nptVSIRxElapsedTime  DisplayString,
		nptVSIRxOctetsPassG Counter64,
		nptVSIRxOctetsPassY Counter64,
		nptVSIRxOctetsPassSum Counter64,
		nptVSIRxOctetsDiscardGY Counter64,
		nptVSIRxOctetsDiscardR Counter64,
		nptVSIRxOctetsDiscardSum Counter64,
		nptVSIRxPacketsPassG Counter64,
		nptVSIRxPacketsPassY Counter64,
		nptVSIRxPacketsPassSum Counter64,
		nptVSIRxPacketsDiscardGY Counter64,
		nptVSIRxPacketsDiscardR Counter64,
		nptVSIRxPacketsDiscardSum Counter64
		}


	nptVSIRxIndex	OBJECT-TYPE	
		SYNTAX			Integer32  ( -2147483648 .. 2147483647  ) 
		MAX-ACCESS		read-only
		STATUS			current
		DESCRIPTION		"Column Description"
		::=  {  nptVSIRxEntry  1  }

    nptVSIRxInstanceName	OBJECT-TYPE	
		SYNTAX			DisplayString 
		MAX-ACCESS		read-only
		STATUS			current
		DESCRIPTION		"instance Name"
		::=  {  nptVSIRxEntry  2  }

    nptVSIRxMACMoveEvents	OBJECT-TYPE	
		SYNTAX			Integer32
		MAX-ACCESS		read-only
		STATUS			current
		DESCRIPTION		"MAC MoveEvents"
		::=  {  nptVSIRxEntry  3  }

    nptVSIRxRxPm	OBJECT-TYPE	
		SYNTAX			Integer32
		MAX-ACCESS		read-only
		STATUS			current
		DESCRIPTION		"PM"
		::=  {  nptVSIRxEntry  4  }

    nptVSIRxDisContinuityTime	OBJECT-TYPE	
		SYNTAX			DisplayString
		MAX-ACCESS		read-only
		STATUS			current
		DESCRIPTION		"DisContinuity Time"
		::=  {  nptVSIRxEntry  5  }
		
	nptVSIRxElapsedTime	OBJECT-TYPE	
		SYNTAX			DisplayString
		MAX-ACCESS		read-only
		STATUS			current
		DESCRIPTION		"Elapsed Time"
		::=  {  nptVSIRxEntry  6  }


    nptVSIRxOctetsPassG	OBJECT-TYPE	
		SYNTAX			Counter64
		MAX-ACCESS		read-only
		STATUS			current
		DESCRIPTION		"Description"
		::=  {  nptVSIRxEntry  7  }

    nptVSIRxOctetsPassY	OBJECT-TYPE	
		SYNTAX			Counter64
		MAX-ACCESS		read-only
		STATUS			current
		DESCRIPTION		"Description"
		::=  {  nptVSIRxEntry  8  }

    nptVSIRxOctetsPassSum	OBJECT-TYPE	
		SYNTAX			Counter64
		MAX-ACCESS		read-only
		STATUS			current
		DESCRIPTION		"Description"
		::=  {  nptVSIRxEntry  9  }

    nptVSIRxOctetsDiscardGY	OBJECT-TYPE	
		SYNTAX			Counter64
		MAX-ACCESS		read-only
		STATUS			current
		DESCRIPTION		"Description"
		::=  {  nptVSIRxEntry  10  }

    nptVSIRxOctetsDiscardR	OBJECT-TYPE	
		SYNTAX			Counter64
		MAX-ACCESS		read-only
		STATUS			current
		DESCRIPTION		"Description"
		::=  {  nptVSIRxEntry  11  }

    nptVSIRxOctetsDiscardSum	OBJECT-TYPE	
		SYNTAX			Counter64
		MAX-ACCESS		read-only
		STATUS			current
		DESCRIPTION		"Description"
		::=  {  nptVSIRxEntry  12  }

    nptVSIRxPacketsPassG	OBJECT-TYPE	
		SYNTAX			Counter64
		MAX-ACCESS		read-only
		STATUS			current
		DESCRIPTION		"Description"
		::=  {  nptVSIRxEntry  13  }

    nptVSIRxPacketsPassY	OBJECT-TYPE	
		SYNTAX			Counter64
		MAX-ACCESS		read-only
		STATUS			current
		DESCRIPTION		"Description"
		::=  {  nptVSIRxEntry  14  }

    nptVSIRxPacketsPassSum	OBJECT-TYPE	
		SYNTAX			Counter64
		MAX-ACCESS		read-only
		STATUS			current
		DESCRIPTION		"Description"
		::=  {  nptVSIRxEntry  15  }

    nptVSIRxPacketsDiscardGY	OBJECT-TYPE	
		SYNTAX			Counter64
		MAX-ACCESS		read-only
		STATUS			current
		DESCRIPTION		"Description"
		::=  {  nptVSIRxEntry  16  }

    nptVSIRxPacketsDiscardR	OBJECT-TYPE	
		SYNTAX			Counter64
		MAX-ACCESS		read-only
		STATUS			current
		DESCRIPTION		"Description"
		::=  {  nptVSIRxEntry  17  }

    nptVSIRxPacketsDiscardSum	OBJECT-TYPE	
		SYNTAX			Counter64
		MAX-ACCESS		read-only
		STATUS			current
		DESCRIPTION		"Description"
		::=  {  nptVSIRxEntry  18  }
		
	nptVSITxTable	OBJECT-TYPE
		SYNTAX		SEQUENCE  OF  NptVSITxEntry
		MAX-ACCESS	not-accessible
		STATUS		current
		DESCRIPTION	"Description"
		::=  { nptVSITx  1 }

	nptVSITxEntry	OBJECT-TYPE
		SYNTAX		NptVSITxEntry
		MAX-ACCESS	not-accessible
		STATUS		current
		DESCRIPTION	"Row Description"
		INDEX		{  nptVSITxIndex  }
		::=  { nptVSITxTable 1 }

	NptVSITxEntry  ::=  SEQUENCE {
	    nptVSITxIndex  Integer32,
        nptVSITxInstanceName  DisplayString,
        nptVSITxMACMoveEvents  Integer32,
        nptVSITxRxPm  Integer32,
        nptVSITxDisContinuityTime  DisplayString,
		nptVSITxElapsedTime  DisplayString,
		nptVSITxOctetsPassG Counter64,
		nptVSITxOctetsPassY Counter64,
		nptVSITxOctetsPassSum Counter64,
		nptVSITxPacketsPassG Counter64,
		nptVSITxPacketsPassY Counter64,
		nptVSITxPacketsPassSum Counter64
		}


	nptVSITxIndex	OBJECT-TYPE	
		SYNTAX			Integer32  ( -2147483648 .. 2147483647  ) 
		MAX-ACCESS		read-only
		STATUS			current
		DESCRIPTION		"Column Description"
		::=  {  nptVSITxEntry  1  }

    nptVSITxInstanceName	OBJECT-TYPE	
		SYNTAX			DisplayString 
		MAX-ACCESS		read-only
		STATUS			current
		DESCRIPTION		"instance Name"
		::=  {  nptVSITxEntry  2  }

    nptVSITxMACMoveEvents	OBJECT-TYPE	
		SYNTAX			Integer32
		MAX-ACCESS		read-only
		STATUS			current
		DESCRIPTION		"MAC MoveEvents"
		::=  {  nptVSITxEntry  3  }

    nptVSITxRxPm	OBJECT-TYPE	
		SYNTAX			Integer32
		MAX-ACCESS		read-only
		STATUS			current
		DESCRIPTION		"PM"
		::=  {  nptVSITxEntry  4  }

    nptVSITxDisContinuityTime	OBJECT-TYPE	
		SYNTAX			DisplayString
		MAX-ACCESS		read-only
		STATUS			current
		DESCRIPTION		"DisContinuity Time"
		::=  {  nptVSITxEntry  5  }
		
	nptVSITxElapsedTime	OBJECT-TYPE	
		SYNTAX			DisplayString
		MAX-ACCESS		read-only
		STATUS			current
		DESCRIPTION		"Elapsed Time"
		::=  {  nptVSITxEntry  6  }


    nptVSITxOctetsPassG	OBJECT-TYPE	
		SYNTAX			Counter64
		MAX-ACCESS		read-only
		STATUS			current
		DESCRIPTION		"Description"
		::=  {  nptVSITxEntry  7  }

    nptVSITxOctetsPassY	OBJECT-TYPE	
		SYNTAX			Counter64
		MAX-ACCESS		read-only
		STATUS			current
		DESCRIPTION		"Description"
		::=  {  nptVSITxEntry  8  }

    nptVSITxOctetsPassSum	OBJECT-TYPE	
		SYNTAX			Counter64
		MAX-ACCESS		read-only
		STATUS			current
		DESCRIPTION		"Description"
		::=  {  nptVSITxEntry  9  }

    nptVSITxPacketsPassG	OBJECT-TYPE	
		SYNTAX			Counter64
		MAX-ACCESS		read-only
		STATUS			current
		DESCRIPTION		"Description"
		::=  {  nptVSITxEntry  10  }

    nptVSITxPacketsPassY	OBJECT-TYPE	
		SYNTAX			Counter64
		MAX-ACCESS		read-only
		STATUS			current
		DESCRIPTION		"Description"
		::=  {  nptVSITxEntry  11  }

    nptVSITxPacketsPassSum	OBJECT-TYPE	
		SYNTAX			Counter64
		MAX-ACCESS		read-only
		STATUS			current
		DESCRIPTION		"Description"
		::=  {  nptVSITxEntry  12  }

		
	nptVSIRxCoSTable	OBJECT-TYPE
		SYNTAX		SEQUENCE  OF  NptVSIRxCoSEntry
		MAX-ACCESS	not-accessible
		STATUS		current
		DESCRIPTION	"Description"
		::=  { nptVSIRxCoS  1 }

	nptVSIRxCoSEntry	OBJECT-TYPE
		SYNTAX		NptVSIRxCoSEntry
		MAX-ACCESS	not-accessible
		STATUS		current
		DESCRIPTION	"Row Description"
		INDEX		{  nptVSIRxCoSIndex  }
		::=  { nptVSIRxCoSTable 1 }

	NptVSIRxCoSEntry  ::=  SEQUENCE {
	    nptVSIRxCoSIndex  Integer32,
        nptVSIRxCoSInstanceName  DisplayString,
        nptVSIRxCoSID  Integer32,
        nptVSIRxCoSRxPm  Integer32,
        nptVSIRxCoSDisContinuityTime  DisplayString,
		nptVSIRxCoSElapsedTime  DisplayString,
		nptVSIRxCoSOctetsPassG Counter64,
		nptVSIRxCoSOctetsPassY Counter64,
		nptVSIRxCoSOctetsPassSum Counter64,
		nptVSIRxCoSOctetsDiscardGY Counter64,
		nptVSIRxCoSOctetsDiscardR Counter64,
		nptVSIRxCoSOctetsDiscardSum Counter64,
		nptVSIRxCoSPacketsPassG Counter64,
		nptVSIRxCoSPacketsPassY Counter64,
		nptVSIRxCoSPacketsPassSum Counter64,
		nptVSIRxCoSPacketsDiscardGY Counter64,
		nptVSIRxCoSPacketsDiscardR Counter64,
		nptVSIRxCoSPacketsDiscardSum Counter64
		}


	nptVSIRxCoSIndex	OBJECT-TYPE	
		SYNTAX			Integer32  ( -2147483648 .. 2147483647  ) 
		MAX-ACCESS		read-only
		STATUS			current
		DESCRIPTION		"Column Description"
		::=  {  nptVSIRxCoSEntry  1  }

    nptVSIRxCoSInstanceName	OBJECT-TYPE	
		SYNTAX			DisplayString 
		MAX-ACCESS		read-only
		STATUS			current
		DESCRIPTION		"instance Name"
		::=  {  nptVSIRxCoSEntry  2  }

    nptVSIRxCoSID	OBJECT-TYPE	
		SYNTAX			Integer32
		MAX-ACCESS		read-only
		STATUS			current
		DESCRIPTION		"CoS ID"
		::=  {  nptVSIRxCoSEntry  3  }

    nptVSIRxCoSRxPm	OBJECT-TYPE	
		SYNTAX			Integer32
		MAX-ACCESS		read-only
		STATUS			current
		DESCRIPTION		"PM"
		::=  {  nptVSIRxCoSEntry  4  }

    nptVSIRxCoSDisContinuityTime	OBJECT-TYPE	
		SYNTAX			DisplayString
		MAX-ACCESS		read-only
		STATUS			current
		DESCRIPTION		"DisContinuity Time"
		::=  {  nptVSIRxCoSEntry  5  }
		
	nptVSIRxCoSElapsedTime	OBJECT-TYPE	
		SYNTAX			DisplayString 
		MAX-ACCESS		read-only
		STATUS			current
		DESCRIPTION		"Elapsed Time"
		::=  {  nptVSIRxCoSEntry  6  }


    nptVSIRxCoSOctetsPassG	OBJECT-TYPE	
		SYNTAX			Counter64
		MAX-ACCESS		read-only
		STATUS			current
		DESCRIPTION		"Description"
		::=  {  nptVSIRxCoSEntry  7  }

    nptVSIRxCoSOctetsPassY	OBJECT-TYPE	
		SYNTAX			Counter64
		MAX-ACCESS		read-only
		STATUS			current
		DESCRIPTION		"Description"
		::=  {  nptVSIRxCoSEntry  8  }

    nptVSIRxCoSOctetsPassSum	OBJECT-TYPE	
		SYNTAX			Counter64
		MAX-ACCESS		read-only
		STATUS			current
		DESCRIPTION		"Description"
		::=  {  nptVSIRxCoSEntry  9  }

    nptVSIRxCoSOctetsDiscardGY	OBJECT-TYPE	
		SYNTAX			Counter64
		MAX-ACCESS		read-only
		STATUS			current
		DESCRIPTION		"Description"
		::=  {  nptVSIRxCoSEntry  10  }

    nptVSIRxCoSOctetsDiscardR	OBJECT-TYPE	
		SYNTAX			Counter64
		MAX-ACCESS		read-only
		STATUS			current
		DESCRIPTION		"Description"
		::=  {  nptVSIRxCoSEntry  11  }

    nptVSIRxCoSOctetsDiscardSum	OBJECT-TYPE	
		SYNTAX			Counter64
		MAX-ACCESS		read-only
		STATUS			current
		DESCRIPTION		"Description"
		::=  {  nptVSIRxCoSEntry  12  }

    nptVSIRxCoSPacketsPassG	OBJECT-TYPE	
		SYNTAX			Counter64
		MAX-ACCESS		read-only
		STATUS			current
		DESCRIPTION		"Description"
		::=  {  nptVSIRxCoSEntry  13  }

    nptVSIRxCoSPacketsPassY	OBJECT-TYPE	
		SYNTAX			Counter64
		MAX-ACCESS		read-only
		STATUS			current
		DESCRIPTION		"Description"
		::=  {  nptVSIRxCoSEntry  14  }

    nptVSIRxCoSPacketsPassSum	OBJECT-TYPE	
		SYNTAX			Counter64
		MAX-ACCESS		read-only
		STATUS			current
		DESCRIPTION		"Description"
		::=  {  nptVSIRxCoSEntry  15  }

    nptVSIRxCoSPacketsDiscardGY	OBJECT-TYPE	
		SYNTAX			Counter64
		MAX-ACCESS		read-only
		STATUS			current
		DESCRIPTION		"Description"
		::=  {  nptVSIRxCoSEntry  16  }

    nptVSIRxCoSPacketsDiscardR	OBJECT-TYPE	
		SYNTAX			Counter64
		MAX-ACCESS		read-only
		STATUS			current
		DESCRIPTION		"Description"
		::=  {  nptVSIRxCoSEntry  17  }

    nptVSIRxCoSPacketsDiscardSum	OBJECT-TYPE	
		SYNTAX			Counter64
		MAX-ACCESS		read-only
		STATUS			current
		DESCRIPTION		"Description"
		::=  {  nptVSIRxCoSEntry  18  }
		
	nptVSITxCoSTable	OBJECT-TYPE
		SYNTAX		SEQUENCE  OF  NptVSITxCoSEntry
		MAX-ACCESS	not-accessible
		STATUS		current
		DESCRIPTION	"Description"
		::=  { nptVSITxCoS  1 }

	nptVSITxCoSEntry	OBJECT-TYPE
		SYNTAX		NptVSITxCoSEntry
		MAX-ACCESS	not-accessible
		STATUS		current
		DESCRIPTION	"Row Description"
		INDEX		{  nptVSITxCoSIndex  }
		::=  { nptVSITxCoSTable 1 }

	NptVSITxCoSEntry  ::=  SEQUENCE {
	    nptVSITxCoSIndex  Integer32,
        nptVSITxCoSInstanceName  DisplayString,
        nptVSITxCoSID  Integer32,
        nptVSITxCoSRxPm  Integer32,
        nptVSITxCoSDisContinuityTime  DisplayString,
		nptVSITxCoSElapsedTime  DisplayString,
		nptVSITxCoSOctetsPassG Counter64,
		nptVSITxCoSOctetsPassY Counter64,
		nptVSITxCoSOctetsPassSum Counter64,
		nptVSITxCoSPacketsPassG Counter64,
		nptVSITxCoSPacketsPassY Counter64,
		nptVSITxCoSPacketsPassSum Counter64
		}


	nptVSITxCoSIndex	OBJECT-TYPE	
		SYNTAX			Integer32  ( -2147483648 .. 2147483647  ) 
		MAX-ACCESS		read-only
		STATUS			current
		DESCRIPTION		"Column Description"
		::=  {  nptVSITxCoSEntry  1  }

    nptVSITxCoSInstanceName	OBJECT-TYPE	
		SYNTAX			DisplayString 
		MAX-ACCESS		read-only
		STATUS			current
		DESCRIPTION		"instance Name"
		::=  {  nptVSITxCoSEntry  2  }

    nptVSITxCoSID	OBJECT-TYPE	
		SYNTAX			Integer32
		MAX-ACCESS		read-only
		STATUS			current
		DESCRIPTION		"CoS ID"
		::=  {  nptVSITxCoSEntry  3  }

    nptVSITxCoSRxPm	OBJECT-TYPE	
		SYNTAX			Integer32
		MAX-ACCESS		read-only
		STATUS			current
		DESCRIPTION		"PM"
		::=  {  nptVSITxCoSEntry  4  }

    nptVSITxCoSDisContinuityTime	OBJECT-TYPE	
		SYNTAX			DisplayString
		MAX-ACCESS		read-only
		STATUS			current
		DESCRIPTION		"DisContinuity Time"
		::=  {  nptVSITxCoSEntry  5  }
		
	nptVSITxCoSElapsedTime	OBJECT-TYPE	
		SYNTAX			DisplayString 
		MAX-ACCESS		read-only
		STATUS			current
		DESCRIPTION		"Elapsed Time"
		::=  {  nptVSITxCoSEntry  6  }


    nptVSITxCoSOctetsPassG	OBJECT-TYPE	
		SYNTAX			Counter64
		MAX-ACCESS		read-only
		STATUS			current
		DESCRIPTION		"Description"
		::=  {  nptVSITxCoSEntry  7  }

    nptVSITxCoSOctetsPassY	OBJECT-TYPE	
		SYNTAX			Counter64
		MAX-ACCESS		read-only
		STATUS			current
		DESCRIPTION		"Description"
		::=  {  nptVSITxCoSEntry  8  }

    nptVSITxCoSOctetsPassSum	OBJECT-TYPE	
		SYNTAX			Counter64
		MAX-ACCESS		read-only
		STATUS			current
		DESCRIPTION		"Description"
		::=  {  nptVSITxCoSEntry  9  }

    nptVSITxCoSPacketsPassG	OBJECT-TYPE	
		SYNTAX			Counter64
		MAX-ACCESS		read-only
		STATUS			current
		DESCRIPTION		"Description"
		::=  {  nptVSITxCoSEntry  10  }

    nptVSITxCoSPacketsPassY	OBJECT-TYPE	
		SYNTAX			Counter64
		MAX-ACCESS		read-only
		STATUS			current
		DESCRIPTION		"Description"
		::=  {  nptVSITxCoSEntry  11  }

    nptVSITxCoSPacketsPassSum	OBJECT-TYPE	
		SYNTAX			Counter64
		MAX-ACCESS		read-only
		STATUS			current
		DESCRIPTION		"Description"
		::=  {  nptVSITxCoSEntry  12  }
		
	nptSwitchRouterTable	OBJECT-TYPE
		SYNTAX		SEQUENCE  OF  NptSwitchRouterEntry
		MAX-ACCESS	not-accessible
		STATUS		current
		DESCRIPTION	"Description"
		::=  { nptSwitchRouter  1 }

	nptSwitchRouterEntry	OBJECT-TYPE
		SYNTAX		NptSwitchRouterEntry
		MAX-ACCESS	not-accessible
		STATUS		current
		DESCRIPTION	"Row Description"
		INDEX		{  nptSwitchRouterIndex  }
		::=  { nptSwitchRouterTable 1 }

	NptSwitchRouterEntry  ::=  SEQUENCE {
	    nptSwitchRouterIndex  Integer32,
        nptSwitchRouterDisContinuityTime  Integer32,
		nptSwitchRouterElapsedTime  DisplayString,
		nptSwitchRouterMstpTopologyChanges Counter64,
		nptSwitchRouterMclagUnknownRgPktsRx Counter64,
		nptSwitchRouterSoamPmFramesDiscardedByNpu Counter64,
		nptSwitchRouterInvalidDmmDiscarded Counter64,
		nptSwitchRouterInvalidDmrDiscarded Counter64,
		nptSwitchRouterInvalidSlmDiscarded Counter64,
		nptSwitchRouterInvalidSlrDiscarded Counter64,
		nptSwitchRouterRxFilterL2RapsWithMyMacSa Counter64,
		nptSwitchRouterRxFilterL2L2cp Counter64,
		nptSwitchRouterRxFilterL2FormatError Counter64,
		nptSwitchRouterRxFilterL2IllegalFormat Counter64,
		nptSwitchRouterRxFilterL2BridgeFiltering Counter64,
		nptSwitchRouterRxFilterL2802dot1xFiltering Counter64,
		nptSwitchRouterRxFilterL2IngressVlanFiltering Counter64,
		nptSwitchRouterRxFilterL2XstpStateFiltering Counter64,
		nptSwitchRouterRxFilterL2EgressShgFiltering Counter64,
		nptSwitchRouterRxFilterIgmpAwareMcNotFound Counter64,
		nptSwitchRouterRxFilterIgmpAwareMcFromIllegalDirection Counter64,
		nptSwitchRouterRxFilterIgmpAwareIGMPfromIllegalDirection Counter64,
		nptSwitchRouterRxFilterIgmpAwareMC Counter64,
		nptSwitchRouterRxFilterIpv4FormatError Counter64,
		nptSwitchRouterRxFilterIpv4UrpfFailure Counter64,
		nptSwitchRouterRxFilterIpv4LinkLocalDip Counter64,
		nptSwitchRouterRxFilterMplsDisabled Counter64,
		nptSwitchRouterRxFilterMplsHeaderError Counter64,
		nptSwitchRouterRxFilterMplsLabelNotFound Counter64,
		nptSwitchRouterRxFilterDiscardAction Counter64,
		nptSwitchRouterTotalRxFilter Counter64
		}


	nptSwitchRouterIndex	OBJECT-TYPE	
		SYNTAX			Integer32  ( -2147483648 .. 2147483647  ) 
		MAX-ACCESS		read-only
		STATUS			current
		DESCRIPTION		"Column Description"
		::=  {  nptSwitchRouterEntry  1  }


    nptSwitchRouterDisContinuityTime	OBJECT-TYPE	
		SYNTAX			Integer32
		MAX-ACCESS		read-only
		STATUS			current
		DESCRIPTION		"DisContinuity Time"
		::=  {  nptSwitchRouterEntry  2  }
		
	nptSwitchRouterElapsedTime	OBJECT-TYPE	
		SYNTAX			DisplayString
		MAX-ACCESS		read-only
		STATUS			current
		DESCRIPTION		"Elapsed Time"
		::=  {  nptSwitchRouterEntry  3  }


    nptSwitchRouterMstpTopologyChanges	OBJECT-TYPE	
		SYNTAX			Counter64
		MAX-ACCESS		read-only
		STATUS			current
		DESCRIPTION		"Description"
		::=  {  nptSwitchRouterEntry  4  }

    nptSwitchRouterMclagUnknownRgPktsRx	OBJECT-TYPE	
		SYNTAX			Counter64
		MAX-ACCESS		read-only
		STATUS			current
		DESCRIPTION		"Description"
		::=  {  nptSwitchRouterEntry  5  }

    nptSwitchRouterSoamPmFramesDiscardedByNpu	OBJECT-TYPE	
		SYNTAX			Counter64
		MAX-ACCESS		read-only
		STATUS			current
		DESCRIPTION		"Description"
		::=  {  nptSwitchRouterEntry  6  }

    nptSwitchRouterInvalidDmmDiscarded	OBJECT-TYPE	
		SYNTAX			Counter64
		MAX-ACCESS		read-only
		STATUS			current
		DESCRIPTION		"Description"
		::=  {  nptSwitchRouterEntry  7  }

    nptSwitchRouterInvalidDmrDiscarded	OBJECT-TYPE	
		SYNTAX			Counter64
		MAX-ACCESS		read-only
		STATUS			current
		DESCRIPTION		"Description"
		::=  {  nptSwitchRouterEntry  8  }

    nptSwitchRouterInvalidSlmDiscarded	OBJECT-TYPE	
		SYNTAX			Counter64
		MAX-ACCESS		read-only
		STATUS			current
		DESCRIPTION		"Description"
		::=  {  nptSwitchRouterEntry  9  }

    nptSwitchRouterInvalidSlrDiscarded	OBJECT-TYPE	
		SYNTAX			Counter64
		MAX-ACCESS		read-only
		STATUS			current
		DESCRIPTION		"Description"
		::=  {  nptSwitchRouterEntry  10  }

    nptSwitchRouterRxFilterL2RapsWithMyMacSa	OBJECT-TYPE	
		SYNTAX			Counter64
		MAX-ACCESS		read-only
		STATUS			current
		DESCRIPTION		"Description"
		::=  {  nptSwitchRouterEntry  11  }

    nptSwitchRouterRxFilterL2L2cp	OBJECT-TYPE	
		SYNTAX			Counter64
		MAX-ACCESS		read-only
		STATUS			current
		DESCRIPTION		"Description"
		::=  {  nptSwitchRouterEntry  12  }

    nptSwitchRouterRxFilterL2FormatError	OBJECT-TYPE	
		SYNTAX			Counter64
		MAX-ACCESS		read-only
		STATUS			current
		DESCRIPTION		"Description"
		::=  {  nptSwitchRouterEntry  13  }

    nptSwitchRouterRxFilterL2IllegalFormat	OBJECT-TYPE	
		SYNTAX			Counter64
		MAX-ACCESS		read-only
		STATUS			current
		DESCRIPTION		"Description"
		::=  {  nptSwitchRouterEntry  14  }

    nptSwitchRouterRxFilterL2BridgeFiltering	OBJECT-TYPE	
		SYNTAX			Counter64
		MAX-ACCESS		read-only
		STATUS			current
		DESCRIPTION		"Description"
		::=  {  nptSwitchRouterEntry  15  }

    nptSwitchRouterRxFilterL2802dot1xFiltering	OBJECT-TYPE	
		SYNTAX			Counter64
		MAX-ACCESS		read-only
		STATUS			current
		DESCRIPTION		"Description"
		::=  {  nptSwitchRouterEntry  16  }

    nptSwitchRouterRxFilterL2IngressVlanFiltering	OBJECT-TYPE	
		SYNTAX			Counter64
		MAX-ACCESS		read-only
		STATUS			current
		DESCRIPTION		"Description"
		::=  {  nptSwitchRouterEntry  17  }

    nptSwitchRouterRxFilterL2XstpStateFiltering	OBJECT-TYPE	
		SYNTAX			Counter64
		MAX-ACCESS		read-only
		STATUS			current
		DESCRIPTION		"Description"
		::=  {  nptSwitchRouterEntry  18  }

    nptSwitchRouterRxFilterL2EgressShgFiltering	OBJECT-TYPE	
		SYNTAX			Counter64
		MAX-ACCESS		read-only
		STATUS			current
		DESCRIPTION		"Description"
		::=  {  nptSwitchRouterEntry  19  }

    nptSwitchRouterRxFilterIgmpAwareMcNotFound	OBJECT-TYPE	
		SYNTAX			Counter64
		MAX-ACCESS		read-only
		STATUS			current
		DESCRIPTION		"Description"
		::=  {  nptSwitchRouterEntry  20  }

    nptSwitchRouterRxFilterIgmpAwareMcFromIllegalDirection	OBJECT-TYPE	
		SYNTAX			Counter64
		MAX-ACCESS		read-only
		STATUS			current
		DESCRIPTION		"Description"
		::=  {  nptSwitchRouterEntry  21  }

    nptSwitchRouterRxFilterIgmpAwareIGMPfromIllegalDirection	OBJECT-TYPE	
		SYNTAX			Counter64
		MAX-ACCESS		read-only
		STATUS			current
		DESCRIPTION		"Description"
		::=  {  nptSwitchRouterEntry  22  }

    nptSwitchRouterRxFilterIgmpAwareMC	OBJECT-TYPE	
		SYNTAX			Counter64
		MAX-ACCESS		read-only
		STATUS			current
		DESCRIPTION		"Description"
		::=  {  nptSwitchRouterEntry  23  }

    nptSwitchRouterRxFilterIpv4FormatError	OBJECT-TYPE	
		SYNTAX			Counter64
		MAX-ACCESS		read-only
		STATUS			current
		DESCRIPTION		"Description"
		::=  {  nptSwitchRouterEntry  24  }

    nptSwitchRouterRxFilterIpv4UrpfFailure	OBJECT-TYPE	
		SYNTAX			Counter64
		MAX-ACCESS		read-only
		STATUS			current
		DESCRIPTION		"Description"
		::=  {  nptSwitchRouterEntry  25  }

    nptSwitchRouterRxFilterIpv4LinkLocalDip	OBJECT-TYPE	
		SYNTAX			Counter64
		MAX-ACCESS		read-only
		STATUS			current
		DESCRIPTION		"Description"
		::=  {  nptSwitchRouterEntry  26  }

    nptSwitchRouterRxFilterMplsDisabled	OBJECT-TYPE	
		SYNTAX			Counter64
		MAX-ACCESS		read-only
		STATUS			current
		DESCRIPTION		"Description"
		::=  {  nptSwitchRouterEntry  27  }

    nptSwitchRouterRxFilterMplsHeaderError	OBJECT-TYPE	
		SYNTAX			Counter64
		MAX-ACCESS		read-only
		STATUS			current
		DESCRIPTION		"Description"
		::=  {  nptSwitchRouterEntry  28  }

    nptSwitchRouterRxFilterMplsLabelNotFound	OBJECT-TYPE	
		SYNTAX			Counter64
		MAX-ACCESS		read-only
		STATUS			current
		DESCRIPTION		"Description"
		::=  {  nptSwitchRouterEntry  29  }

    nptSwitchRouterRxFilterDiscardAction	OBJECT-TYPE	
		SYNTAX			Counter64
		MAX-ACCESS		read-only
		STATUS			current
		DESCRIPTION		"Description"
		::=  {  nptSwitchRouterEntry  30  }

    
    nptSwitchRouterTotalRxFilter	OBJECT-TYPE	
		SYNTAX			Counter64
		MAX-ACCESS		read-only
		STATUS			current
		DESCRIPTION		"Description"
		::=  {  nptSwitchRouterEntry  31  }
		


    nptSwitchInstanceTable	OBJECT-TYPE
		SYNTAX		SEQUENCE  OF  NptSwitchInstanceEntry
		MAX-ACCESS	not-accessible
		STATUS		current
		DESCRIPTION	"Description"
		::=  { nptSwitchInstance  1 }

	nptSwitchInstanceEntry	OBJECT-TYPE
		SYNTAX		NptSwitchInstanceEntry
		MAX-ACCESS	not-accessible
		STATUS		current
		DESCRIPTION	"Row Description"
		INDEX		{  nptSwitchInstanceIndex  }
		::=  { nptSwitchInstanceTable 1 }

	NptSwitchInstanceEntry  ::=  SEQUENCE {
        nptSwitchInstanceIndex  Integer32,
        nptSwitchInstanceInstanceName  DisplayString,
		nptSwitchInstanceRemoteTPE  DisplayString,
		nptSwitchInstancePeer  DisplayString,
		nptSwitchInstancePath  DisplayString,
        nptSwitchInstanceElapsed DisplayString,
		nptSwitchInstanceDisContinuityTime  DisplayString,
        nptSwitchInstanceTrapTxStatusMessages Integer32,
    	nptSwitchInstanceTrapRxStatusMessages Integer32,
    	nptSwitchInstanceTrapRxInvalidStatusMessage Integer32
		}


	nptSwitchInstanceIndex	OBJECT-TYPE	
		SYNTAX			Integer32  ( -2147483648 .. 2147483647  ) 
		MAX-ACCESS		read-only
		STATUS			current
		DESCRIPTION		"Column Description"
		::=  {  nptSwitchInstanceEntry  1  }


    nptSwitchInstanceInstanceName	OBJECT-TYPE	
		SYNTAX			DisplayString 
		MAX-ACCESS		read-only
		STATUS			current
		DESCRIPTION		"InstanceName"
		::=  {  nptSwitchInstanceEntry  2  }

    nptSwitchInstanceRemoteTPE	OBJECT-TYPE	
		SYNTAX			DisplayString
		MAX-ACCESS		read-only
		STATUS			current
		DESCRIPTION		"description"
		::=  {  nptSwitchInstanceEntry  3  }
		
	nptSwitchInstancePeer	OBJECT-TYPE	
		SYNTAX			DisplayString
		MAX-ACCESS		read-only
		STATUS			current
		DESCRIPTION		"description"
		::=  {  nptSwitchInstanceEntry  4  }
		
	nptSwitchInstancePath	OBJECT-TYPE	
		SYNTAX			DisplayString
		MAX-ACCESS		read-only
		STATUS			current
		DESCRIPTION		"description"
		::=  {  nptSwitchInstanceEntry  5  }

    nptSwitchInstanceElapsed	OBJECT-TYPE	
		SYNTAX			DisplayString
		MAX-ACCESS		read-only
		STATUS			current
		DESCRIPTION		"description"
		::=  {  nptSwitchInstanceEntry  6  }

	nptSwitchInstanceDisContinuityTime	OBJECT-TYPE	
		SYNTAX			DisplayString
		MAX-ACCESS		read-only
		STATUS			current
		DESCRIPTION		"description"
		::=  {  nptSwitchInstanceEntry  7  }

    nptSwitchInstanceTrapTxStatusMessages	OBJECT-TYPE	
		SYNTAX			Integer32
		MAX-ACCESS		read-only
		STATUS			current
		DESCRIPTION		"description"
		::=  {  nptSwitchInstanceEntry  8  }

    nptSwitchInstanceTrapRxStatusMessages	OBJECT-TYPE	
		SYNTAX			Integer32
		MAX-ACCESS		read-only
		STATUS			current
		DESCRIPTION		"description"
		::=  {  nptSwitchInstanceEntry  9  }

    nptSwitchInstanceTrapRxInvalidStatusMessage	OBJECT-TYPE	
		SYNTAX			Integer32
		MAX-ACCESS		read-only
		STATUS			current
		DESCRIPTION		"description"
		::=  {  nptSwitchInstanceEntry  10  }
		
	nptSwitchInstanceRxTable	OBJECT-TYPE
		SYNTAX		SEQUENCE  OF  NptSwitchInstanceRxEntry
		MAX-ACCESS	not-accessible
		STATUS		current
		DESCRIPTION	"Description"
		::=  { nptSwitchInstanceRx  1 }

	nptSwitchInstanceRxEntry	OBJECT-TYPE
		SYNTAX		NptSwitchInstanceRxEntry
		MAX-ACCESS	not-accessible
		STATUS		current
		DESCRIPTION	"Row Description"
		INDEX		{  nptSwitchInstanceRxIndex  }
		::=  { nptSwitchInstanceRxTable 1 }

	NptSwitchInstanceRxEntry  ::=  SEQUENCE {
	    nptSwitchInstanceRxIndex  Integer32,
        nptSwitchInstanceRxInstanceName  DisplayString,
        nptSwitchInstanceRxRemoteTPE  DisplayString,
		nptSwitchInstanceRxPeer  DisplayString,
		nptSwitchInstanceRxPath  DisplayString,
        nptSwitchInstanceRxPm  Integer32,
        nptSwitchInstanceRxDisContinuityTime  Integer32,
        nptSwitchInstanceRxElapsed DisplayString,
		nptSwitchInstanceRxOctetsPassG Counter64,
		nptSwitchInstanceRxOctetsPassY Counter64,
		nptSwitchInstanceRxOctetsPassSum Counter64,
		nptSwitchInstanceRxOctetsDiscardGY Counter64,
		nptSwitchInstanceRxOctetsDiscardR Counter64,
		nptSwitchInstanceRxOctetsDiscardSum Counter64,
		nptSwitchInstanceRxPacketsPassG Counter64,
		nptSwitchInstanceRxPacketsPassY Counter64,
		nptSwitchInstanceRxPacketsPassSum Counter64,
		nptSwitchInstanceRxPacketsDiscardGY Counter64,
		nptSwitchInstanceRxPacketsDiscardR Counter64,
		nptSwitchInstanceRxPacketsDiscardSum Counter64
		}


	nptSwitchInstanceRxIndex	OBJECT-TYPE	
		SYNTAX			Integer32  ( -2147483648 .. 2147483647  ) 
		MAX-ACCESS		read-only
		STATUS			current
		DESCRIPTION		"Column Description"
		::=  {  nptSwitchInstanceRxEntry  1  }

    nptSwitchInstanceRxInstanceName	OBJECT-TYPE	
		SYNTAX			DisplayString 
		MAX-ACCESS		read-only
		STATUS			current
		DESCRIPTION		"InstanceName"
		::=  {  nptSwitchInstanceRxEntry  2  }

    nptSwitchInstanceRxRemoteTPE	OBJECT-TYPE	
		SYNTAX			DisplayString 
		MAX-ACCESS		read-only
		STATUS			current
		DESCRIPTION		"Remote TPE"
		::=  {  nptSwitchInstanceRxEntry  3  }
		
	nptSwitchInstanceRxPeer	OBJECT-TYPE	
		SYNTAX			DisplayString 
		MAX-ACCESS		read-only
		STATUS			current
		DESCRIPTION		"Remote TPE"
		::=  {  nptSwitchInstanceRxEntry  4  }
		
	nptSwitchInstanceRxPath	OBJECT-TYPE	
		SYNTAX			DisplayString 
		MAX-ACCESS		read-only
		STATUS			current
		DESCRIPTION		"Remote TPE"
		::=  {  nptSwitchInstanceRxEntry  5  }

    nptSwitchInstanceRxPm	OBJECT-TYPE	
		SYNTAX			Integer32
		MAX-ACCESS		read-only
		STATUS			current
		DESCRIPTION		"PM"
		::=  {  nptSwitchInstanceRxEntry  6  }

    nptSwitchInstanceRxDisContinuityTime	OBJECT-TYPE	
		SYNTAX			Integer32
		MAX-ACCESS		read-only
		STATUS			current
		DESCRIPTION		"DisContinuity Time"
		::=  {  nptSwitchInstanceRxEntry  7  }

    nptSwitchInstanceRxElapsed	OBJECT-TYPE	
		SYNTAX			DisplayString
		MAX-ACCESS		read-only
		STATUS			current
		DESCRIPTION		"Elapsed"
		::=  {  nptSwitchInstanceRxEntry  8  }


    nptSwitchInstanceRxOctetsPassG	OBJECT-TYPE	
		SYNTAX			Counter64
		MAX-ACCESS		read-only
		STATUS			current
		DESCRIPTION		"Description"
		::=  {  nptSwitchInstanceRxEntry  9  }

    nptSwitchInstanceRxOctetsPassY	OBJECT-TYPE	
		SYNTAX			Counter64
		MAX-ACCESS		read-only
		STATUS			current
		DESCRIPTION		"Description"
		::=  {  nptSwitchInstanceRxEntry  10  }

    nptSwitchInstanceRxOctetsPassSum	OBJECT-TYPE	
		SYNTAX			Counter64
		MAX-ACCESS		read-only
		STATUS			current
		DESCRIPTION		"Description"
		::=  {  nptSwitchInstanceRxEntry  11  }

    nptSwitchInstanceRxOctetsDiscardGY	OBJECT-TYPE	
		SYNTAX			Counter64
		MAX-ACCESS		read-only
		STATUS			current
		DESCRIPTION		"Description"
		::=  {  nptSwitchInstanceRxEntry  12  }

    nptSwitchInstanceRxOctetsDiscardR	OBJECT-TYPE	
		SYNTAX			Counter64
		MAX-ACCESS		read-only
		STATUS			current
		DESCRIPTION		"Description"
		::=  {  nptSwitchInstanceRxEntry  13  }

    nptSwitchInstanceRxOctetsDiscardSum	OBJECT-TYPE	
		SYNTAX			Counter64
		MAX-ACCESS		read-only
		STATUS			current
		DESCRIPTION		"Description"
		::=  {  nptSwitchInstanceRxEntry  14  }

    nptSwitchInstanceRxPacketsPassG	OBJECT-TYPE	
		SYNTAX			Counter64
		MAX-ACCESS		read-only
		STATUS			current
		DESCRIPTION		"Description"
		::=  {  nptSwitchInstanceRxEntry  15  }

    nptSwitchInstanceRxPacketsPassY	OBJECT-TYPE	
		SYNTAX			Counter64
		MAX-ACCESS		read-only
		STATUS			current
		DESCRIPTION		"Description"
		::=  {  nptSwitchInstanceRxEntry  16  }

    nptSwitchInstanceRxPacketsPassSum	OBJECT-TYPE	
		SYNTAX			Counter64
		MAX-ACCESS		read-only
		STATUS			current
		DESCRIPTION		"Description"
		::=  {  nptSwitchInstanceRxEntry  17  }

    nptSwitchInstanceRxPacketsDiscardGY	OBJECT-TYPE	
		SYNTAX			Counter64
		MAX-ACCESS		read-only
		STATUS			current
		DESCRIPTION		"Description"
		::=  {  nptSwitchInstanceRxEntry  18  }

    nptSwitchInstanceRxPacketsDiscardR	OBJECT-TYPE	
		SYNTAX			Counter64
		MAX-ACCESS		read-only
		STATUS			current
		DESCRIPTION		"Description"
		::=  {  nptSwitchInstanceRxEntry  19  }

    nptSwitchInstanceRxPacketsDiscardSum	OBJECT-TYPE	
		SYNTAX			Counter64
		MAX-ACCESS		read-only
		STATUS			current
		DESCRIPTION		"Description"
		::=  {  nptSwitchInstanceRxEntry  20  }

	nptSwitchInstanceTxTable	OBJECT-TYPE
		SYNTAX		SEQUENCE  OF  NptSwitchInstanceTxEntry
		MAX-ACCESS	not-accessible
		STATUS		current
		DESCRIPTION	"Description"
		::=  { nptSwitchInstanceTx  1 }

	nptSwitchInstanceTxEntry	OBJECT-TYPE
		SYNTAX		NptSwitchInstanceTxEntry
		MAX-ACCESS	not-accessible
		STATUS		current
		DESCRIPTION	"Row Description"
		INDEX		{  nptSwitchInstanceTxIndex  }
		::=  { nptSwitchInstanceTxTable 1 }

	NptSwitchInstanceTxEntry  ::=  SEQUENCE {
	    nptSwitchInstanceTxIndex  Integer32,
        nptSwitchInstanceTxInstanceName  DisplayString,
        nptSwitchInstanceTxRemoteTPE  DisplayString,
		nptSwitchInstanceTxPeer  DisplayString,
		nptSwitchInstanceTxPath  DisplayString,
        nptSwitchInstanceTxPm  Integer32,
        nptSwitchInstanceTxDisContinuityTime  DisplayString,
        nptSwitchInstanceTxElapsed DisplayString,
		nptSwitchInstanceTxOctetsPassG Counter64,
		nptSwitchInstanceTxOctetsPassY Counter64,
		nptSwitchInstanceTxOctetsPassSum Counter64,
		nptSwitchInstanceTxOctetsDiscardGY Counter64,
		nptSwitchInstanceTxOctetsDiscardR Counter64,
		nptSwitchInstanceTxOctetsDiscardSum Counter64,
		nptSwitchInstanceTxPacketsPassG Counter64,
		nptSwitchInstanceTxPacketsPassY Counter64,
		nptSwitchInstanceTxPacketsPassSum Counter64,
		nptSwitchInstanceTxPacketsDiscardGY Counter64,
		nptSwitchInstanceTxPacketsDiscardR Counter64,
		nptSwitchInstanceTxPacketsDiscardSum Counter64
		}


	nptSwitchInstanceTxIndex	OBJECT-TYPE	
		SYNTAX			Integer32  ( -2147483648 .. 2147483647  ) 
		MAX-ACCESS		read-only
		STATUS			current
		DESCRIPTION		"Column Description"
		::=  {  nptSwitchInstanceTxEntry  1  }

    nptSwitchInstanceTxInstanceName	OBJECT-TYPE	
		SYNTAX			DisplayString 
		MAX-ACCESS		read-only
		STATUS			current
		DESCRIPTION		"InstanceName"
		::=  {  nptSwitchInstanceTxEntry  2  }

    nptSwitchInstanceTxRemoteTPE	OBJECT-TYPE	
		SYNTAX			DisplayString 
		MAX-ACCESS		read-only
		STATUS			current
		DESCRIPTION		"Remote TPE"
		::=  {  nptSwitchInstanceTxEntry  3  }
		
	nptSwitchInstanceTxPeer	OBJECT-TYPE	
		SYNTAX			DisplayString 
		MAX-ACCESS		read-only
		STATUS			current
		DESCRIPTION		"Remote TPE"
		::=  {  nptSwitchInstanceTxEntry  4  }
		
	nptSwitchInstanceTxPath	OBJECT-TYPE	
		SYNTAX			DisplayString 
		MAX-ACCESS		read-only
		STATUS			current
		DESCRIPTION		"Remote TPE"
		::=  {  nptSwitchInstanceTxEntry  5  }

    nptSwitchInstanceTxPm	OBJECT-TYPE	
		SYNTAX			Integer32
		MAX-ACCESS		read-only
		STATUS			current
		DESCRIPTION		"PM"
		::=  {  nptSwitchInstanceTxEntry  6  }

    nptSwitchInstanceTxDisContinuityTime	OBJECT-TYPE	
		SYNTAX			DisplayString
		MAX-ACCESS		read-only
		STATUS			current
		DESCRIPTION		"DisContinuity Time"
		::=  {  nptSwitchInstanceTxEntry  7  }

    nptSwitchInstanceTxElapsed	OBJECT-TYPE	
		SYNTAX			DisplayString
		MAX-ACCESS		read-only
		STATUS			current
		DESCRIPTION		"Elapsed"
		::=  {  nptSwitchInstanceTxEntry  8  }


    nptSwitchInstanceTxOctetsPassG	OBJECT-TYPE	
		SYNTAX			Counter64
		MAX-ACCESS		read-only
		STATUS			current
		DESCRIPTION		"Description"
		::=  {  nptSwitchInstanceTxEntry  9  }

    nptSwitchInstanceTxOctetsPassY	OBJECT-TYPE	
		SYNTAX			Counter64
		MAX-ACCESS		read-only
		STATUS			current
		DESCRIPTION		"Description"
		::=  {  nptSwitchInstanceTxEntry  10  }

    nptSwitchInstanceTxOctetsPassSum	OBJECT-TYPE	
		SYNTAX			Counter64
		MAX-ACCESS		read-only
		STATUS			current
		DESCRIPTION		"Description"
		::=  {  nptSwitchInstanceTxEntry  11  }

    nptSwitchInstanceTxOctetsDiscardGY	OBJECT-TYPE	
		SYNTAX			Counter64
		MAX-ACCESS		read-only
		STATUS			current
		DESCRIPTION		"Description"
		::=  {  nptSwitchInstanceTxEntry  12  }

    nptSwitchInstanceTxOctetsDiscardR	OBJECT-TYPE	
		SYNTAX			Counter64
		MAX-ACCESS		read-only
		STATUS			current
		DESCRIPTION		"Description"
		::=  {  nptSwitchInstanceTxEntry  13  }

    nptSwitchInstanceTxOctetsDiscardSum	OBJECT-TYPE	
		SYNTAX			Counter64
		MAX-ACCESS		read-only
		STATUS			current
		DESCRIPTION		"Description"
		::=  {  nptSwitchInstanceTxEntry  14  }

    nptSwitchInstanceTxPacketsPassG	OBJECT-TYPE	
		SYNTAX			Counter64
		MAX-ACCESS		read-only
		STATUS			current
		DESCRIPTION		"Description"
		::=  {  nptSwitchInstanceTxEntry  15  }

    nptSwitchInstanceTxPacketsPassY	OBJECT-TYPE	
		SYNTAX			Counter64
		MAX-ACCESS		read-only
		STATUS			current
		DESCRIPTION		"Description"
		::=  {  nptSwitchInstanceTxEntry  16  }

    nptSwitchInstanceTxPacketsPassSum	OBJECT-TYPE	
		SYNTAX			Counter64
		MAX-ACCESS		read-only
		STATUS			current
		DESCRIPTION		"Description"
		::=  {  nptSwitchInstanceTxEntry  17  }

    nptSwitchInstanceTxPacketsDiscardGY	OBJECT-TYPE	
		SYNTAX			Counter64
		MAX-ACCESS		read-only
		STATUS			current
		DESCRIPTION		"Description"
		::=  {  nptSwitchInstanceTxEntry  18  }

    nptSwitchInstanceTxPacketsDiscardR	OBJECT-TYPE	
		SYNTAX			Counter64
		MAX-ACCESS		read-only
		STATUS			current
		DESCRIPTION		"Description"
		::=  {  nptSwitchInstanceTxEntry  19  }

    nptSwitchInstanceTxPacketsDiscardSum	OBJECT-TYPE	
		SYNTAX			Counter64
		MAX-ACCESS		read-only
		STATUS			current
		DESCRIPTION		"Description"
		::=  {  nptSwitchInstanceTxEntry  20  }
		
	nptSwitchInstanceRxCoSTable	OBJECT-TYPE
		SYNTAX		SEQUENCE  OF  NptSwitchInstanceRxCoSEntry
		MAX-ACCESS	not-accessible
		STATUS		current
		DESCRIPTION	"Description"
		::=  { nptSwitchInstanceRxCoS  1 }

	nptSwitchInstanceRxCoSEntry	OBJECT-TYPE
		SYNTAX		NptSwitchInstanceRxCoSEntry
		MAX-ACCESS	not-accessible
		STATUS		current
		DESCRIPTION	"Row Description"
		INDEX		{  nptSwitchInstanceRxCoSIndex  }
		::=  { nptSwitchInstanceRxCoSTable 1 }

	NptSwitchInstanceRxCoSEntry  ::=  SEQUENCE {
	    nptSwitchInstanceRxCoSIndex  Integer32,
        nptSwitchInstanceRxCoSInstanceName  DisplayString,
        nptSwitchInstanceRxCoSRemoteTPE  DisplayString,
		nptSwitchInstanceRxCoSPeer  DisplayString,
		nptSwitchInstanceRxCoSPath  DisplayString,
        nptSwitchInstanceRxCoSID  Integer32,
        nptSwitchInstanceRxCoSPm  Integer32,
        nptSwitchInstanceRxCoSDisContinuityTime  DisplayString,
        nptSwitchInstanceRxCoSElapsed DisplayString,
		nptSwitchInstanceRxCoSOctetsPassG Counter64,
		nptSwitchInstanceRxCoSOctetsPassY Counter64,
		nptSwitchInstanceRxCoSOctetsPassSum Counter64,
		nptSwitchInstanceRxCoSOctetsDiscardGY Counter64,
		nptSwitchInstanceRxCoSOctetsDiscardR Counter64,
		nptSwitchInstanceRxCoSOctetsDiscardSum Counter64,
		nptSwitchInstanceRxCoSPacketsPassG Counter64,
		nptSwitchInstanceRxCoSPacketsPassY Counter64,
		nptSwitchInstanceRxCoSPacketsPassSum Counter64,
		nptSwitchInstanceRxCoSPacketsDiscardGY Counter64,
		nptSwitchInstanceRxCoSPacketsDiscardR Counter64,
		nptSwitchInstanceRxCoSPacketsDiscardSum Counter64
		}


	nptSwitchInstanceRxCoSIndex	OBJECT-TYPE	
		SYNTAX			Integer32  ( -2147483648 .. 2147483647  ) 
		MAX-ACCESS		read-only
		STATUS			current
		DESCRIPTION		"Column Description"
		::=  {  nptSwitchInstanceRxCoSEntry  1  }

    nptSwitchInstanceRxCoSInstanceName	OBJECT-TYPE	
		SYNTAX			DisplayString 
		MAX-ACCESS		read-only
		STATUS			current
		DESCRIPTION		"InstanceName"
		::=  {  nptSwitchInstanceRxCoSEntry  2  }


    nptSwitchInstanceRxCoSRemoteTPE	OBJECT-TYPE	
		SYNTAX			DisplayString 
		MAX-ACCESS		read-only
		STATUS			current
		DESCRIPTION		"Sec Remote TPE"
		::=  {  nptSwitchInstanceRxCoSEntry  3  }
		
	nptSwitchInstanceRxCoSPeer	OBJECT-TYPE	
		SYNTAX			DisplayString 
		MAX-ACCESS		read-only
		STATUS			current
		DESCRIPTION		"Sec Peer"
		::=  {  nptSwitchInstanceRxCoSEntry  4  }
		
	nptSwitchInstanceRxCoSPath	OBJECT-TYPE	
		SYNTAX			DisplayString 
		MAX-ACCESS		read-only
		STATUS			current
		DESCRIPTION		"Sec Remote TPE"
		::=  {  nptSwitchInstanceRxCoSEntry  5  }

    nptSwitchInstanceRxCoSID	OBJECT-TYPE	
		SYNTAX			Integer32
		MAX-ACCESS		read-only
		STATUS			current
		DESCRIPTION		"CoS ID"
		::=  {  nptSwitchInstanceRxCoSEntry  6  }

    nptSwitchInstanceRxCoSPm	OBJECT-TYPE	
		SYNTAX			Integer32
		MAX-ACCESS		read-only
		STATUS			current
		DESCRIPTION		"PM"
		::=  {  nptSwitchInstanceRxCoSEntry  7  }

    nptSwitchInstanceRxCoSDisContinuityTime	OBJECT-TYPE	
		SYNTAX			DisplayString
		MAX-ACCESS		read-only
		STATUS			current
		DESCRIPTION		"DisContinuity Time"
		::=  {  nptSwitchInstanceRxCoSEntry  8  }

    nptSwitchInstanceRxCoSElapsed	OBJECT-TYPE	
		SYNTAX			DisplayString
		MAX-ACCESS		read-only
		STATUS			current
		DESCRIPTION		"Elapsed"
		::=  {  nptSwitchInstanceRxCoSEntry  9  }


    nptSwitchInstanceRxCoSOctetsPassG	OBJECT-TYPE	
		SYNTAX			Counter64
		MAX-ACCESS		read-only
		STATUS			current
		DESCRIPTION		"Description"
		::=  {  nptSwitchInstanceRxCoSEntry  10  }

    nptSwitchInstanceRxCoSOctetsPassY	OBJECT-TYPE	
		SYNTAX			Counter64
		MAX-ACCESS		read-only
		STATUS			current
		DESCRIPTION		"Description"
		::=  {  nptSwitchInstanceRxCoSEntry  11  }

    nptSwitchInstanceRxCoSOctetsPassSum	OBJECT-TYPE	
		SYNTAX			Counter64
		MAX-ACCESS		read-only
		STATUS			current
		DESCRIPTION		"Description"
		::=  {  nptSwitchInstanceRxCoSEntry  12  }

    nptSwitchInstanceRxCoSOctetsDiscardGY	OBJECT-TYPE	
		SYNTAX			Counter64
		MAX-ACCESS		read-only
		STATUS			current
		DESCRIPTION		"Description"
		::=  {  nptSwitchInstanceRxCoSEntry  13  }

    nptSwitchInstanceRxCoSOctetsDiscardR	OBJECT-TYPE	
		SYNTAX			Counter64
		MAX-ACCESS		read-only
		STATUS			current
		DESCRIPTION		"Description"
		::=  {  nptSwitchInstanceRxCoSEntry  14  }

    nptSwitchInstanceRxCoSOctetsDiscardSum	OBJECT-TYPE	
		SYNTAX			Counter64
		MAX-ACCESS		read-only
		STATUS			current
		DESCRIPTION		"Description"
		::=  {  nptSwitchInstanceRxCoSEntry  15  }

    nptSwitchInstanceRxCoSPacketsPassG	OBJECT-TYPE	
		SYNTAX			Counter64
		MAX-ACCESS		read-only
		STATUS			current
		DESCRIPTION		"Description"
		::=  {  nptSwitchInstanceRxCoSEntry  16  }

    nptSwitchInstanceRxCoSPacketsPassY	OBJECT-TYPE	
		SYNTAX			Counter64
		MAX-ACCESS		read-only
		STATUS			current
		DESCRIPTION		"Description"
		::=  {  nptSwitchInstanceRxCoSEntry  17  }

    nptSwitchInstanceRxCoSPacketsPassSum	OBJECT-TYPE	
		SYNTAX			Counter64
		MAX-ACCESS		read-only
		STATUS			current
		DESCRIPTION		"Description"
		::=  {  nptSwitchInstanceRxCoSEntry  18  }

    nptSwitchInstanceRxCoSPacketsDiscardGY	OBJECT-TYPE	
		SYNTAX			Counter64
		MAX-ACCESS		read-only
		STATUS			current
		DESCRIPTION		"Description"
		::=  {  nptSwitchInstanceRxCoSEntry  19  }

    nptSwitchInstanceRxCoSPacketsDiscardR	OBJECT-TYPE	
		SYNTAX			Counter64
		MAX-ACCESS		read-only
		STATUS			current
		DESCRIPTION		"Description"
		::=  {  nptSwitchInstanceRxCoSEntry  20  }

    nptSwitchInstanceRxCoSPacketsDiscardSum	OBJECT-TYPE	
		SYNTAX			Counter64
		MAX-ACCESS		read-only
		STATUS			current
		DESCRIPTION		"Description"
		::=  {  nptSwitchInstanceRxCoSEntry  21  }

	nptSwitchInstanceTxCoSTable	OBJECT-TYPE
		SYNTAX		SEQUENCE  OF  NptSwitchInstanceTxCoSEntry
		MAX-ACCESS	not-accessible
		STATUS		current
		DESCRIPTION	"Description"
		::=  { nptSwitchInstanceTxCoS  1 }

	nptSwitchInstanceTxCoSEntry	OBJECT-TYPE
		SYNTAX		NptSwitchInstanceTxCoSEntry
		MAX-ACCESS	not-accessible
		STATUS		current
		DESCRIPTION	"Row Description"
		INDEX		{  nptSwitchInstanceTxCoSIndex  }
		::=  { nptSwitchInstanceTxCoSTable 1 }

	NptSwitchInstanceTxCoSEntry  ::=  SEQUENCE {
	    nptSwitchInstanceTxCoSIndex  Integer32,
        nptSwitchInstanceTxCoSInstanceName  DisplayString,
        nptSwitchInstanceTxCoSRemoteTPE  DisplayString,
		nptSwitchInstanceTxCoSPeer  DisplayString,
		nptSwitchInstanceTxCoSPath  DisplayString,
        nptSwitchInstanceTxCoSID  Integer32,
        nptSwitchInstanceTxCoSPm  Integer32,
        nptSwitchInstanceTxCoSDisContinuityTime  DisplayString,
        nptSwitchInstanceTxCoSElapsed DisplayString,
		nptSwitchInstanceTxCoSOctetsPassG Counter64,
		nptSwitchInstanceTxCoSOctetsPassY Counter64,
		nptSwitchInstanceTxCoSOctetsPassSum Counter64,
		nptSwitchInstanceTxCoSOctetsDiscardGY Counter64,
		nptSwitchInstanceTxCoSOctetsDiscardR Counter64,
		nptSwitchInstanceTxCoSOctetsDiscardSum Counter64,
		nptSwitchInstanceTxCoSPacketsPassG Counter64,
		nptSwitchInstanceTxCoSPacketsPassY Counter64,
		nptSwitchInstanceTxCoSPacketsPassSum Counter64,
		nptSwitchInstanceTxCoSPacketsDiscardGY Counter64,
		nptSwitchInstanceTxCoSPacketsDiscardR Counter64,
		nptSwitchInstanceTxCoSPacketsDiscardSum Counter64
		}


	nptSwitchInstanceTxCoSIndex	OBJECT-TYPE	
		SYNTAX			Integer32  ( -2147483648 .. 2147483647  ) 
		MAX-ACCESS		read-only
		STATUS			current
		DESCRIPTION		"Column Description"
		::=  {  nptSwitchInstanceTxCoSEntry  1  }

    nptSwitchInstanceTxCoSInstanceName	OBJECT-TYPE	
		SYNTAX			DisplayString 
		MAX-ACCESS		read-only
		STATUS			current
		DESCRIPTION		"InstanceName"
		::=  {  nptSwitchInstanceTxCoSEntry  2  }

    nptSwitchInstanceTxCoSRemoteTPE	OBJECT-TYPE	
		SYNTAX			DisplayString 
		MAX-ACCESS		read-only
		STATUS			current
		DESCRIPTION		"Pri Remote TPE"
		::=  {  nptSwitchInstanceTxCoSEntry  3  }
		
	nptSwitchInstanceTxCoSPeer	OBJECT-TYPE	
		SYNTAX			DisplayString 
		MAX-ACCESS		read-only
		STATUS			current
		DESCRIPTION		"Pri Remote TPE"
		::=  {  nptSwitchInstanceTxCoSEntry  4  }
		
	nptSwitchInstanceTxCoSPath	OBJECT-TYPE	
		SYNTAX			DisplayString 
		MAX-ACCESS		read-only
		STATUS			current
		DESCRIPTION		"Pri Remote TPE"
		::=  {  nptSwitchInstanceTxCoSEntry  5  }

    nptSwitchInstanceTxCoSID	OBJECT-TYPE	
		SYNTAX			Integer32
		MAX-ACCESS		read-only
		STATUS			current
		DESCRIPTION		"CoS ID"
		::=  {  nptSwitchInstanceTxCoSEntry  6  }

    nptSwitchInstanceTxCoSPm	OBJECT-TYPE	
		SYNTAX			Integer32
		MAX-ACCESS		read-only
		STATUS			current
		DESCRIPTION		"PM"
		::=  {  nptSwitchInstanceTxCoSEntry  7  }

    nptSwitchInstanceTxCoSDisContinuityTime	OBJECT-TYPE	
		SYNTAX			DisplayString
		MAX-ACCESS		read-only
		STATUS			current
		DESCRIPTION		"DisContinuity Time"
		::=  {  nptSwitchInstanceTxCoSEntry  8  }

    nptSwitchInstanceTxCoSElapsed	OBJECT-TYPE	
		SYNTAX			DisplayString
		MAX-ACCESS		read-only
		STATUS			current
		DESCRIPTION		"Elapsed"
		::=  {  nptSwitchInstanceTxCoSEntry  9  }


    nptSwitchInstanceTxCoSOctetsPassG	OBJECT-TYPE	
		SYNTAX			Counter64
		MAX-ACCESS		read-only
		STATUS			current
		DESCRIPTION		"Description"
		::=  {  nptSwitchInstanceTxCoSEntry  10  }

    nptSwitchInstanceTxCoSOctetsPassY	OBJECT-TYPE	
		SYNTAX			Counter64
		MAX-ACCESS		read-only
		STATUS			current
		DESCRIPTION		"Description"
		::=  {  nptSwitchInstanceTxCoSEntry  11  }

    nptSwitchInstanceTxCoSOctetsPassSum	OBJECT-TYPE	
		SYNTAX			Counter64
		MAX-ACCESS		read-only
		STATUS			current
		DESCRIPTION		"Description"
		::=  {  nptSwitchInstanceTxCoSEntry  12  }

    nptSwitchInstanceTxCoSOctetsDiscardGY	OBJECT-TYPE	
		SYNTAX			Counter64
		MAX-ACCESS		read-only
		STATUS			current
		DESCRIPTION		"Description"
		::=  {  nptSwitchInstanceTxCoSEntry  13  }

    nptSwitchInstanceTxCoSOctetsDiscardR	OBJECT-TYPE	
		SYNTAX			Counter64
		MAX-ACCESS		read-only
		STATUS			current
		DESCRIPTION		"Description"
		::=  {  nptSwitchInstanceTxCoSEntry  14  }

    nptSwitchInstanceTxCoSOctetsDiscardSum	OBJECT-TYPE	
		SYNTAX			Counter64
		MAX-ACCESS		read-only
		STATUS			current
		DESCRIPTION		"Description"
		::=  {  nptSwitchInstanceTxCoSEntry  15  }

    nptSwitchInstanceTxCoSPacketsPassG	OBJECT-TYPE	
		SYNTAX			Counter64
		MAX-ACCESS		read-only
		STATUS			current
		DESCRIPTION		"Description"
		::=  {  nptSwitchInstanceTxCoSEntry  16  }

    nptSwitchInstanceTxCoSPacketsPassY	OBJECT-TYPE	
		SYNTAX			Counter64
		MAX-ACCESS		read-only
		STATUS			current
		DESCRIPTION		"Description"
		::=  {  nptSwitchInstanceTxCoSEntry  17  }

    nptSwitchInstanceTxCoSPacketsPassSum	OBJECT-TYPE	
		SYNTAX			Counter64
		MAX-ACCESS		read-only
		STATUS			current
		DESCRIPTION		"Description"
		::=  {  nptSwitchInstanceTxCoSEntry  18  }

    nptSwitchInstanceTxCoSPacketsDiscardGY	OBJECT-TYPE	
		SYNTAX			Counter64
		MAX-ACCESS		read-only
		STATUS			current
		DESCRIPTION		"Description"
		::=  {  nptSwitchInstanceTxCoSEntry  19  }

    nptSwitchInstanceTxCoSPacketsDiscardR	OBJECT-TYPE	
		SYNTAX			Counter64
		MAX-ACCESS		read-only
		STATUS			current
		DESCRIPTION		"Description"
		::=  {  nptSwitchInstanceTxCoSEntry  20  }

    nptSwitchInstanceTxCoSPacketsDiscardSum	OBJECT-TYPE	
		SYNTAX			Counter64
		MAX-ACCESS		read-only
		STATUS			current
		DESCRIPTION		"Description"
		::=  {  nptSwitchInstanceTxCoSEntry  21  }
	
	nptRoutingInstancesTable	OBJECT-TYPE
		SYNTAX		SEQUENCE  OF  NptRoutingInstancesEntry
		MAX-ACCESS	not-accessible
		STATUS		current
		DESCRIPTION	"Description"
		::=  { nptRoutingInstances  1 }

	nptRoutingInstancesEntry	OBJECT-TYPE
		SYNTAX		NptRoutingInstancesEntry
		MAX-ACCESS	not-accessible
		STATUS		current
		DESCRIPTION	"Row Description"
		INDEX		{  nptRoutingInstancesIndex  }
		::=  { nptRoutingInstancesTable 1 }

	NptRoutingInstancesEntry  ::=  SEQUENCE {
	    nptRoutingInstancesIndex  Integer32,
        nptRoutingInstancesInstanceName  DisplayString,
        nptRoutingInstancesPhtName  DisplayString,
        nptRoutingInstancesRemotePE DisplayString,
        nptRoutingInstancesDisContinuityTime  DisplayString,
        nptRoutingInstancesElapsedTime  DisplayString,
		nptRoutingInstancesTxPwStatusMessagesCount Counter64,
		nptRoutingInstancesRxPwStatusMessagesCount Counter64,
		nptRoutingInstancesRxPwInvalidMessagesCount Counter64,
		nptRoutingInstancesRxEnabled  DisplayString,
		nptRoutingInstancesRxOctetsPassG Counter64,
		nptRoutingInstancesRxOctetsPassY Counter64,
		nptRoutingInstancesRxOctetsPassSum Counter64,
		nptRoutingInstancesRxOctetsDiscardGY Counter64,
		nptRoutingInstancesRxOctetsDiscardR Counter64,
		nptRoutingInstancesRxOctetsDiscardSum Counter64,
		nptRoutingInstancesRxPacketsPassG Counter64,
		nptRoutingInstancesRxPacketsPassY Counter64,
		nptRoutingInstancesRxPacketsPassSum Counter64,
		nptRoutingInstancesRxPacketsDiscardGY Counter64,
		nptRoutingInstancesRxPacketsDiscardR Counter64,
		nptRoutingInstancesRxPacketsDiscardSum Counter64,
		nptRoutingInstancesTxEnabled  DisplayString,
		nptRoutingInstancesTxOctetsPassG Counter64,
		nptRoutingInstancesTxOctetsPassY Counter64,
		nptRoutingInstancesTxOctetsPassSum Counter64,
		nptRoutingInstancesTxOctetsDiscardGY Counter64,
		nptRoutingInstancesTxOctetsDiscardR Counter64,
		nptRoutingInstancesTxOctetsDiscardSum Counter64,
		nptRoutingInstancesTxPacketsPassG Counter64,
		nptRoutingInstancesTxPacketsPassY Counter64,
		nptRoutingInstancesTxPacketsPassSum Counter64,
		nptRoutingInstancesTxPacketsDiscardGY Counter64,
		nptRoutingInstancesTxPacketsDiscardR Counter64,
		nptRoutingInstancesTxPacketsDiscardSum Counter64
		}


	nptRoutingInstancesIndex	OBJECT-TYPE	
		SYNTAX			Integer32  ( -2147483648 .. 2147483647  ) 
		MAX-ACCESS		read-only
		STATUS			current
		DESCRIPTION		"Column Description"
		::=  {  nptRoutingInstancesEntry  1  }

    nptRoutingInstancesInstanceName	OBJECT-TYPE	
		SYNTAX			DisplayString 
		MAX-ACCESS		read-only
		STATUS			current
		DESCRIPTION		"instance Name"
		::=  {  nptRoutingInstancesEntry  2  }

    nptRoutingInstancesPhtName	OBJECT-TYPE	
		SYNTAX			DisplayString
		MAX-ACCESS		read-only
		STATUS			current
		DESCRIPTION		"Pht Name"
		::=  {  nptRoutingInstancesEntry  3  }

    nptRoutingInstancesRemotePE	OBJECT-TYPE	
		SYNTAX			DisplayString
		MAX-ACCESS		read-only
		STATUS			current
		DESCRIPTION		"RemotePE"
		::=  {  nptRoutingInstancesEntry  4  }

    nptRoutingInstancesDisContinuityTime	OBJECT-TYPE	
		SYNTAX			DisplayString
		MAX-ACCESS		read-only
		STATUS			current
		DESCRIPTION		"DisContinuity Time"
		::=  {  nptRoutingInstancesEntry  5  }
		
	nptRoutingInstancesElapsedTime	OBJECT-TYPE	
		SYNTAX			DisplayString
		MAX-ACCESS		read-only
		STATUS			current
		DESCRIPTION		"Elapsed Time"
		::=  {  nptRoutingInstancesEntry  6  }

    nptRoutingInstancesTxPwStatusMessagesCount	OBJECT-TYPE	
		SYNTAX			Counter64
		MAX-ACCESS		read-only
		STATUS			current
		DESCRIPTION		"Description"
		::=  {  nptRoutingInstancesEntry  7  }

    nptRoutingInstancesRxPwStatusMessagesCount	OBJECT-TYPE	
		SYNTAX			Counter64
		MAX-ACCESS		read-only
		STATUS			current
		DESCRIPTION		"Description"
		::=  {  nptRoutingInstancesEntry  8  }

    nptRoutingInstancesRxPwInvalidMessagesCount	OBJECT-TYPE	
		SYNTAX			Counter64
		MAX-ACCESS		read-only
		STATUS			current
		DESCRIPTION		"Description"
		::=  {  nptRoutingInstancesEntry  9  }

    nptRoutingInstancesRxEnabled	OBJECT-TYPE	
		SYNTAX			DisplayString 
		MAX-ACCESS		read-only
		STATUS			current
		DESCRIPTION		"Yes/No"
		::=  {  nptRoutingInstancesEntry  10  }


    nptRoutingInstancesRxOctetsPassG	OBJECT-TYPE	
		SYNTAX			Counter64
		MAX-ACCESS		read-only
		STATUS			current
		DESCRIPTION		"Description"
		::=  {  nptRoutingInstancesEntry  11  }

    nptRoutingInstancesRxOctetsPassY	OBJECT-TYPE	
		SYNTAX			Counter64
		MAX-ACCESS		read-only
		STATUS			current
		DESCRIPTION		"Description"
		::=  {  nptRoutingInstancesEntry  12  }

    nptRoutingInstancesRxOctetsPassSum	OBJECT-TYPE	
		SYNTAX			Counter64
		MAX-ACCESS		read-only
		STATUS			current
		DESCRIPTION		"Description"
		::=  {  nptRoutingInstancesEntry  13  }

    nptRoutingInstancesRxOctetsDiscardGY	OBJECT-TYPE	
		SYNTAX			Counter64
		MAX-ACCESS		read-only
		STATUS			current
		DESCRIPTION		"Description"
		::=  {  nptRoutingInstancesEntry  14  }

    nptRoutingInstancesRxOctetsDiscardR	OBJECT-TYPE	
		SYNTAX			Counter64
		MAX-ACCESS		read-only
		STATUS			current
		DESCRIPTION		"Description"
		::=  {  nptRoutingInstancesEntry  15  }

    nptRoutingInstancesRxOctetsDiscardSum	OBJECT-TYPE	
		SYNTAX			Counter64
		MAX-ACCESS		read-only
		STATUS			current
		DESCRIPTION		"Description"
		::=  {  nptRoutingInstancesEntry  16  }

    nptRoutingInstancesRxPacketsPassG	OBJECT-TYPE	
		SYNTAX			Counter64
		MAX-ACCESS		read-only
		STATUS			current
		DESCRIPTION		"Description"
		::=  {  nptRoutingInstancesEntry  17  }

    nptRoutingInstancesRxPacketsPassY	OBJECT-TYPE	
		SYNTAX			Counter64
		MAX-ACCESS		read-only
		STATUS			current
		DESCRIPTION		"Description"
		::=  {  nptRoutingInstancesEntry  18  }

    nptRoutingInstancesRxPacketsPassSum	OBJECT-TYPE	
		SYNTAX			Counter64
		MAX-ACCESS		read-only
		STATUS			current
		DESCRIPTION		"Description"
		::=  {  nptRoutingInstancesEntry  19  }

    nptRoutingInstancesRxPacketsDiscardGY	OBJECT-TYPE	
		SYNTAX			Counter64
		MAX-ACCESS		read-only
		STATUS			current
		DESCRIPTION		"Description"
		::=  {  nptRoutingInstancesEntry  20  }

    nptRoutingInstancesRxPacketsDiscardR	OBJECT-TYPE	
		SYNTAX			Counter64
		MAX-ACCESS		read-only
		STATUS			current
		DESCRIPTION		"Description"
		::=  {  nptRoutingInstancesEntry  21  }

    nptRoutingInstancesRxPacketsDiscardSum	OBJECT-TYPE	
		SYNTAX			Counter64
		MAX-ACCESS		read-only
		STATUS			current
		DESCRIPTION		"Description"
		::=  {  nptRoutingInstancesEntry  22  }

    nptRoutingInstancesTxEnabled	OBJECT-TYPE	
		SYNTAX			DisplayString 
		MAX-ACCESS		read-only
		STATUS			current
		DESCRIPTION		"Yes/No"
		::=  {  nptRoutingInstancesEntry  23  }


    nptRoutingInstancesTxOctetsPassG	OBJECT-TYPE	
		SYNTAX			Counter64
		MAX-ACCESS		read-only
		STATUS			current
		DESCRIPTION		"Description"
		::=  {  nptRoutingInstancesEntry  24  }

    nptRoutingInstancesTxOctetsPassY	OBJECT-TYPE	
		SYNTAX			Counter64
		MAX-ACCESS		read-only
		STATUS			current
		DESCRIPTION		"Description"
		::=  {  nptRoutingInstancesEntry  25  }

    nptRoutingInstancesTxOctetsPassSum	OBJECT-TYPE	
		SYNTAX			Counter64
		MAX-ACCESS		read-only
		STATUS			current
		DESCRIPTION		"Description"
		::=  {  nptRoutingInstancesEntry  26  }

    nptRoutingInstancesTxOctetsDiscardGY	OBJECT-TYPE	
		SYNTAX			Counter64
		MAX-ACCESS		read-only
		STATUS			current
		DESCRIPTION		"Description"
		::=  {  nptRoutingInstancesEntry  27  }

    nptRoutingInstancesTxOctetsDiscardR	OBJECT-TYPE	
		SYNTAX			Counter64
		MAX-ACCESS		read-only
		STATUS			current
		DESCRIPTION		"Description"
		::=  {  nptRoutingInstancesEntry  28  }

    nptRoutingInstancesTxOctetsDiscardSum	OBJECT-TYPE	
		SYNTAX			Counter64
		MAX-ACCESS		read-only
		STATUS			current
		DESCRIPTION		"Description"
		::=  {  nptRoutingInstancesEntry  29  }

    nptRoutingInstancesTxPacketsPassG	OBJECT-TYPE	
		SYNTAX			Counter64
		MAX-ACCESS		read-only
		STATUS			current
		DESCRIPTION		"Description"
		::=  {  nptRoutingInstancesEntry  30  }

    nptRoutingInstancesTxPacketsPassY	OBJECT-TYPE	
		SYNTAX			Counter64
		MAX-ACCESS		read-only
		STATUS			current
		DESCRIPTION		"Description"
		::=  {  nptRoutingInstancesEntry  31  }

    nptRoutingInstancesTxPacketsPassSum	OBJECT-TYPE	
		SYNTAX			Counter64
		MAX-ACCESS		read-only
		STATUS			current
		DESCRIPTION		"Description"
		::=  {  nptRoutingInstancesEntry  32  }

    nptRoutingInstancesTxPacketsDiscardGY	OBJECT-TYPE	
		SYNTAX			Counter64
		MAX-ACCESS		read-only
		STATUS			current
		DESCRIPTION		"Description"
		::=  {  nptRoutingInstancesEntry  33  }

    nptRoutingInstancesTxPacketsDiscardR	OBJECT-TYPE	
		SYNTAX			Counter64
		MAX-ACCESS		read-only
		STATUS			current
		DESCRIPTION		"Description"
		::=  {  nptRoutingInstancesEntry  34  }

    nptRoutingInstancesTxPacketsDiscardSum	OBJECT-TYPE	
		SYNTAX			Counter64
		MAX-ACCESS		read-only
		STATUS			current
		DESCRIPTION		"Description"
		::=  {  nptRoutingInstancesEntry  35  }
		
	nptRoutingInstancesRxCoSTable	OBJECT-TYPE
		SYNTAX		SEQUENCE  OF  NptRoutingInstancesRxCoSEntry
		MAX-ACCESS	not-accessible
		STATUS		current
		DESCRIPTION	"Description"
		::=  { nptRoutingInstancesRxCoS  1 }

	nptRoutingInstancesRxCoSEntry	OBJECT-TYPE
		SYNTAX		NptRoutingInstancesRxCoSEntry
		MAX-ACCESS	not-accessible
		STATUS		current
		DESCRIPTION	"Row Description"
		INDEX		{  nptRoutingInstancesRxCoSIndex  }
		::=  { nptRoutingInstancesRxCoSTable 1 }

	NptRoutingInstancesRxCoSEntry  ::=  SEQUENCE {
	    nptRoutingInstancesRxCoSIndex  Integer32,
        nptRoutingInstancesRxInstanceName  DisplayString,
        nptRoutingInstancesRxPhtName  DisplayString,
        nptRoutingInstancesRxRemotePE DisplayString,
        nptRoutingInstancesRxDisContinuityTime  DisplayString,
        nptRoutingInstancesRxElapsedTime  DisplayString,
        nptRoutingInstancesRxCoSID  Integer32,
        nptRoutingInstancesRxCoSEnable  DisplayString,
        nptRoutingInstancesRxCoSPM  DisplayString,
		nptRoutingInstancesRxCoSOctetsPassG Counter64,
		nptRoutingInstancesRxCoSOctetsPassY Counter64,
		nptRoutingInstancesRxCoSOctetsPassSum Counter64,
		nptRoutingInstancesRxCoSOctetsDiscardGY Counter64,
		nptRoutingInstancesRxCoSOctetsDiscardR Counter64,
		nptRoutingInstancesRxCoSOctetsDiscardSum Counter64,
		nptRoutingInstancesRxCoSPacketsPassG Counter64,
		nptRoutingInstancesRxCoSPacketsPassY Counter64,
		nptRoutingInstancesRxCoSPacketsPassSum Counter64,
		nptRoutingInstancesRxCoSPacketsDiscardGY Counter64,
		nptRoutingInstancesRxCoSPacketsDiscardR Counter64,
		nptRoutingInstancesRxCoSPacketsDiscardSum Counter64
		}


	nptRoutingInstancesRxCoSIndex	OBJECT-TYPE	
		SYNTAX			Integer32  ( -2147483648 .. 2147483647  ) 
		MAX-ACCESS		read-only
		STATUS			current
		DESCRIPTION		"Column Description"
		::=  {  nptRoutingInstancesRxCoSEntry  1  }

    nptRoutingInstancesRxInstanceName	OBJECT-TYPE	
		SYNTAX			DisplayString 
		MAX-ACCESS		read-only
		STATUS			current
		DESCRIPTION		"Instance Name"
		::=  {  nptRoutingInstancesRxCoSEntry  2  }

    nptRoutingInstancesRxPhtName	OBJECT-TYPE	
		SYNTAX			DisplayString
		MAX-ACCESS		read-only
		STATUS			current
		DESCRIPTION		"PhtName"
		::=  {  nptRoutingInstancesRxCoSEntry  3  }

    nptRoutingInstancesRxRemotePE	OBJECT-TYPE	
		SYNTAX			DisplayString 
		MAX-ACCESS		read-only
		STATUS			current
		DESCRIPTION		"RemotePE"
		::=  {  nptRoutingInstancesRxCoSEntry  4  }

    nptRoutingInstancesRxDisContinuityTime	OBJECT-TYPE	
		SYNTAX			DisplayString
		MAX-ACCESS		read-only
		STATUS			current
		DESCRIPTION		"DisContinuity Time"
		::=  {  nptRoutingInstancesRxCoSEntry  5  }

    nptRoutingInstancesRxElapsedTime	OBJECT-TYPE	
		SYNTAX			DisplayString 
		MAX-ACCESS		read-only
		STATUS			current
		DESCRIPTION		"dd:hh:mm:ss"
		::=  {  nptRoutingInstancesRxCoSEntry  6  }

    nptRoutingInstancesRxCoSID	OBJECT-TYPE	
		SYNTAX			Integer32
		MAX-ACCESS		read-only
		STATUS			current
		DESCRIPTION		"Cos ID"
		::=  {  nptRoutingInstancesRxCoSEntry  7  }

    nptRoutingInstancesRxCoSEnable	OBJECT-TYPE	
		SYNTAX			DisplayString
		MAX-ACCESS		read-only
		STATUS			current
		DESCRIPTION		"Enable"
		::=  {  nptRoutingInstancesRxCoSEntry  8  }


    nptRoutingInstancesRxCoSPM	OBJECT-TYPE	
		SYNTAX			DisplayString
		MAX-ACCESS		read-only
		STATUS			current
		DESCRIPTION		"PM"
		::=  {  nptRoutingInstancesRxCoSEntry  9  }

    nptRoutingInstancesRxCoSOctetsPassG	OBJECT-TYPE	
		SYNTAX			Counter64
		MAX-ACCESS		read-only
		STATUS			current
		DESCRIPTION		"Description"
		::=  {  nptRoutingInstancesRxCoSEntry  10  }

    nptRoutingInstancesRxCoSOctetsPassY	OBJECT-TYPE	
		SYNTAX			Counter64
		MAX-ACCESS		read-only
		STATUS			current
		DESCRIPTION		"Description"
		::=  {  nptRoutingInstancesRxCoSEntry  11  }

    nptRoutingInstancesRxCoSOctetsPassSum	OBJECT-TYPE	
		SYNTAX			Counter64
		MAX-ACCESS		read-only
		STATUS			current
		DESCRIPTION		"Description"
		::=  {  nptRoutingInstancesRxCoSEntry  12  }

    nptRoutingInstancesRxCoSOctetsDiscardGY	OBJECT-TYPE	
		SYNTAX			Counter64
		MAX-ACCESS		read-only
		STATUS			current
		DESCRIPTION		"Description"
		::=  {  nptRoutingInstancesRxCoSEntry  13  }

    nptRoutingInstancesRxCoSOctetsDiscardR	OBJECT-TYPE	
		SYNTAX			Counter64
		MAX-ACCESS		read-only
		STATUS			current
		DESCRIPTION		"Description"
		::=  {  nptRoutingInstancesRxCoSEntry  14  }

    nptRoutingInstancesRxCoSOctetsDiscardSum	OBJECT-TYPE	
		SYNTAX			Counter64
		MAX-ACCESS		read-only
		STATUS			current
		DESCRIPTION		"Description"
		::=  {  nptRoutingInstancesRxCoSEntry  15  }

    nptRoutingInstancesRxCoSPacketsPassG	OBJECT-TYPE	
		SYNTAX			Counter64
		MAX-ACCESS		read-only
		STATUS			current
		DESCRIPTION		"Description"
		::=  {  nptRoutingInstancesRxCoSEntry  16  }

    nptRoutingInstancesRxCoSPacketsPassY	OBJECT-TYPE	
		SYNTAX			Counter64
		MAX-ACCESS		read-only
		STATUS			current
		DESCRIPTION		"Description"
		::=  {  nptRoutingInstancesRxCoSEntry  17  }

    nptRoutingInstancesRxCoSPacketsPassSum	OBJECT-TYPE	
		SYNTAX			Counter64
		MAX-ACCESS		read-only
		STATUS			current
		DESCRIPTION		"Description"
		::=  {  nptRoutingInstancesRxCoSEntry  18  }

    nptRoutingInstancesRxCoSPacketsDiscardGY	OBJECT-TYPE	
		SYNTAX			Counter64
		MAX-ACCESS		read-only
		STATUS			current
		DESCRIPTION		"Description"
		::=  {  nptRoutingInstancesRxCoSEntry  19  }

    nptRoutingInstancesRxCoSPacketsDiscardR	OBJECT-TYPE	
		SYNTAX			Counter64
		MAX-ACCESS		read-only
		STATUS			current
		DESCRIPTION		"Description"
		::=  {  nptRoutingInstancesRxCoSEntry  20  }

    nptRoutingInstancesRxCoSPacketsDiscardSum	OBJECT-TYPE	
		SYNTAX			Counter64
		MAX-ACCESS		read-only
		STATUS			current
		DESCRIPTION		"Description"
		::=  {  nptRoutingInstancesRxCoSEntry  21  }
		
	nptRoutingInstancesTxCoSTable	OBJECT-TYPE
		SYNTAX		SEQUENCE  OF  NptRoutingInstancesTxCoSEntry
		MAX-ACCESS	not-accessible
		STATUS		current
		DESCRIPTION	"Description"
		::=  { nptRoutingInstancesTxCoS  1 }

	nptRoutingInstancesTxCoSEntry	OBJECT-TYPE
		SYNTAX		NptRoutingInstancesTxCoSEntry
		MAX-ACCESS	not-accessible
		STATUS		current
		DESCRIPTION	"Row Description"
		INDEX		{  nptRoutingInstancesTxCoSIndex  }
		::=  { nptRoutingInstancesTxCoSTable 1 }

	NptRoutingInstancesTxCoSEntry  ::=  SEQUENCE {
	    nptRoutingInstancesTxCoSIndex  Integer32,
        nptRoutingInstancesTxInstanceName  DisplayString,
        nptRoutingInstancesTxPhtName  DisplayString,
        nptRoutingInstancesTxRemotePE DisplayString,
        nptRoutingInstancesTxDisContinuityTime  DisplayString,
        nptRoutingInstancesTxElapsedTime  DisplayString,
        nptRoutingInstancesTxCoSID  Integer32,
        nptRoutingInstancesTxCoSEnable  DisplayString,
        nptRoutingInstancesTxCoSPM  DisplayString,
		nptRoutingInstancesTxCoSOctetsPassG Counter64,
		nptRoutingInstancesTxCoSOctetsPassY Counter64,
		nptRoutingInstancesTxCoSOctetsPassSum Counter64,
		nptRoutingInstancesTxCoSOctetsDiscardGY Counter64,
		nptRoutingInstancesTxCoSOctetsDiscardR Counter64,
		nptRoutingInstancesTxCoSOctetsDiscardSum Counter64,
		nptRoutingInstancesTxCoSPacketsPassG Counter64,
		nptRoutingInstancesTxCoSPacketsPassY Counter64,
		nptRoutingInstancesTxCoSPacketsPassSum Counter64,
		nptRoutingInstancesTxCoSPacketsDiscardGY Counter64,
		nptRoutingInstancesTxCoSPacketsDiscardR Counter64,
		nptRoutingInstancesTxCoSPacketsDiscardSum Counter64
		}


	nptRoutingInstancesTxCoSIndex	OBJECT-TYPE	
		SYNTAX			Integer32  ( -2147483648 .. 2147483647  ) 
		MAX-ACCESS		read-only
		STATUS			current
		DESCRIPTION		"Column Description"
		::=  {  nptRoutingInstancesTxCoSEntry  1  }

    nptRoutingInstancesTxInstanceName	OBJECT-TYPE	
		SYNTAX			DisplayString 
		MAX-ACCESS		read-only
		STATUS			current
		DESCRIPTION		"Instance Name"
		::=  {  nptRoutingInstancesTxCoSEntry  2  }

    nptRoutingInstancesTxPhtName	OBJECT-TYPE	
		SYNTAX			DisplayString
		MAX-ACCESS		read-only
		STATUS			current
		DESCRIPTION		"PhtName"
		::=  {  nptRoutingInstancesTxCoSEntry  3  }

    nptRoutingInstancesTxRemotePE	OBJECT-TYPE	
		SYNTAX			DisplayString 
		MAX-ACCESS		read-only
		STATUS			current
		DESCRIPTION		"RemotePE"
		::=  {  nptRoutingInstancesTxCoSEntry  4  }

    nptRoutingInstancesTxDisContinuityTime	OBJECT-TYPE	
		SYNTAX			DisplayString
		MAX-ACCESS		read-only
		STATUS			current
		DESCRIPTION		"DisContinuity Time"
		::=  {  nptRoutingInstancesTxCoSEntry  5  }

    nptRoutingInstancesTxElapsedTime	OBJECT-TYPE	
		SYNTAX			DisplayString 
		MAX-ACCESS		read-only
		STATUS			current
		DESCRIPTION		"dd:hh:mm:ss"
		::=  {  nptRoutingInstancesTxCoSEntry  6  }

    nptRoutingInstancesTxCoSID	OBJECT-TYPE	
		SYNTAX			Integer32
		MAX-ACCESS		read-only
		STATUS			current
		DESCRIPTION		"Cos ID"
		::=  {  nptRoutingInstancesTxCoSEntry  7  }

    nptRoutingInstancesTxCoSEnable	OBJECT-TYPE	
		SYNTAX			DisplayString
		MAX-ACCESS		read-only
		STATUS			current
		DESCRIPTION		"Enable"
		::=  {  nptRoutingInstancesTxCoSEntry  8  }


    nptRoutingInstancesTxCoSPM	OBJECT-TYPE	
		SYNTAX			DisplayString
		MAX-ACCESS		read-only
		STATUS			current
		DESCRIPTION		"PM"
		::=  {  nptRoutingInstancesTxCoSEntry  9  }

    nptRoutingInstancesTxCoSOctetsPassG	OBJECT-TYPE	
		SYNTAX			Counter64
		MAX-ACCESS		read-only
		STATUS			current
		DESCRIPTION		"Description"
		::=  {  nptRoutingInstancesTxCoSEntry  10  }

    nptRoutingInstancesTxCoSOctetsPassY	OBJECT-TYPE	
		SYNTAX			Counter64
		MAX-ACCESS		read-only
		STATUS			current
		DESCRIPTION		"Description"
		::=  {  nptRoutingInstancesTxCoSEntry  11  }

    nptRoutingInstancesTxCoSOctetsPassSum	OBJECT-TYPE	
		SYNTAX			Counter64
		MAX-ACCESS		read-only
		STATUS			current
		DESCRIPTION		"Description"
		::=  {  nptRoutingInstancesTxCoSEntry  12  }

    nptRoutingInstancesTxCoSOctetsDiscardGY	OBJECT-TYPE	
		SYNTAX			Counter64
		MAX-ACCESS		read-only
		STATUS			current
		DESCRIPTION		"Description"
		::=  {  nptRoutingInstancesTxCoSEntry  13  }

    nptRoutingInstancesTxCoSOctetsDiscardR	OBJECT-TYPE	
		SYNTAX			Counter64
		MAX-ACCESS		read-only
		STATUS			current
		DESCRIPTION		"Description"
		::=  {  nptRoutingInstancesTxCoSEntry  14  }

    nptRoutingInstancesTxCoSOctetsDiscardSum	OBJECT-TYPE	
		SYNTAX			Counter64
		MAX-ACCESS		read-only
		STATUS			current
		DESCRIPTION		"Description"
		::=  {  nptRoutingInstancesTxCoSEntry  15  }

    nptRoutingInstancesTxCoSPacketsPassG	OBJECT-TYPE	
		SYNTAX			Counter64
		MAX-ACCESS		read-only
		STATUS			current
		DESCRIPTION		"Description"
		::=  {  nptRoutingInstancesTxCoSEntry  16  }

    nptRoutingInstancesTxCoSPacketsPassY	OBJECT-TYPE	
		SYNTAX			Counter64
		MAX-ACCESS		read-only
		STATUS			current
		DESCRIPTION		"Description"
		::=  {  nptRoutingInstancesTxCoSEntry  17  }

    nptRoutingInstancesTxCoSPacketsPassSum	OBJECT-TYPE	
		SYNTAX			Counter64
		MAX-ACCESS		read-only
		STATUS			current
		DESCRIPTION		"Description"
		::=  {  nptRoutingInstancesTxCoSEntry  18  }

    nptRoutingInstancesTxCoSPacketsDiscardGY	OBJECT-TYPE	
		SYNTAX			Counter64
		MAX-ACCESS		read-only
		STATUS			current
		DESCRIPTION		"Description"
		::=  {  nptRoutingInstancesTxCoSEntry  19  }

    nptRoutingInstancesTxCoSPacketsDiscardR	OBJECT-TYPE	
		SYNTAX			Counter64
		MAX-ACCESS		read-only
		STATUS			current
		DESCRIPTION		"Description"
		::=  {  nptRoutingInstancesTxCoSEntry  20  }

    nptRoutingInstancesTxCoSPacketsDiscardSum	OBJECT-TYPE	
		SYNTAX			Counter64
		MAX-ACCESS		read-only
		STATUS			current
		DESCRIPTION		"Description"
		::=  {  nptRoutingInstancesTxCoSEntry  21  }

		
		
	nptSecurityMacsecStatisticsComPortTable	OBJECT-TYPE
		SYNTAX		SEQUENCE  OF  NptSecurityMacsecStatisticsComPortEntry
		MAX-ACCESS	not-accessible
		STATUS		current
		DESCRIPTION	"Description"
		::=  { nptSecurityMacsecStatisticsComPort  1 }

	nptSecurityMacsecStatisticsComPortEntry	OBJECT-TYPE
		SYNTAX		NptSecurityMacsecStatisticsComPortEntry
		MAX-ACCESS	not-accessible
		STATUS		current
		DESCRIPTION	"Row Description"
		INDEX		{  nptSecurityMacsecStatisticsComPortIndex  }
		::=  { nptSecurityMacsecStatisticsComPortTable 1 }

	NptSecurityMacsecStatisticsComPortEntry  ::=  SEQUENCE {
		nptSecurityMacsecStatisticsComPortIndex  Integer32,
		nptSecurityMacsecStatisticsComPortiMACPort  DisplayString,
		nptSecurityMacsecStatisticsComPortRecOctets  Counter64,
		nptSecurityMacsecStatisticsComPortRecUnicast  Counter64,
		nptSecurityMacsecStatisticsComPortRecMulticast  Counter64,
		nptSecurityMacsecStatisticsComPortRecBroadcast  Counter64,
		nptSecurityMacsecStatisticsComPortRecDiscarded  Counter64,
		nptSecurityMacsecStatisticsComPortRecError  Counter64,
		nptSecurityMacsecStatisticsComPortTraOctets  Counter64,
		nptSecurityMacsecStatisticsComPortTraUnicast  Counter64,
		nptSecurityMacsecStatisticsComPortTraMulticast  Counter64,
		nptSecurityMacsecStatisticsComPortTraBroadcast  Counter64,
		nptSecurityMacsecStatisticsComPortTraError  Counter64
		}


	nptSecurityMacsecStatisticsComPortIndex	OBJECT-TYPE	
		SYNTAX			Integer32  ( -2147483648 .. 2147483647  ) 
		MAX-ACCESS		read-only
		STATUS			current
		DESCRIPTION		"Column Description"
		::=  {  nptSecurityMacsecStatisticsComPortEntry  1  }

	nptSecurityMacsecStatisticsComPortiMACPort	OBJECT-TYPE	
		SYNTAX			DisplayString 
		MAX-ACCESS		read-only
		STATUS			current
		DESCRIPTION		"Description"
		::=  {  nptSecurityMacsecStatisticsComPortEntry  2  }

	nptSecurityMacsecStatisticsComPortRecOctets	OBJECT-TYPE	
		SYNTAX			Counter64
		MAX-ACCESS		read-only
		STATUS			current
		DESCRIPTION		"Description"
		::=  {  nptSecurityMacsecStatisticsComPortEntry  3  }

	nptSecurityMacsecStatisticsComPortRecUnicast	OBJECT-TYPE	
		SYNTAX			Counter64 
		MAX-ACCESS		read-only
		STATUS			current
		DESCRIPTION		"Description"
		::=  {  nptSecurityMacsecStatisticsComPortEntry  4  }

    nptSecurityMacsecStatisticsComPortRecMulticast	OBJECT-TYPE	
		SYNTAX			Counter64
		MAX-ACCESS		read-only
		STATUS			current
		DESCRIPTION		"Description"
		::=  {  nptSecurityMacsecStatisticsComPortEntry  5  }

	nptSecurityMacsecStatisticsComPortRecBroadcast	OBJECT-TYPE	
		SYNTAX			Counter64 
		MAX-ACCESS		read-only
		STATUS			current
		DESCRIPTION		"Description"
		::=  {  nptSecurityMacsecStatisticsComPortEntry  6  }

	nptSecurityMacsecStatisticsComPortRecDiscarded	OBJECT-TYPE	
		SYNTAX			Counter64
		MAX-ACCESS		read-only
		STATUS			current
		DESCRIPTION		"Description"
		::=  {  nptSecurityMacsecStatisticsComPortEntry  7  }

	nptSecurityMacsecStatisticsComPortRecError	OBJECT-TYPE	
		SYNTAX			Counter64
		MAX-ACCESS		read-only
		STATUS			current
		DESCRIPTION		"Description"
		::=  {  nptSecurityMacsecStatisticsComPortEntry  8  }
		
		nptSecurityMacsecStatisticsComPortTraOctets	OBJECT-TYPE	
		SYNTAX			Counter64
		MAX-ACCESS		read-only
		STATUS			current
		DESCRIPTION		"Description"
		::=  {  nptSecurityMacsecStatisticsComPortEntry  9  }
		
		nptSecurityMacsecStatisticsComPortTraUnicast	OBJECT-TYPE	
		SYNTAX			Counter64
		MAX-ACCESS		read-only
		STATUS			current
		DESCRIPTION		"Description"
		::=  {  nptSecurityMacsecStatisticsComPortEntry  10  }
		
		nptSecurityMacsecStatisticsComPortTraMulticast	OBJECT-TYPE	
		SYNTAX			Counter64
		MAX-ACCESS		read-only
		STATUS			current
		DESCRIPTION		"Description"
		::=  {  nptSecurityMacsecStatisticsComPortEntry  11  }
		
		nptSecurityMacsecStatisticsComPortTraBroadcast	OBJECT-TYPE	
		SYNTAX			Counter64
		MAX-ACCESS		read-only
		STATUS			current
		DESCRIPTION		"Description"
		::=  {  nptSecurityMacsecStatisticsComPortEntry  12  }
		
		nptSecurityMacsecStatisticsComPortTraError	OBJECT-TYPE	
		SYNTAX			Counter64
		MAX-ACCESS		read-only
		STATUS			current
		DESCRIPTION		"Description"
		::=  {  nptSecurityMacsecStatisticsComPortEntry  13  }

		
		
	nptSecurityMacsecStatisticsCtrlPortTable	OBJECT-TYPE	
		SYNTAX		SEQUENCE  OF  NptSecurityMacsecStatisticsCtrlPortEntry
		MAX-ACCESS	not-accessible
		STATUS		current
		DESCRIPTION	"Description"
		::=  { nptSecurityMacsecStatisticsCtrlPort  1 }

	nptSecurityMacsecStatisticsCtrlPortEntry	OBJECT-TYPE
		SYNTAX		NptSecurityMacsecStatisticsCtrlPortEntry
		MAX-ACCESS	not-accessible
		STATUS		current
		DESCRIPTION	"Description"
		INDEX		{  nptSecurityMacsecStatisticsCtrlPortIndex  }
		::=  { nptSecurityMacsecStatisticsCtrlPortTable 1 }

	NptSecurityMacsecStatisticsCtrlPortEntry  ::=  SEQUENCE {
		nptSecurityMacsecStatisticsCtrlPortIndex  Integer32,
		nptSecurityMacsecStatisticsCtrlPortiMACPort  DisplayString,
		nptSecurityMacsecStatisticsCtrlPortRecOctets  Counter64,
		nptSecurityMacsecStatisticsCtrlPortRecPackets  Counter64,
		nptSecurityMacsecStatisticsCtrlPortRecUnicast  Counter64,
		nptSecurityMacsecStatisticsCtrlPortRecMulticast  Counter64,
		nptSecurityMacsecStatisticsCtrlPortRecBroadcast  Counter64,
		nptSecurityMacsecStatisticsCtrlPortRecDiscarded  Counter64,
		nptSecurityMacsecStatisticsCtrlPortRecError  Counter64,
		nptSecurityMacsecStatisticsCtrlPortTraOctets  Counter64,
		nptSecurityMacsecStatisticsCtrlPortTraPackets  Counter64,
		nptSecurityMacsecStatisticsCtrlPortTraUnicast  Counter64,
		nptSecurityMacsecStatisticsCtrlPortTraMulticast  Counter64,
		nptSecurityMacsecStatisticsCtrlPortTraBroadcast  Counter64,
		nptSecurityMacsecStatisticsCtrlPortTraError  Counter64
		}


	nptSecurityMacsecStatisticsCtrlPortIndex	OBJECT-TYPE	
		SYNTAX			Integer32  ( -2147483648 .. 2147483647  ) 
		MAX-ACCESS		read-only
		STATUS			current
		DESCRIPTION		"Description"
		::=  {  nptSecurityMacsecStatisticsCtrlPortEntry  1  }

	nptSecurityMacsecStatisticsCtrlPortiMACPort	OBJECT-TYPE	
		SYNTAX			DisplayString 
		MAX-ACCESS		read-only
		STATUS			current
		DESCRIPTION		"Description"
		::=  {  nptSecurityMacsecStatisticsCtrlPortEntry  2  }

	nptSecurityMacsecStatisticsCtrlPortRecOctets	OBJECT-TYPE	
		SYNTAX			Counter64
		MAX-ACCESS		read-only
		STATUS			current
		DESCRIPTION		"Description"
		::=  {  nptSecurityMacsecStatisticsCtrlPortEntry  3  }

	nptSecurityMacsecStatisticsCtrlPortRecPackets	OBJECT-TYPE	
		SYNTAX			Counter64
		MAX-ACCESS		read-only
		STATUS			current
		DESCRIPTION		"Description"
		::=  {  nptSecurityMacsecStatisticsCtrlPortEntry  4  }

	nptSecurityMacsecStatisticsCtrlPortRecUnicast	OBJECT-TYPE	
		SYNTAX			Counter64 
		MAX-ACCESS		read-only
		STATUS			current
		DESCRIPTION		"Description"
		::=  {  nptSecurityMacsecStatisticsCtrlPortEntry  5  }

    nptSecurityMacsecStatisticsCtrlPortRecMulticast	OBJECT-TYPE	
		SYNTAX			Counter64
		MAX-ACCESS		read-only
		STATUS			current
		DESCRIPTION		"Description"
		::=  {  nptSecurityMacsecStatisticsCtrlPortEntry  6  }

	nptSecurityMacsecStatisticsCtrlPortRecBroadcast	OBJECT-TYPE	
		SYNTAX			Counter64 
		MAX-ACCESS		read-only
		STATUS			current
		DESCRIPTION		"Description"
		::=  {  nptSecurityMacsecStatisticsCtrlPortEntry  7  }

	nptSecurityMacsecStatisticsCtrlPortRecDiscarded	OBJECT-TYPE	
		SYNTAX			Counter64
		MAX-ACCESS		read-only
		STATUS			current
		DESCRIPTION		"Description"
		::=  {  nptSecurityMacsecStatisticsCtrlPortEntry  8  }

	nptSecurityMacsecStatisticsCtrlPortRecError	OBJECT-TYPE	
		SYNTAX			Counter64
		MAX-ACCESS		read-only
		STATUS			current
		DESCRIPTION		"Description"
		::=  {  nptSecurityMacsecStatisticsCtrlPortEntry  9  }
		
		nptSecurityMacsecStatisticsCtrlPortTraOctets	OBJECT-TYPE	
		SYNTAX			Counter64
		MAX-ACCESS		read-only
		STATUS			current
		DESCRIPTION		"Description"
		::=  {  nptSecurityMacsecStatisticsCtrlPortEntry  10  }
		
		nptSecurityMacsecStatisticsCtrlPortTraPackets	OBJECT-TYPE	
		SYNTAX			Counter64
		MAX-ACCESS		read-only
		STATUS			current
		DESCRIPTION		"Description"
		::=  {  nptSecurityMacsecStatisticsCtrlPortEntry  11  }
		
		nptSecurityMacsecStatisticsCtrlPortTraUnicast	OBJECT-TYPE	
		SYNTAX			Counter64
		MAX-ACCESS		read-only
		STATUS			current
		DESCRIPTION		"Description"
		::=  {  nptSecurityMacsecStatisticsCtrlPortEntry  12  }
		
		nptSecurityMacsecStatisticsCtrlPortTraMulticast	OBJECT-TYPE	
		SYNTAX			Counter64
		MAX-ACCESS		read-only
		STATUS			current
		DESCRIPTION		"Description"
		::=  {  nptSecurityMacsecStatisticsCtrlPortEntry  13  }
		
		nptSecurityMacsecStatisticsCtrlPortTraBroadcast	OBJECT-TYPE	
		SYNTAX			Counter64
		MAX-ACCESS		read-only
		STATUS			current
		DESCRIPTION		"Description"
		::=  {  nptSecurityMacsecStatisticsCtrlPortEntry  14  }
		
		nptSecurityMacsecStatisticsCtrlPortTraError	OBJECT-TYPE	
		SYNTAX			Counter64
		MAX-ACCESS		read-only
		STATUS			current
		DESCRIPTION		"Description"
		::=  {  nptSecurityMacsecStatisticsCtrlPortEntry  15  }

		
	nptSecurityMacsecStatisticsUnctrlPortTable	OBJECT-TYPE	
		SYNTAX		SEQUENCE  OF  NptSecurityMacsecStatisticsUnctrlPortEntry
		MAX-ACCESS	not-accessible
		STATUS		current
		DESCRIPTION	"Description"
		::=  { nptSecurityMacsecStatisticsUnctrlPort  1 }

	nptSecurityMacsecStatisticsUnctrlPortEntry	OBJECT-TYPE
		SYNTAX		NptSecurityMacsecStatisticsUnctrlPortEntry
		MAX-ACCESS	not-accessible
		STATUS		current
		DESCRIPTION	"Description"
		INDEX		{  nptSecurityMacsecStatisticsUnctrlPortIndex  }
		::=  { nptSecurityMacsecStatisticsUnctrlPortTable 1 }

	NptSecurityMacsecStatisticsUnctrlPortEntry  ::=  SEQUENCE {
		nptSecurityMacsecStatisticsUnctrlPortIndex  Integer32,
		nptSecurityMacsecStatisticsUnctrlPortiMACPort  DisplayString,
		nptSecurityMacsecStatisticsUnctrlPortRecOctets  Counter64,
		nptSecurityMacsecStatisticsUnctrlPortRecUnicast  Counter64,
		nptSecurityMacsecStatisticsUnctrlPortRecMulticast  Counter64,
		nptSecurityMacsecStatisticsUnctrlPortRecBroadcast  Counter64,
		nptSecurityMacsecStatisticsUnctrlPortRecDiscarded  Counter64,
		nptSecurityMacsecStatisticsUnctrlPortRecError  Counter64,
		nptSecurityMacsecStatisticsUnctrlPortTraOctets  Counter64,
		nptSecurityMacsecStatisticsUnctrlPortTraUnicast  Counter64,
		nptSecurityMacsecStatisticsUnctrlPortTraMulticast  Counter64,
		nptSecurityMacsecStatisticsUnctrlPortTraBroadcast  Counter64,
		nptSecurityMacsecStatisticsUnctrlPortTraError  Counter64
		}


	nptSecurityMacsecStatisticsUnctrlPortIndex	OBJECT-TYPE	
		SYNTAX			Integer32  ( -2147483648 .. 2147483647  ) 
		MAX-ACCESS		read-only
		STATUS			current
		DESCRIPTION		"Description"
		::=  {  nptSecurityMacsecStatisticsUnctrlPortEntry  1  }

	nptSecurityMacsecStatisticsUnctrlPortiMACPort	OBJECT-TYPE	
		SYNTAX			DisplayString 
		MAX-ACCESS		read-only
		STATUS			current
		DESCRIPTION		"Description"
		::=  {  nptSecurityMacsecStatisticsUnctrlPortEntry  2  }

	nptSecurityMacsecStatisticsUnctrlPortRecOctets	OBJECT-TYPE	
		SYNTAX			Counter64
		MAX-ACCESS		read-only
		STATUS			current
		DESCRIPTION		"Description"
		::=  {  nptSecurityMacsecStatisticsUnctrlPortEntry  3  }

	nptSecurityMacsecStatisticsUnctrlPortRecUnicast	OBJECT-TYPE	
		SYNTAX			Counter64 
		MAX-ACCESS		read-only
		STATUS			current
		DESCRIPTION		"Description"
		::=  {  nptSecurityMacsecStatisticsUnctrlPortEntry  4  }

    nptSecurityMacsecStatisticsUnctrlPortRecMulticast	OBJECT-TYPE	
		SYNTAX			Counter64
		MAX-ACCESS		read-only
		STATUS			current
		DESCRIPTION		"Description"
		::=  {  nptSecurityMacsecStatisticsUnctrlPortEntry  5  }

	nptSecurityMacsecStatisticsUnctrlPortRecBroadcast	OBJECT-TYPE	
		SYNTAX			Counter64 
		MAX-ACCESS		read-only
		STATUS			current
		DESCRIPTION		"Description"
		::=  {  nptSecurityMacsecStatisticsUnctrlPortEntry  6  }

	nptSecurityMacsecStatisticsUnctrlPortRecDiscarded	OBJECT-TYPE	
		SYNTAX			Counter64
		MAX-ACCESS		read-only
		STATUS			current
		DESCRIPTION		"Description"
		::=  {  nptSecurityMacsecStatisticsUnctrlPortEntry  7  }

	nptSecurityMacsecStatisticsUnctrlPortRecError	OBJECT-TYPE	
		SYNTAX			Counter64
		MAX-ACCESS		read-only
		STATUS			current
		DESCRIPTION		"Description"
		::=  {  nptSecurityMacsecStatisticsUnctrlPortEntry  8  }
		
		nptSecurityMacsecStatisticsUnctrlPortTraOctets	OBJECT-TYPE	
		SYNTAX			Counter64
		MAX-ACCESS		read-only
		STATUS			current
		DESCRIPTION		"Description"
		::=  {  nptSecurityMacsecStatisticsUnctrlPortEntry  9  }
		
		nptSecurityMacsecStatisticsUnctrlPortTraUnicast	OBJECT-TYPE	
		SYNTAX			Counter64
		MAX-ACCESS		read-only
		STATUS			current
		DESCRIPTION		"Description"
		::=  {  nptSecurityMacsecStatisticsUnctrlPortEntry  10  }
		
		nptSecurityMacsecStatisticsUnctrlPortTraMulticast	OBJECT-TYPE	
		SYNTAX			Counter64
		MAX-ACCESS		read-only
		STATUS			current
		DESCRIPTION		"Description"
		::=  {  nptSecurityMacsecStatisticsUnctrlPortEntry  11  }
		
		nptSecurityMacsecStatisticsUnctrlPortTraBroadcast	OBJECT-TYPE	
		SYNTAX			Counter64
		MAX-ACCESS		read-only
		STATUS			current
		DESCRIPTION		"Description"
		::=  {  nptSecurityMacsecStatisticsUnctrlPortEntry  12  }
		
		nptSecurityMacsecStatisticsUnctrlPortTraError	OBJECT-TYPE	
		SYNTAX			Counter64
		MAX-ACCESS		read-only
		STATUS			current
		DESCRIPTION		"Description"
		::=  {  nptSecurityMacsecStatisticsUnctrlPortEntry  13  }



		
	nptSecurityMacsecStatisticsEAPolTable	OBJECT-TYPE	
		SYNTAX		SEQUENCE  OF  NptSecurityMacsecStatisticsEAPolEntry
		MAX-ACCESS	not-accessible
		STATUS		current
		DESCRIPTION	"Description"
		::=  { nptSecurityMacsecStatisticsEAPol  1 }

	nptSecurityMacsecStatisticsEAPolEntry	OBJECT-TYPE
		SYNTAX		NptSecurityMacsecStatisticsEAPolEntry
		MAX-ACCESS	not-accessible
		STATUS		current
		DESCRIPTION	"Description"
		INDEX		{  nptSecurityMacsecStatisticsEAPolIndex  }
		::=  { nptSecurityMacsecStatisticsEAPolTable 1 }

	NptSecurityMacsecStatisticsEAPolEntry  ::=  SEQUENCE {
		nptSecurityMacsecStatisticsEAPolIndex  Integer32,
		nptSecurityMacsecStatisticsEAPoliMACPort  DisplayString,
		nptSecurityMacsecStatisticsEAPolDiscontinuityTime  DisplayString,
		nptSecurityMacsecStatisticsEAPolElapsed  DisplayString,
		nptSecurityMacsecStatisticsEAPolInvalidEapol  Counter64,
		nptSecurityMacsecStatisticsEAPolEapLength  Counter64,
		nptSecurityMacsecStatisticsEAPolEapMkaNoCKN  Counter64,
		nptSecurityMacsecStatisticsEAPolEapMkaInvRx  Counter64,
		nptSecurityMacsecStatisticsEAPolEapMkaTx  Counter64
		}


	nptSecurityMacsecStatisticsEAPolIndex	OBJECT-TYPE	
		SYNTAX			Integer32  ( -2147483648 .. 2147483647  ) 
		MAX-ACCESS		read-only
		STATUS			current
		DESCRIPTION		"Description"
		::=  {  nptSecurityMacsecStatisticsEAPolEntry  1  }

	nptSecurityMacsecStatisticsEAPoliMACPort	OBJECT-TYPE	
		SYNTAX			DisplayString 
		MAX-ACCESS		read-only
		STATUS			current
		DESCRIPTION		"Description"
		::=  {  nptSecurityMacsecStatisticsEAPolEntry  2  }

	nptSecurityMacsecStatisticsEAPolDiscontinuityTime	OBJECT-TYPE	
		SYNTAX			DisplayString
		MAX-ACCESS		read-only
		STATUS			current
		DESCRIPTION		"Description"
		::=  {  nptSecurityMacsecStatisticsEAPolEntry  3  }

	nptSecurityMacsecStatisticsEAPolElapsed	OBJECT-TYPE	
		SYNTAX			DisplayString 
		MAX-ACCESS		read-only
		STATUS			current
		DESCRIPTION		"Description"
		::=  {  nptSecurityMacsecStatisticsEAPolEntry  4  }

    nptSecurityMacsecStatisticsEAPolInvalidEapol	OBJECT-TYPE	
		SYNTAX			Counter64
		MAX-ACCESS		read-only
		STATUS			current
		DESCRIPTION		"Description"
		::=  {  nptSecurityMacsecStatisticsEAPolEntry  5  }

	nptSecurityMacsecStatisticsEAPolEapLength	OBJECT-TYPE	
		SYNTAX			Counter64 
		MAX-ACCESS		read-only
		STATUS			current
		DESCRIPTION		"Description"
		::=  {  nptSecurityMacsecStatisticsEAPolEntry  6  }

	nptSecurityMacsecStatisticsEAPolEapMkaNoCKN	OBJECT-TYPE	
		SYNTAX			Counter64
		MAX-ACCESS		read-only
		STATUS			current
		DESCRIPTION		"Description"
		::=  {  nptSecurityMacsecStatisticsEAPolEntry  7  }

	nptSecurityMacsecStatisticsEAPolEapMkaInvRx	OBJECT-TYPE	
		SYNTAX			Counter64
		MAX-ACCESS		read-only
		STATUS			current
		DESCRIPTION		"Description"
		::=  {  nptSecurityMacsecStatisticsEAPolEntry  8  }
		
	nptSecurityMacsecStatisticsEAPolEapMkaTx	OBJECT-TYPE	
		SYNTAX			Counter64
		MAX-ACCESS		read-only
		STATUS			current
		DESCRIPTION		"Description"
		::=  {  nptSecurityMacsecStatisticsEAPolEntry  9  }
		

	nptSecurityMacsecStatisticsMACEntityTable	OBJECT-TYPE	
		SYNTAX		SEQUENCE  OF  NptSecurityMacsecStatisticsMACEntityEntry
		MAX-ACCESS	not-accessible
		STATUS		current
		DESCRIPTION	"Description"
		::=  { nptSecurityMacsecStatisticsMACEntity  1 }

	nptSecurityMacsecStatisticsMACEntityEntry	OBJECT-TYPE
		SYNTAX		NptSecurityMacsecStatisticsMACEntityEntry
		MAX-ACCESS	not-accessible
		STATUS		current
		DESCRIPTION	"Description"
		INDEX		{  nptSecurityMacsecStatisticsMACEntityIndex  }
		::=  { nptSecurityMacsecStatisticsMACEntityTable 1 }

	NptSecurityMacsecStatisticsMACEntityEntry  ::=  SEQUENCE {
		nptSecurityMacsecStatisticsMACEntityIndex  Integer32,
		nptSecurityMacsecStatisticsMACEntityiMACPort  DisplayString,
		nptSecurityMacsecStatisticsMACEntityRecUnTag  Counter64,
		nptSecurityMacsecStatisticsMACEntityRecNoTag  Counter64,
		nptSecurityMacsecStatisticsMACEntityRecBadTag  Counter64,
		nptSecurityMacsecStatisticsMACEntityRecUnknownSci  Counter64,
		nptSecurityMacsecStatisticsMACEntityRecNoSci  Counter64,
		nptSecurityMacsecStatisticsMACEntityRecOverrun  Counter64,
		nptSecurityMacsecStatisticsMACEntityRecValidat  Counter64,
		nptSecurityMacsecStatisticsMACEntityRecDecrypt  Counter64,
		nptSecurityMacsecStatisticsMACEntityTraUnTag  Counter64,
		nptSecurityMacsecStatisticsMACEntityTraLong  Counter64,
		nptSecurityMacsecStatisticsMACEntityTraProtect  Counter64,
		nptSecurityMacsecStatisticsMACEntityTraEncrypt  Counter64
		}


	nptSecurityMacsecStatisticsMACEntityIndex	OBJECT-TYPE	
		SYNTAX			Integer32  ( -2147483648 .. 2147483647  ) 
		MAX-ACCESS		read-only
		STATUS			current
		DESCRIPTION		"Description"
		::=  {  nptSecurityMacsecStatisticsMACEntityEntry  1  }

	nptSecurityMacsecStatisticsMACEntityiMACPort	OBJECT-TYPE	
		SYNTAX			DisplayString 
		MAX-ACCESS		read-only
		STATUS			current
		DESCRIPTION		"Description"
		::=  {  nptSecurityMacsecStatisticsMACEntityEntry  2  }

	nptSecurityMacsecStatisticsMACEntityRecUnTag	OBJECT-TYPE	
		SYNTAX			Counter64
		MAX-ACCESS		read-only
		STATUS			current
		DESCRIPTION		"Description"
		::=  {  nptSecurityMacsecStatisticsMACEntityEntry  3  }

	nptSecurityMacsecStatisticsMACEntityRecNoTag	OBJECT-TYPE	
		SYNTAX			Counter64 
		MAX-ACCESS		read-only
		STATUS			current
		DESCRIPTION		"Description"
		::=  {  nptSecurityMacsecStatisticsMACEntityEntry  4  }

    nptSecurityMacsecStatisticsMACEntityRecBadTag	OBJECT-TYPE	
		SYNTAX			Counter64
		MAX-ACCESS		read-only
		STATUS			current
		DESCRIPTION		"Description"
		::=  {  nptSecurityMacsecStatisticsMACEntityEntry  5  }

	nptSecurityMacsecStatisticsMACEntityRecUnknownSci	OBJECT-TYPE	
		SYNTAX			Counter64 
		MAX-ACCESS		read-only
		STATUS			current
		DESCRIPTION		"Description"
		::=  {  nptSecurityMacsecStatisticsMACEntityEntry  6  }

	nptSecurityMacsecStatisticsMACEntityRecNoSci	OBJECT-TYPE	
		SYNTAX			Counter64
		MAX-ACCESS		read-only
		STATUS			current
		DESCRIPTION		"Description"
		::=  {  nptSecurityMacsecStatisticsMACEntityEntry  7  }

	nptSecurityMacsecStatisticsMACEntityRecOverrun	OBJECT-TYPE	
		SYNTAX			Counter64
		MAX-ACCESS		read-only
		STATUS			current
		DESCRIPTION		"Description"
		::=  {  nptSecurityMacsecStatisticsMACEntityEntry  8  }
		
		nptSecurityMacsecStatisticsMACEntityRecValidat	OBJECT-TYPE	
		SYNTAX			Counter64
		MAX-ACCESS		read-only
		STATUS			current
		DESCRIPTION		"Description"
		::=  {  nptSecurityMacsecStatisticsMACEntityEntry  9  }
		
		nptSecurityMacsecStatisticsMACEntityRecDecrypt	OBJECT-TYPE	
		SYNTAX			Counter64
		MAX-ACCESS		read-only
		STATUS			current
		DESCRIPTION		"Description"
		::=  {  nptSecurityMacsecStatisticsMACEntityEntry  10  }
		
		nptSecurityMacsecStatisticsMACEntityTraUnTag	OBJECT-TYPE	
		SYNTAX			Counter64
		MAX-ACCESS		read-only
		STATUS			current
		DESCRIPTION		"Description"
		::=  {  nptSecurityMacsecStatisticsMACEntityEntry  11  }
		
		nptSecurityMacsecStatisticsMACEntityTraLong	OBJECT-TYPE	
		SYNTAX			Counter64
		MAX-ACCESS		read-only
		STATUS			current
		DESCRIPTION		"Description"
		::=  {  nptSecurityMacsecStatisticsMACEntityEntry  12  }
		
		nptSecurityMacsecStatisticsMACEntityTraProtect	OBJECT-TYPE	
		SYNTAX			Counter64
		MAX-ACCESS		read-only
		STATUS			current
		DESCRIPTION		"Description"
		::=  {  nptSecurityMacsecStatisticsMACEntityEntry  13  }
		
		nptSecurityMacsecStatisticsMACEntityTraEncrypt	OBJECT-TYPE	
		SYNTAX			Counter64
		MAX-ACCESS		read-only
		STATUS			current
		DESCRIPTION		"Description"
		::=  {  nptSecurityMacsecStatisticsMACEntityEntry  14  }
		



	nptSecurityMacsecStatisticsSecChanTable	OBJECT-TYPE	
		SYNTAX		SEQUENCE  OF  NptSecurityMacsecStatisticsSecChanEntry
		MAX-ACCESS	not-accessible
		STATUS		current
		DESCRIPTION	"Description"
		::=  { nptSecurityMacsecStatisticsSecChan  1 }

	nptSecurityMacsecStatisticsSecChanEntry	OBJECT-TYPE
		SYNTAX		NptSecurityMacsecStatisticsSecChanEntry
		MAX-ACCESS	not-accessible
		STATUS		current
		DESCRIPTION	"Description"
		INDEX		{  nptSecurityMacsecStatisticsSecChanIndex  }
		::=  { nptSecurityMacsecStatisticsSecChanTable 1 }

	NptSecurityMacsecStatisticsSecChanEntry  ::=  SEQUENCE {
		nptSecurityMacsecStatisticsSecChanIndex  Integer32,
		nptSecurityMacsecStatisticsSecChaniMACPort  DisplayString,
		nptSecurityMacsecStatisticsSecChanRecUncheck  Counter64,
		nptSecurityMacsecStatisticsSecChanRecDelay  Counter64,
		nptSecurityMacsecStatisticsSecChanRecLate  Counter64,
		nptSecurityMacsecStatisticsSecChanRecOk  Counter64,
		nptSecurityMacsecStatisticsSecChanRecInvalid  Counter64,
		nptSecurityMacsecStatisticsSecChanRecNotvalid  Counter64,
		nptSecurityMacsecStatisticsSecChanRecNotUsSa  Counter64,
		nptSecurityMacsecStatisticsSecChanRecUnusedSa  Counter64,
		nptSecurityMacsecStatisticsSecChanRecValidat  Counter64,
		nptSecurityMacsecStatisticsSecChanRecDecrypt  Counter64,
		nptSecurityMacsecStatisticsSecChanTraPktProtect  Counter64,
		nptSecurityMacsecStatisticsSecChanTraPktEncrypt  Counter64,
		nptSecurityMacsecStatisticsSecChanTraOctProtect  Counter64,
		nptSecurityMacsecStatisticsSecChanTraOctEncrypt  Counter64
		}


	nptSecurityMacsecStatisticsSecChanIndex	OBJECT-TYPE	
		SYNTAX			Integer32  ( -2147483648 .. 2147483647  ) 
		MAX-ACCESS		read-only
		STATUS			current
		DESCRIPTION		"Description"
		::=  {  nptSecurityMacsecStatisticsSecChanEntry  1  }

	nptSecurityMacsecStatisticsSecChaniMACPort	OBJECT-TYPE	
		SYNTAX			DisplayString 
		MAX-ACCESS		read-only
		STATUS			current
		DESCRIPTION		"Description"
		::=  {  nptSecurityMacsecStatisticsSecChanEntry  2  }

	nptSecurityMacsecStatisticsSecChanRecUncheck	OBJECT-TYPE	
		SYNTAX			Counter64
		MAX-ACCESS		read-only
		STATUS			current
		DESCRIPTION		"Description"
		::=  {  nptSecurityMacsecStatisticsSecChanEntry  3  }

	nptSecurityMacsecStatisticsSecChanRecDelay	OBJECT-TYPE	
		SYNTAX			Counter64 
		MAX-ACCESS		read-only
		STATUS			current
		DESCRIPTION		"Description"
		::=  {  nptSecurityMacsecStatisticsSecChanEntry  4  }

    nptSecurityMacsecStatisticsSecChanRecLate	OBJECT-TYPE	
		SYNTAX			Counter64
		MAX-ACCESS		read-only
		STATUS			current
		DESCRIPTION		"Description"
		::=  {  nptSecurityMacsecStatisticsSecChanEntry  5  }

	nptSecurityMacsecStatisticsSecChanRecOk	OBJECT-TYPE	
		SYNTAX			Counter64 
		MAX-ACCESS		read-only
		STATUS			current
		DESCRIPTION		"Description"
		::=  {  nptSecurityMacsecStatisticsSecChanEntry  6  }

	nptSecurityMacsecStatisticsSecChanRecInvalid	OBJECT-TYPE	
		SYNTAX			Counter64
		MAX-ACCESS		read-only
		STATUS			current
		DESCRIPTION		"Description"
		::=  {  nptSecurityMacsecStatisticsSecChanEntry  7  }

	nptSecurityMacsecStatisticsSecChanRecNotvalid	OBJECT-TYPE	
		SYNTAX			Counter64
		MAX-ACCESS		read-only
		STATUS			current
		DESCRIPTION		"Description"
		::=  {  nptSecurityMacsecStatisticsSecChanEntry  8  }
		
		nptSecurityMacsecStatisticsSecChanRecNotUsSa	OBJECT-TYPE	
		SYNTAX			Counter64
		MAX-ACCESS		read-only
		STATUS			current
		DESCRIPTION		"Description"
		::=  {  nptSecurityMacsecStatisticsSecChanEntry  9  }
		
		nptSecurityMacsecStatisticsSecChanRecUnusedSa	OBJECT-TYPE	
		SYNTAX			Counter64
		MAX-ACCESS		read-only
		STATUS			current
		DESCRIPTION		"Description"
		::=  {  nptSecurityMacsecStatisticsSecChanEntry  10  }
		
		nptSecurityMacsecStatisticsSecChanRecValidat	OBJECT-TYPE	
		SYNTAX			Counter64
		MAX-ACCESS		read-only
		STATUS			current
		DESCRIPTION		"Description"
		::=  {  nptSecurityMacsecStatisticsSecChanEntry  11  }
		
		nptSecurityMacsecStatisticsSecChanRecDecrypt	OBJECT-TYPE	
		SYNTAX			Counter64
		MAX-ACCESS		read-only
		STATUS			current
		DESCRIPTION		"Description"
		::=  {  nptSecurityMacsecStatisticsSecChanEntry  12  }
		
		nptSecurityMacsecStatisticsSecChanTraPktProtect	OBJECT-TYPE	
		SYNTAX			Counter64
		MAX-ACCESS		read-only
		STATUS			current
		DESCRIPTION		"Description"
		::=  {  nptSecurityMacsecStatisticsSecChanEntry  13  }
		
		nptSecurityMacsecStatisticsSecChanTraPktEncrypt	OBJECT-TYPE	
		SYNTAX			Counter64
		MAX-ACCESS		read-only
		STATUS			current
		DESCRIPTION		"Description"
		::=  {  nptSecurityMacsecStatisticsSecChanEntry  14  }
		nptSecurityMacsecStatisticsSecChanTraOctProtect	OBJECT-TYPE	
		SYNTAX			Counter64
		MAX-ACCESS		read-only
		STATUS			current
		DESCRIPTION		"Description"
		::=  {  nptSecurityMacsecStatisticsSecChanEntry  15  }
		nptSecurityMacsecStatisticsSecChanTraOctEncrypt	OBJECT-TYPE	
		SYNTAX			Counter64
		MAX-ACCESS		read-only
		STATUS			current
		DESCRIPTION		"Description"
		::=  {  nptSecurityMacsecStatisticsSecChanEntry  16  }



		
	nptSecurityMkaStatisticsErrorTable	OBJECT-TYPE	
		SYNTAX		SEQUENCE  OF  NptSecurityMkaStatisticsErrorEntry
		MAX-ACCESS	not-accessible
		STATUS		current
		DESCRIPTION	"Description"
		::=  { nptSecurityMkaStatisticsError  1 }

	nptSecurityMkaStatisticsErrorEntry	OBJECT-TYPE
		SYNTAX		NptSecurityMkaStatisticsErrorEntry
		MAX-ACCESS	not-accessible
		STATUS		current
		DESCRIPTION	"Description"
		INDEX		{  nptSecurityMkaStatisticsErrorIndex  }
		::=  { nptSecurityMkaStatisticsErrorTable 1 }

	NptSecurityMkaStatisticsErrorEntry  ::=  SEQUENCE {
		nptSecurityMkaStatisticsErrorIndex  Integer32,
		nptSecurityMkaStatisticsErrorSakGeneration  Counter64,
		nptSecurityMkaStatisticsErrorSakEncryption  Counter64,
		nptSecurityMkaStatisticsErrorSakDecryption  Counter64,
		nptSecurityMkaStatisticsErrorCaGeneration  Counter64,
		nptSecurityMkaStatisticsErrorCaEncryption  Counter64,
		nptSecurityMkaStatisticsErrorCaDecryption  Counter64,
		nptSecurityMkaStatisticsErrorCaCakDeriv  Counter64,
		nptSecurityMkaStatisticsErrorCaCknDeriv  Counter64,
		nptSecurityMkaStatisticsErrorCaIckDeriv  Counter64,
		nptSecurityMkaStatisticsErrorCaKekDeriv  Counter64,
		nptSecurityMkaStatisticsErrorCaCapability  Counter64,
		nptSecurityMkaStatisticsErrorMacRxSC  Counter64,
		nptSecurityMkaStatisticsErrorMacTxSC  Counter64,
		nptSecurityMkaStatisticsErrorMacRxSA  Counter64,
		nptSecurityMkaStatisticsErrorMacTxSA  Counter64,
		nptSecurityMkaStatisticsErrorMkpduTx  Counter64,
		nptSecurityMkaStatisticsErrorMkpduRx  Counter64,
		nptSecurityMkaStatisticsErrorMkpduRxBadMN  Counter64,
		nptSecurityMkaStatisticsErrorMkpduRxNonMN  Counter64
		}


	nptSecurityMkaStatisticsErrorIndex	OBJECT-TYPE	
		SYNTAX			Integer32  ( -2147483648 .. 2147483647  ) 
		MAX-ACCESS		read-only
		STATUS			current
		DESCRIPTION		"Description"
		::=  {  nptSecurityMkaStatisticsErrorEntry  1  }

	nptSecurityMkaStatisticsErrorSakGeneration	OBJECT-TYPE	
		SYNTAX			Counter64 
		MAX-ACCESS		read-only
		STATUS			current
		DESCRIPTION		"Description"
		::=  {  nptSecurityMkaStatisticsErrorEntry  2  }

	nptSecurityMkaStatisticsErrorSakEncryption	OBJECT-TYPE	
		SYNTAX			Counter64
		MAX-ACCESS		read-only
		STATUS			current
		DESCRIPTION		"Description"
		::=  {  nptSecurityMkaStatisticsErrorEntry  3  }

	nptSecurityMkaStatisticsErrorSakDecryption	OBJECT-TYPE	
		SYNTAX			Counter64 
		MAX-ACCESS		read-only
		STATUS			current
		DESCRIPTION		"Description"
		::=  {  nptSecurityMkaStatisticsErrorEntry  4  }

    nptSecurityMkaStatisticsErrorCaGeneration	OBJECT-TYPE	
		SYNTAX			Counter64
		MAX-ACCESS		read-only
		STATUS			current
		DESCRIPTION		"Description"
		::=  {  nptSecurityMkaStatisticsErrorEntry  5  }

	nptSecurityMkaStatisticsErrorCaEncryption	OBJECT-TYPE	
		SYNTAX			Counter64 
		MAX-ACCESS		read-only
		STATUS			current
		DESCRIPTION		"Description"
		::=  {  nptSecurityMkaStatisticsErrorEntry  6  }

	nptSecurityMkaStatisticsErrorCaDecryption	OBJECT-TYPE	
		SYNTAX			Counter64
		MAX-ACCESS		read-only
		STATUS			current
		DESCRIPTION		"Description"
		::=  {  nptSecurityMkaStatisticsErrorEntry  7  }

	nptSecurityMkaStatisticsErrorCaCakDeriv	OBJECT-TYPE	
		SYNTAX			Counter64
		MAX-ACCESS		read-only
		STATUS			current
		DESCRIPTION		"Description"
		::=  {  nptSecurityMkaStatisticsErrorEntry  8  }
		
		nptSecurityMkaStatisticsErrorCaCknDeriv	OBJECT-TYPE	
		SYNTAX			Counter64
		MAX-ACCESS		read-only
		STATUS			current
		DESCRIPTION		"Description"
		::=  {  nptSecurityMkaStatisticsErrorEntry  9  }
		
		nptSecurityMkaStatisticsErrorCaIckDeriv	OBJECT-TYPE	
		SYNTAX			Counter64
		MAX-ACCESS		read-only
		STATUS			current
		DESCRIPTION		"Description"
		::=  {  nptSecurityMkaStatisticsErrorEntry  10  }
		
		nptSecurityMkaStatisticsErrorCaKekDeriv	OBJECT-TYPE	
		SYNTAX			Counter64
		MAX-ACCESS		read-only
		STATUS			current
		DESCRIPTION		"Description"
		::=  {  nptSecurityMkaStatisticsErrorEntry  11  }
		
		nptSecurityMkaStatisticsErrorCaCapability	OBJECT-TYPE	
		SYNTAX			Counter64
		MAX-ACCESS		read-only
		STATUS			current
		DESCRIPTION		"Description"
		::=  {  nptSecurityMkaStatisticsErrorEntry  12  }
		
		nptSecurityMkaStatisticsErrorMacRxSC	OBJECT-TYPE	
		SYNTAX			Counter64
		MAX-ACCESS		read-only
		STATUS			current
		DESCRIPTION		"Description"
		::=  {  nptSecurityMkaStatisticsErrorEntry  13  }
		
		nptSecurityMkaStatisticsErrorMacTxSC	OBJECT-TYPE	
		SYNTAX			Counter64
		MAX-ACCESS		read-only
		STATUS			current
		DESCRIPTION		"Description"
		::=  {  nptSecurityMkaStatisticsErrorEntry  14  }
		nptSecurityMkaStatisticsErrorMacRxSA	OBJECT-TYPE	
		SYNTAX			Counter64
		MAX-ACCESS		read-only
		STATUS			current
		DESCRIPTION		"Description"
		::=  {  nptSecurityMkaStatisticsErrorEntry  15  }
		nptSecurityMkaStatisticsErrorMacTxSA	OBJECT-TYPE	
		SYNTAX			Counter64
		MAX-ACCESS		read-only
		STATUS			current
		DESCRIPTION		"Description"
		::=  {  nptSecurityMkaStatisticsErrorEntry  16  }
		nptSecurityMkaStatisticsErrorMkpduTx	OBJECT-TYPE	
		SYNTAX			Counter64
		MAX-ACCESS		read-only
		STATUS			current
		DESCRIPTION		"Description"
		::=  {  nptSecurityMkaStatisticsErrorEntry  17  }
		nptSecurityMkaStatisticsErrorMkpduRx	OBJECT-TYPE	
		SYNTAX			Counter64
		MAX-ACCESS		read-only
		STATUS			current
		DESCRIPTION		"Description"
		::=  {  nptSecurityMkaStatisticsErrorEntry  18  }
		nptSecurityMkaStatisticsErrorMkpduRxBadMN	OBJECT-TYPE	
		SYNTAX			Counter64
		MAX-ACCESS		read-only
		STATUS			current
		DESCRIPTION		"Description"
		::=  {  nptSecurityMkaStatisticsErrorEntry  19  }
		nptSecurityMkaStatisticsErrorMkpduRxNonMN	OBJECT-TYPE	
		SYNTAX			Counter64
		MAX-ACCESS		read-only
		STATUS			current
		DESCRIPTION		"Description"
		::=  {  nptSecurityMkaStatisticsErrorEntry  20  }



		
	nptSecurityMkaStatisticsGlobalTable	OBJECT-TYPE	
		SYNTAX		SEQUENCE  OF  NptSecurityMkaStatisticsGlobalEntry
		MAX-ACCESS	not-accessible
		STATUS		current
		DESCRIPTION	"Description"
		::=  { nptSecurityMkaStatisticsGlobal  1 }

	nptSecurityMkaStatisticsGlobalEntry	OBJECT-TYPE
		SYNTAX		NptSecurityMkaStatisticsGlobalEntry
		MAX-ACCESS	not-accessible
		STATUS		current
		DESCRIPTION	"Row Description"
		INDEX		{  nptSecurityMkaStatisticsGlobalIndex  }
		::=  { nptSecurityMkaStatisticsGlobalTable 1 }

	NptSecurityMkaStatisticsGlobalEntry  ::=  SEQUENCE {
		nptSecurityMkaStatisticsGlobalIndex  Integer32,
		nptSecurityMkaStatisticsGlobalMkaSecured  Counter64,
		nptSecurityMkaStatisticsGlobalMkaAttempts  Counter64,
		nptSecurityMkaStatisticsGlobalMkaDelSecured  Counter64,
		nptSecurityMkaStatisticsGlobalMkaTimeouts  Counter64,
		nptSecurityMkaStatisticsGlobalCaDerived  Counter64,
		nptSecurityMkaStatisticsGlobalCaRekeys  Counter64,
		nptSecurityMkaStatisticsGlobalCaGenerated  Counter64,
		nptSecurityMkaStatisticsGlobalCaReceived  Counter64,
		nptSecurityMkaStatisticsGlobalSaGenerated  Counter64,
		nptSecurityMkaStatisticsGlobalSaRekeyed  Counter64,
		nptSecurityMkaStatisticsGlobalSaReceived  Counter64,
		nptSecurityMkaStatisticsGlobalSaResponses  Counter64,
		nptSecurityMkaStatisticsGlobalMkpduRx  Counter64,
		nptSecurityMkaStatisticsGlobalMkpduRxSAK  Counter64,
		nptSecurityMkaStatisticsGlobalMkpduRxCAK  Counter64,
		nptSecurityMkaStatisticsGlobalMkpduTx  Counter64,
		nptSecurityMkaStatisticsGlobalMkpduTxSAK  Counter64,
		nptSecurityMkaStatisticsGlobalMkpduTxCAK  Counter64
		}


	nptSecurityMkaStatisticsGlobalIndex	OBJECT-TYPE	
		SYNTAX			Integer32  ( -2147483648 .. 2147483647  ) 
		MAX-ACCESS		read-only
		STATUS			current
		DESCRIPTION		"Description"
		::=  {  nptSecurityMkaStatisticsGlobalEntry  1  }

	nptSecurityMkaStatisticsGlobalMkaSecured	OBJECT-TYPE	
		SYNTAX			Counter64 
		MAX-ACCESS		read-only
		STATUS			current
		DESCRIPTION		"Description"
		::=  {  nptSecurityMkaStatisticsGlobalEntry  2  }

	nptSecurityMkaStatisticsGlobalMkaAttempts	OBJECT-TYPE	
		SYNTAX			Counter64
		MAX-ACCESS		read-only
		STATUS			current
		DESCRIPTION		"Description"
		::=  {  nptSecurityMkaStatisticsGlobalEntry  3  }

	nptSecurityMkaStatisticsGlobalMkaDelSecured	OBJECT-TYPE	
		SYNTAX			Counter64 
		MAX-ACCESS		read-only
		STATUS			current
		DESCRIPTION		"Description"
		::=  {  nptSecurityMkaStatisticsGlobalEntry  4  }

    nptSecurityMkaStatisticsGlobalMkaTimeouts	OBJECT-TYPE	
		SYNTAX			Counter64
		MAX-ACCESS		read-only
		STATUS			current
		DESCRIPTION		"Description"
		::=  {  nptSecurityMkaStatisticsGlobalEntry  5  }

	nptSecurityMkaStatisticsGlobalCaDerived	OBJECT-TYPE	
		SYNTAX			Counter64 
		MAX-ACCESS		read-only
		STATUS			current
		DESCRIPTION		"Description"
		::=  {  nptSecurityMkaStatisticsGlobalEntry  6  }

	nptSecurityMkaStatisticsGlobalCaRekeys	OBJECT-TYPE	
		SYNTAX			Counter64
		MAX-ACCESS		read-only
		STATUS			current
		DESCRIPTION		"Description"
		::=  {  nptSecurityMkaStatisticsGlobalEntry  7  }

	nptSecurityMkaStatisticsGlobalCaGenerated	OBJECT-TYPE	
		SYNTAX			Counter64
		MAX-ACCESS		read-only
		STATUS			current
		DESCRIPTION		"Description"
		::=  {  nptSecurityMkaStatisticsGlobalEntry  8  }
		
		nptSecurityMkaStatisticsGlobalCaReceived	OBJECT-TYPE	
		SYNTAX			Counter64
		MAX-ACCESS		read-only
		STATUS			current
		DESCRIPTION		"Description"
		::=  {  nptSecurityMkaStatisticsGlobalEntry  9  }
		
		nptSecurityMkaStatisticsGlobalSaGenerated	OBJECT-TYPE	
		SYNTAX			Counter64
		MAX-ACCESS		read-only
		STATUS			current
		DESCRIPTION		"Description"
		::=  {  nptSecurityMkaStatisticsGlobalEntry  10  }
		
		nptSecurityMkaStatisticsGlobalSaRekeyed	OBJECT-TYPE	
		SYNTAX			Counter64
		MAX-ACCESS		read-only
		STATUS			current
		DESCRIPTION		"Description"
		::=  {  nptSecurityMkaStatisticsGlobalEntry  11  }
		
		nptSecurityMkaStatisticsGlobalSaReceived	OBJECT-TYPE	
		SYNTAX			Counter64
		MAX-ACCESS		read-only
		STATUS			current
		DESCRIPTION		"Description"
		::=  {  nptSecurityMkaStatisticsGlobalEntry  12  }
		
		nptSecurityMkaStatisticsGlobalSaResponses	OBJECT-TYPE	
		SYNTAX			Counter64
		MAX-ACCESS		read-only
		STATUS			current
		DESCRIPTION		"Description"
		::=  {  nptSecurityMkaStatisticsGlobalEntry  13  }
		
		nptSecurityMkaStatisticsGlobalMkpduRx	OBJECT-TYPE	
		SYNTAX			Counter64
		MAX-ACCESS		read-only
		STATUS			current
		DESCRIPTION		"Description"
		::=  {  nptSecurityMkaStatisticsGlobalEntry  14  }
		nptSecurityMkaStatisticsGlobalMkpduRxSAK	OBJECT-TYPE	
		SYNTAX			Counter64
		MAX-ACCESS		read-only
		STATUS			current
		DESCRIPTION		"Description"
		::=  {  nptSecurityMkaStatisticsGlobalEntry  15  }
		nptSecurityMkaStatisticsGlobalMkpduRxCAK	OBJECT-TYPE	
		SYNTAX			Counter64
		MAX-ACCESS		read-only
		STATUS			current
		DESCRIPTION		"Description"
		::=  {  nptSecurityMkaStatisticsGlobalEntry  16  }
		nptSecurityMkaStatisticsGlobalMkpduTx	OBJECT-TYPE	
		SYNTAX			Counter64
		MAX-ACCESS		read-only
		STATUS			current
		DESCRIPTION		"Description"
		::=  {  nptSecurityMkaStatisticsGlobalEntry  17  }
		nptSecurityMkaStatisticsGlobalMkpduTxSAK	OBJECT-TYPE	
		SYNTAX			Counter64
		MAX-ACCESS		read-only
		STATUS			current
		DESCRIPTION		"Description"
		::=  {  nptSecurityMkaStatisticsGlobalEntry  18  }
		nptSecurityMkaStatisticsGlobalMkpduTxCAK	OBJECT-TYPE	
		SYNTAX			Counter64
		MAX-ACCESS		read-only
		STATUS			current
		DESCRIPTION		"Description"
		::=  {  nptSecurityMkaStatisticsGlobalEntry  19  }



	nptSmartSfpEthPortStatisticsTable	OBJECT-TYPE
		SYNTAX		SEQUENCE  OF  NptSmartSfpEthPortStatisticsEntry
		MAX-ACCESS	not-accessible
		STATUS		current
		DESCRIPTION	"Description"
		::=  { nptSmartSfpEthPortStatistics  1 }

	nptSmartSfpEthPortStatisticsEntry	OBJECT-TYPE
		SYNTAX		NptSmartSfpEthPortStatisticsEntry
		MAX-ACCESS	not-accessible
		STATUS		current
		DESCRIPTION	"Row Description"
		INDEX		{  nptSmartSfpEthPortStatisticsIndex  }
		::=  { nptSmartSfpEthPortStatisticsTable 1 }

	NptSmartSfpEthPortStatisticsEntry  ::=  SEQUENCE {
		nptSmartSfpEthPortStatisticsIndex  Integer32,
		nptSmartSfpEthPortStatisticsSlot  DisplayString,
		nptSmartSfpEthPortStatisticsPortName  DisplayString,
		nptSmartSfpEthPortStatisticsDiscontinuityTime  DisplayString,
        nptSmartSfpEthPortStatisticsElapsed  DisplayString,
		nptSmartSfpEthPortStatisticsRxOctets  Counter64,
		nptSmartSfpEthPortStatisticsRxPkts  Counter64,
		nptSmartSfpEthPortStatisticsRxErroredFCSPkts  Counter64,
		nptSmartSfpEthPortStatisticsRxUnicastPkts  Counter64,
		nptSmartSfpEthPortStatisticsRxBroadcastPkts  Counter64,
		nptSmartSfpEthPortStatisticsRxMulticastPkts  Counter64,
		nptSmartSfpEthPortStatisticsTxOctets  Counter64,
		nptSmartSfpEthPortStatisticsTxPkts  Counter64,
        nptSmartSfpEthPortStatisticsTxUnicastPkts  Counter64,
        nptSmartSfpEthPortStatisticsTxBroadcastPkts  Counter64,
		nptSmartSfpEthPortStatisticsTxMulticastPkts  Counter64,
        nptSmartSfpEthPortStatisticsRxUndersizePkts  Counter64,
        nptSmartSfpEthPortStatisticsRxOversizePkts  Counter64,
		nptSmartSfpEthPortStatisticsRxFragments  Counter64,
        nptSmartSfpEthPortStatisticsRxJabberPkts  Counter64,
        nptSmartSfpEthPortStatisticsRxVidMismatchPkts  Counter64
		}


	nptSmartSfpEthPortStatisticsIndex	OBJECT-TYPE	
		SYNTAX			Integer32  ( -2147483648 .. 2147483647  ) 
		MAX-ACCESS		read-only
		STATUS			current
		DESCRIPTION		"Column Description"
		::=  {  nptSmartSfpEthPortStatisticsEntry  1  }

	nptSmartSfpEthPortStatisticsSlot	OBJECT-TYPE	
		SYNTAX			DisplayString 
		MAX-ACCESS		read-only
		STATUS			current
		DESCRIPTION		"Description"
		::=  {  nptSmartSfpEthPortStatisticsEntry  2  }

	nptSmartSfpEthPortStatisticsPortName	OBJECT-TYPE	
		SYNTAX			DisplayString
		MAX-ACCESS		read-only
		STATUS			current
		DESCRIPTION		"Description"
		::=  {  nptSmartSfpEthPortStatisticsEntry  3  }

    nptSmartSfpEthPortStatisticsDiscontinuityTime	OBJECT-TYPE	
        SYNTAX			DisplayString
        MAX-ACCESS		read-only
        STATUS			current
        DESCRIPTION		"Description"
        ::=  {  nptSmartSfpEthPortStatisticsEntry  5  }

    nptSmartSfpEthPortStatisticsElapsed	OBJECT-TYPE	
        SYNTAX			DisplayString 
        MAX-ACCESS		read-only
        STATUS			current
        DESCRIPTION		"Description"
        ::=  {  nptSmartSfpEthPortStatisticsEntry  6  }

    nptSmartSfpEthPortStatisticsRxOctets	OBJECT-TYPE	
        SYNTAX			Counter64
        MAX-ACCESS		read-only
        STATUS			current
        DESCRIPTION		"Description"
        ::=  {  nptSmartSfpEthPortStatisticsEntry  7  }

    nptSmartSfpEthPortStatisticsRxPkts	OBJECT-TYPE	
        SYNTAX			Counter64
        MAX-ACCESS		read-only
        STATUS			current
        DESCRIPTION		"Description"
        ::=  {  nptSmartSfpEthPortStatisticsEntry  8  }
        
    nptSmartSfpEthPortStatisticsRxErroredFCSPkts	OBJECT-TYPE	
        SYNTAX			Counter64
        MAX-ACCESS		read-only
        STATUS			current
        DESCRIPTION		"Description"
        ::=  {  nptSmartSfpEthPortStatisticsEntry  9  }
    
    nptSmartSfpEthPortStatisticsRxUnicastPkts	OBJECT-TYPE	
        SYNTAX			Counter64
        MAX-ACCESS		read-only
        STATUS			current
        DESCRIPTION		"Description"
        ::=  {  nptSmartSfpEthPortStatisticsEntry  10  }
    
    nptSmartSfpEthPortStatisticsRxBroadcastPkts	OBJECT-TYPE	
        SYNTAX			Counter64
        MAX-ACCESS		read-only
        STATUS			current
        DESCRIPTION		"Description"
        ::=  {  nptSmartSfpEthPortStatisticsEntry  11  }
    
    nptSmartSfpEthPortStatisticsRxMulticastPkts	OBJECT-TYPE	
        SYNTAX			Counter64
        MAX-ACCESS		read-only
        STATUS			current
        DESCRIPTION		"Description"
        ::=  {  nptSmartSfpEthPortStatisticsEntry  12  }
    
    nptSmartSfpEthPortStatisticsTxOctets	OBJECT-TYPE	
        SYNTAX			Counter64
        MAX-ACCESS		read-only
        STATUS			current
        DESCRIPTION		"Description"
        ::=  {  nptSmartSfpEthPortStatisticsEntry  13  }

    nptSmartSfpEthPortStatisticsTxPkts	OBJECT-TYPE	
        SYNTAX			Counter64
        MAX-ACCESS		read-only
        STATUS			current
        DESCRIPTION		"Description"
        ::=  {  nptSmartSfpEthPortStatisticsEntry  14  }

    nptSmartSfpEthPortStatisticsTxUnicastPkts	OBJECT-TYPE	
        SYNTAX			Counter64
        MAX-ACCESS		read-only
        STATUS			current
        DESCRIPTION		"Description"
        ::=  {  nptSmartSfpEthPortStatisticsEntry  15  }
        
    nptSmartSfpEthPortStatisticsTxBroadcastPkts	OBJECT-TYPE	
        SYNTAX			Counter64
        MAX-ACCESS		read-only
        STATUS			current
        DESCRIPTION		"Description"
        ::=  {  nptSmartSfpEthPortStatisticsEntry  16  }
    
    nptSmartSfpEthPortStatisticsTxMulticastPkts	OBJECT-TYPE	
        SYNTAX			Counter64
        MAX-ACCESS		read-only
        STATUS			current
        DESCRIPTION		"Description"
        ::=  {  nptSmartSfpEthPortStatisticsEntry  17  }
    
    nptSmartSfpEthPortStatisticsRxUndersizePkts	OBJECT-TYPE	
        SYNTAX			Counter64
        MAX-ACCESS		read-only
        STATUS			current
        DESCRIPTION		"Description"
        ::=  {  nptSmartSfpEthPortStatisticsEntry  18  }
    
    nptSmartSfpEthPortStatisticsRxOversizePkts	OBJECT-TYPE	
        SYNTAX			Counter64
        MAX-ACCESS		read-only
        STATUS			current
        DESCRIPTION		"Description"
        ::=  {  nptSmartSfpEthPortStatisticsEntry  19  }
    
    nptSmartSfpEthPortStatisticsRxFragments	OBJECT-TYPE	
        SYNTAX			Counter64
        MAX-ACCESS		read-only
        STATUS			current
        DESCRIPTION		"Description"
        ::=  {  nptSmartSfpEthPortStatisticsEntry  20  }

    nptSmartSfpEthPortStatisticsRxJabberPkts	OBJECT-TYPE	
        SYNTAX			Counter64
        MAX-ACCESS		read-only
        STATUS			current
        DESCRIPTION		"Description"
        ::=  {  nptSmartSfpEthPortStatisticsEntry  21  }

    nptSmartSfpEthPortStatisticsRxVidMismatchPkts	OBJECT-TYPE	
        SYNTAX			Counter64
        MAX-ACCESS		read-only
        STATUS			current
        DESCRIPTION		"Description"
        ::=  {  nptSmartSfpEthPortStatisticsEntry  22  }
        

	nptSmartSfpStmPortStatisticsTable	OBJECT-TYPE
		SYNTAX		SEQUENCE  OF  NptSmartSfpStmPortStatisticsEntry
		MAX-ACCESS	not-accessible
		STATUS		current
		DESCRIPTION	"Description"
		::=  { nptSmartSfpStmPortStatistics  1 }

	nptSmartSfpStmPortStatisticsEntry	OBJECT-TYPE
		SYNTAX		NptSmartSfpStmPortStatisticsEntry
		MAX-ACCESS	not-accessible
		STATUS		current
		DESCRIPTION	"Row Description"
		INDEX		{  nptSmartSfpStmPortStatisticsIndex  }
		::=  { nptSmartSfpStmPortStatisticsTable 1 }

	NptSmartSfpStmPortStatisticsEntry  ::=  SEQUENCE {
		nptSmartSfpStmPortStatisticsIndex  Integer32,
		nptSmartSfpStmPortStatisticsSlot  DisplayString,
		nptSmartSfpStmPortStatisticsPortName  DisplayString,
		nptSmartSfpStmPortStatisticsDiscontinuityTime  DisplayString,
        nptSmartSfpStmPortStatisticsElapsed  DisplayString,
		nptSmartSfpStmPortStatisticsRSBBEorCVS  Counter64
		}


	nptSmartSfpStmPortStatisticsIndex	OBJECT-TYPE	
		SYNTAX			Integer32  ( -2147483648 .. 2147483647  ) 
		MAX-ACCESS		read-only
		STATUS			current
		DESCRIPTION		"Column Description"
		::=  {  nptSmartSfpStmPortStatisticsEntry  1  }

	nptSmartSfpStmPortStatisticsSlot	OBJECT-TYPE	
		SYNTAX			DisplayString 
		MAX-ACCESS		read-only
		STATUS			current
		DESCRIPTION		"Description"
		::=  {  nptSmartSfpStmPortStatisticsEntry  2  }

	nptSmartSfpStmPortStatisticsPortName	OBJECT-TYPE	
		SYNTAX			DisplayString
		MAX-ACCESS		read-only
		STATUS			current
		DESCRIPTION		"Description"
		::=  {  nptSmartSfpStmPortStatisticsEntry  3  }

    nptSmartSfpStmPortStatisticsDiscontinuityTime	OBJECT-TYPE	
        SYNTAX			DisplayString
        MAX-ACCESS		read-only
        STATUS			current
        DESCRIPTION		"Description"
        ::=  {  nptSmartSfpStmPortStatisticsEntry  5  }

    nptSmartSfpStmPortStatisticsElapsed	OBJECT-TYPE	
        SYNTAX			DisplayString 
        MAX-ACCESS		read-only
        STATUS			current
        DESCRIPTION		"Description"
        ::=  {  nptSmartSfpStmPortStatisticsEntry  6  }

    nptSmartSfpStmPortStatisticsRSBBEorCVS	OBJECT-TYPE	
        SYNTAX			Counter64
        MAX-ACCESS		read-only
        STATUS			current
        DESCRIPTION		"Description"
        ::=  {  nptSmartSfpStmPortStatisticsEntry  7  }


	nptSmartSfpE1PortStatisticsTable	OBJECT-TYPE
		SYNTAX		SEQUENCE  OF  NptSmartSfpE1PortStatisticsEntry
		MAX-ACCESS	not-accessible
		STATUS		current
		DESCRIPTION	"Description"
		::=  { nptSmartSfpE1PortStatistics  1 }

	nptSmartSfpE1PortStatisticsEntry	OBJECT-TYPE
		SYNTAX		NptSmartSfpE1PortStatisticsEntry
		MAX-ACCESS	not-accessible
		STATUS		current
		DESCRIPTION	"Row Description"
		INDEX		{  nptSmartSfpE1PortStatisticsIndex  }
		::=  { nptSmartSfpE1PortStatisticsTable 1 }

	NptSmartSfpE1PortStatisticsEntry  ::=  SEQUENCE {
		nptSmartSfpE1PortStatisticsIndex  Integer32,
		nptSmartSfpE1PortStatisticsSlot  DisplayString,
		nptSmartSfpE1PortStatisticsPortName  DisplayString,
		nptSmartSfpE1PortStatisticsDiscontinuityTime  DisplayString,
        nptSmartSfpE1PortStatisticsElapsed  DisplayString,
		nptSmartSfpE1PortStatisticsE1CV  Counter64
		}


	nptSmartSfpE1PortStatisticsIndex	OBJECT-TYPE	
		SYNTAX			Integer32  ( -2147483648 .. 2147483647  ) 
		MAX-ACCESS		read-only
		STATUS			current
		DESCRIPTION		"Column Description"
		::=  {  nptSmartSfpE1PortStatisticsEntry  1  }

	nptSmartSfpE1PortStatisticsSlot	OBJECT-TYPE	
		SYNTAX			DisplayString 
		MAX-ACCESS		read-only
		STATUS			current
		DESCRIPTION		"Description"
		::=  {  nptSmartSfpE1PortStatisticsEntry  2  }

	nptSmartSfpE1PortStatisticsPortName	OBJECT-TYPE	
		SYNTAX			DisplayString
		MAX-ACCESS		read-only
		STATUS			current
		DESCRIPTION		"Description"
		::=  {  nptSmartSfpE1PortStatisticsEntry  3  }

    nptSmartSfpE1PortStatisticsDiscontinuityTime	OBJECT-TYPE	
        SYNTAX			DisplayString
        MAX-ACCESS		read-only
        STATUS			current
        DESCRIPTION		"Description"
        ::=  {  nptSmartSfpE1PortStatisticsEntry  5  }

    nptSmartSfpE1PortStatisticsElapsed	OBJECT-TYPE	
        SYNTAX			DisplayString 
        MAX-ACCESS		read-only
        STATUS			current
        DESCRIPTION		"Description"
        ::=  {  nptSmartSfpE1PortStatisticsEntry  6  }

    nptSmartSfpE1PortStatisticsE1CV	OBJECT-TYPE	
        SYNTAX			Counter64
        MAX-ACCESS		read-only
        STATUS			current
        DESCRIPTION		"Description"
        ::=  {  nptSmartSfpE1PortStatisticsEntry  7  }


	nptSmartSfpCesStatisticsTable	OBJECT-TYPE
		SYNTAX		SEQUENCE  OF  NptSmartSfpCesStatisticsEntry
		MAX-ACCESS	not-accessible
		STATUS		current
		DESCRIPTION	"Description"
		::=  { nptSmartSfpCesStatistics  1 }

	nptSmartSfpCesStatisticsEntry	OBJECT-TYPE
		SYNTAX		NptSmartSfpCesStatisticsEntry
		MAX-ACCESS	not-accessible
		STATUS		current
		DESCRIPTION	"Row Description"
		INDEX		{  nptSmartSfpCesStatisticsIndex  }
		::=  { nptSmartSfpCesStatisticsTable 1 }

	NptSmartSfpCesStatisticsEntry  ::=  SEQUENCE {
		nptSmartSfpCesStatisticsIndex  Integer32,
		nptSmartSfpCesStatisticsInterfaceName  DisplayString,
		nptSmartSfpCesStatisticsDiscontinuityTime  DisplayString,
        nptSmartSfpCesStatisticsElapsed  DisplayString,
		nptSmartSfpCesStatisticsTxPsnPkts  Counter64,
		nptSmartSfpCesStatisticsRxPsnPkts  Counter64,
		nptSmartSfpCesStatisticsRxPsnReorderPkts  Counter64,
		nptSmartSfpCesStatisticsRxPsnMisorderedPkts  Counter64,
		nptSmartSfpCesStatisticsRxPsnMalformDiscardPkts  Counter64,
		nptSmartSfpCesStatisticsRxPsnLostPkts  Counter64,
		nptSmartSfpCesStatisticsRxPsnOverrunDiscardPkts  Counter64,
		nptSmartSfpCesStatisticsRxPsnUnderrunPkts  Counter64,
        nptSmartSfpCesStatisticsPlayedOutPkts  Counter64
		}


	nptSmartSfpCesStatisticsIndex	OBJECT-TYPE	
		SYNTAX			Integer32  ( -2147483648 .. 2147483647  ) 
		MAX-ACCESS		read-only
		STATUS			current
		DESCRIPTION		"Column Description"
		::=  {  nptSmartSfpCesStatisticsEntry  1  }

	nptSmartSfpCesStatisticsInterfaceName	OBJECT-TYPE	
		SYNTAX			DisplayString
		MAX-ACCESS		read-only
		STATUS			current
		DESCRIPTION		"Description"
		::=  {  nptSmartSfpCesStatisticsEntry  2  }

    nptSmartSfpCesStatisticsDiscontinuityTime	OBJECT-TYPE	
        SYNTAX			DisplayString
        MAX-ACCESS		read-only
        STATUS			current
        DESCRIPTION		"Description"
        ::=  {  nptSmartSfpCesStatisticsEntry  3  }

    nptSmartSfpCesStatisticsElapsed	OBJECT-TYPE	
        SYNTAX			DisplayString 
        MAX-ACCESS		read-only
        STATUS			current
        DESCRIPTION		"Description"
        ::=  {  nptSmartSfpCesStatisticsEntry  4  }

    nptSmartSfpCesStatisticsTxPsnPkts	OBJECT-TYPE	
        SYNTAX			Counter64
        MAX-ACCESS		read-only
        STATUS			current
        DESCRIPTION		"Description"
        ::=  {  nptSmartSfpCesStatisticsEntry  5  }

    nptSmartSfpCesStatisticsRxPsnPkts	OBJECT-TYPE	
        SYNTAX			Counter64
        MAX-ACCESS		read-only
        STATUS			current
        DESCRIPTION		"Description"
        ::=  {  nptSmartSfpCesStatisticsEntry  6  }
        
    nptSmartSfpCesStatisticsRxPsnReorderPkts	OBJECT-TYPE	
        SYNTAX			Counter64
        MAX-ACCESS		read-only
        STATUS			current
        DESCRIPTION		"Description"
        ::=  {  nptSmartSfpCesStatisticsEntry  7  }
    
    nptSmartSfpCesStatisticsRxPsnMisorderedPkts	OBJECT-TYPE	
        SYNTAX			Counter64
        MAX-ACCESS		read-only
        STATUS			current
        DESCRIPTION		"Description"
        ::=  {  nptSmartSfpCesStatisticsEntry  8  }
    
    nptSmartSfpCesStatisticsRxPsnMalformDiscardPkts	OBJECT-TYPE	
        SYNTAX			Counter64
        MAX-ACCESS		read-only
        STATUS			current
        DESCRIPTION		"Description"
        ::=  {  nptSmartSfpCesStatisticsEntry  9  }
    
    nptSmartSfpCesStatisticsRxPsnLostPkts	OBJECT-TYPE	
        SYNTAX			Counter64
        MAX-ACCESS		read-only
        STATUS			current
        DESCRIPTION		"Description"
        ::=  {  nptSmartSfpCesStatisticsEntry  10  }
    
    nptSmartSfpCesStatisticsRxPsnOverrunDiscardPkts	OBJECT-TYPE	
        SYNTAX			Counter64
        MAX-ACCESS		read-only
        STATUS			current
        DESCRIPTION		"Description"
        ::=  {  nptSmartSfpCesStatisticsEntry  11  }

    nptSmartSfpCesStatisticsRxPsnUnderrunPkts	OBJECT-TYPE	
        SYNTAX			Counter64
        MAX-ACCESS		read-only
        STATUS			current
        DESCRIPTION		"Description"
        ::=  {  nptSmartSfpCesStatisticsEntry  12  }

    nptSmartSfpCesStatisticsPlayedOutPkts	OBJECT-TYPE	
        SYNTAX			Counter64
        MAX-ACCESS		read-only
        STATUS			current
        DESCRIPTION		"Description"
        ::=  {  nptSmartSfpCesStatisticsEntry  13  }


END
