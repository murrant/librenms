-- File Name : NPT-TRAP-MIB
-- Date      : Thu Jun 09 18:50:03 CST 2011
-- Author    : AdventNet Agent Toolkit C Edition - MibEditor 6



NPT-TRAP-MIB	DEFINITIONS ::= BEGIN
	IMPORTS
		nptTrap
			FROM NPT-ROOT-MIB
		RowStatus, DateAndTime, TEXTUAL-CONVENTION, DisplayString
			FROM SNMPv2-TC
		DisplayString
			FROM RFC1213-MIB
		MODULE-IDENTITY, OBJECT-TYPE, Integer32, enterprises, NOTIFICATION-TYPE
			FROM SNMPv2-SMI
        nptObjectId, nptAlarmId, nptAlarmName, nptAlarmDescription, nptAlarmSeverity, nptAlarmType, nptNeId, nptAlarmTimeStamp, nptAlarmAddtionalinfo
            FROM NPT-ALARM-MIB;
            
   nptEquipmentDetected NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Equipment card detected"
        ::= { nptTrap 2000 }

   nptEquipmentSwapIn NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Equipment swapped in"
        ::= { nptTrap 2001 }

   nptEquipmentSwapOut NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Equipment swapped out"
        ::= { nptTrap 2002 }

   nptTypeUnknown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Equipment type unknown"
        ::= { nptTrap 2003 }

   nptEquipmentMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Equipment type mismatch"
        ::= { nptTrap 2004 }

   nptCardUnderutilized NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Reassignable to high capacity card"
        ::= { nptTrap 2005 }

   nptHwRevMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "HW Revision mismatched"
        ::= { nptTrap 2006 }

   nptEquipmentOut NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Equipment out"
        ::= { nptTrap 2007 }

   nptCardFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Card HW Fail"
        ::= { nptTrap 2008 }

   nptPowerFailures NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Power supply failures"
        ::= { nptTrap 2009 }

   nptTempHigh NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "High temperature"
        ::= { nptTrap 2010 }

   nptTempHighWarning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "High temperature warning"
        ::= { nptTrap 2011 }

   nptTempLow NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Low temperature"
        ::= { nptTrap 2012 }

   nptTempLowWarning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Low temperature warning"
        ::= { nptTrap 2013 }

   nptLockOpen NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Lock mechanism unlocked"
        ::= { nptTrap 2014 }

   nptPoeOverVoltage NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PoE power supply over-voltage"
        ::= { nptTrap 2015 }

   nptPoeUnderVoltage NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PoE power supply under-voltage"
        ::= { nptTrap 2016 }

   nptPoeVoltageLow NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PoE Power supply low than"
        ::= { nptTrap 2017 }

   nptBitFailed NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Built-in test: HW failed"
        ::= { nptTrap 2018 }

   nptBitNotOk NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Built-in test: input signal failed or degraded."
        ::= { nptTrap 2019 }

   nptBitDegraded NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Built-in test: HW degraded"
        ::= { nptTrap 2020 }

   nptBitSlightlyDegraded NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Built-in test: HW slightly degraded"
        ::= { nptTrap 2021 }

   nptCommunicationFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Low layer communication failed"
        ::= { nptTrap 2022 }

   nptCardCtrlFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Card Not Responding to MCP"
        ::= { nptTrap 2023 }

   nptCardPatchInstallFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Patch installation failed"
        ::= { nptTrap 2024 }

   nptVersionMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SW version mismatched"
        ::= { nptTrap 2025 }

   nptCfgRestoreSuccess NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Configuration recovered successfully"
        ::= { nptTrap 2026 }

   nptCfgRestoreFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Configuration recovery failed"
        ::= { nptTrap 2027 }

   nptCfgInconsistency NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Card configuration inconsistent with MCP"
        ::= { nptTrap 2028 }

   nptWarmReset NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Warm reset happened"
        ::= { nptTrap 2029 }

   nptColdReset NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Cold reset happened"
        ::= { nptTrap 2030 }

   nptCardReassigned NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Card reassigned"
        ::= { nptTrap 2031 }

   nptCardReassignNotification NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Card reassign notification"
        ::= { nptTrap 2032 }

   nptCpuUtilizationHigh NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CPU utilization over threshold Alert"
        ::= { nptTrap 2033 }

   nptFreeMemLow NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Memory usage over threshold Alert"
        ::= { nptTrap 2034 }

   nptMemFragmentation NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Max memory block size lower than threshold"
        ::= { nptTrap 2035 }

   nptFreeNvmLow NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NVM usage over threshold Alert"
        ::= { nptTrap 2036 }

   nptDcInFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "No Power input"
        ::= { nptTrap 2037 }

   nptDcInAFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "No power input at port A"
        ::= { nptTrap 2038 }

   nptDcInBFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "No power input at port B"
        ::= { nptTrap 2039 }

   nptFanFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Fan fail"
        ::= { nptTrap 2040 }

   nptFanFilterChangeReminder NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Fan filter cleaning Alert"
        ::= { nptTrap 2041 }

   nptFanFilterMissing NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Fan Filter is missing"
        ::= { nptTrap 2042 }

   nptEnvTempHigh NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Environment temperature High"
        ::= { nptTrap 2043 }

   nptEnvTempLow NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Environment temperature Low"
        ::= { nptTrap 2044 }

   nptExtAlm1 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "External alarm input #1"
        ::= { nptTrap 2045 }

   nptExtAlm2 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "External alarm input #2"
        ::= { nptTrap 2046 }

   nptExtAlm3 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "External alarm input #3"
        ::= { nptTrap 2047 }

   nptExtAlm4 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "External alarm input #4"
        ::= { nptTrap 2048 }

   nptHaSwitchover NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Switch over happened"
        ::= { nptTrap 2049 }

   nptCardProtectionSwitch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Card protection switch happened"
        ::= { nptTrap 2050 }

   nptNvmOut NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NVM is swapped out"
        ::= { nptTrap 2051 }

   nptNvmLockOpen NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NVM cover not locked"
        ::= { nptTrap 2052 }

   nptNvmReplaced NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NVM is replaced"
        ::= { nptTrap 2053 }

   nptSyncChannelDisconnected NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Sync Channel Disconnected"
        ::= { nptTrap 2054 }

   nptCfgSyncFailed NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CFG Sync Failed"
        ::= { nptTrap 2055 }

   nptDpAuditOverwriteFai NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DP Configuration Audit Failed"
        ::= { nptTrap 2056 }

   nptStandbySyncChannelDisconnected NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Sync Channel Disconnected"
        ::= { nptTrap 2057 }

   nptHeatUpRapidly NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Ambient temperature changes rapidly"
        ::= { nptTrap 2058 }

   nptIdmMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Object ID mismatched"
        ::= { nptTrap 2059 }

   nptDefaultMacInUse NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Default base MAC is used in DP"
        ::= { nptTrap 2060 }

   nptDcOutFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "No DC power output"
        ::= { nptTrap 2061 }

   nptPs48vOutFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "No 48v power output"
        ::= { nptTrap 2062 }

   nptFanPsFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "No 12v power to FAN"
        ::= { nptTrap 2063 }

   nptReassignFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Reassign operation is failed"
        ::= { nptTrap 2064 }

   nptReassignSuccess NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Reassign operation is successful"
        ::= { nptTrap 2065 }

   nptDyingGasp NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The equipment is going power down"
        ::= { nptTrap 2066 }

   nptMcp2npHeartbeatFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MCP to NP Heart beat detection is failed."
        ::= { nptTrap 2067 }

   nptFanInTurbo NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The fans are running at full speed"
        ::= { nptTrap 2068 }

   nptPtpDpMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "HW not support high accuracy PTP"
        ::= { nptTrap 2069 }

   nptHwRevNeedApproval NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Card usage restricted due to limitation in HW revision"
        ::= { nptTrap 2070 }

   nptCardOperstateDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Card operational state is down"
        ::= { nptTrap 2071 }

   nptPowerInAnomaly NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Transient power-in anomaly"
        ::= { nptTrap 2072 }

   nptGnssWarmReset NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "GNSS Warm reset happened"
        ::= { nptTrap 2073 }

   nptGnssColdReset NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "GNSS Cold reset happened"
        ::= { nptTrap 2074 }

   nptGnssRestoreFactorySet NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "GNSS restores to factory setting"
        ::= { nptTrap 2075 }

   nptResetRequestPending NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Reset action Required"
        ::= { nptTrap 2076 }

   nptSsfpMacMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The smart SFP has a wrong MAC address compared to the hosting port"
        ::= { nptTrap 2077 }

   nptPartIdVerifyFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PART-ID verification failed"
        ::= { nptTrap 2200 }

   nptTypeMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Transceiver type mismatched"
        ::= { nptTrap 2201 }

   nptAppcodeMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Application code mismatched"
        ::= { nptTrap 2202 }

   nptWavelengthMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Wavelength mismatched"
        ::= { nptTrap 2203 }

   nptTxPowerHigh NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx Power High"
        ::= { nptTrap 2204 }

   nptTxPowerLow NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx Power Low"
        ::= { nptTrap 2205 }

   nptRxPowerHigh NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Rx Power High"
        ::= { nptTrap 2206 }

   nptRxPowerLow NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Rx PowerLow"
        ::= { nptTrap 2207 }

   nptTxLaserBiasHigh NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx-Laser-Bias-High"
        ::= { nptTrap 2208 }

   nptTxLaserBiasLow NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx-Laser-Bias-Low"
        ::= { nptTrap 2209 }

   nptTxLaserBiasHighWarning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx-Laser-Bias-High-Warning"
        ::= { nptTrap 2210 }

   nptTxLaserBiasLowWarning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx-Laser-Bias-Low-Warning"
        ::= { nptTrap 2211 }

   nptTxPowerHighWarning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx-Power-High-Warning"
        ::= { nptTrap 2212 }

   nptTxPowerLowWarning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx-Power-Low-Warning"
        ::= { nptTrap 2213 }

   nptRxPowerHighWarning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Rx-Power-High-Warning"
        ::= { nptTrap 2214 }

   nptRxPowerLowWarning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Rx-Power-Low-Warning"
        ::= { nptTrap 2215 }

   nptRxLos NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of signal"
        ::= { nptTrap 2216 }

   nptLowInputOsnr NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Low Input OSNR"
        ::= { nptTrap 2217 }

   nptSwRxPowerHigh NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Used defined Rx Power High"
        ::= { nptTrap 2218 }

   nptSwRxPowerLow NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "User defined Rx Power Low"
        ::= { nptTrap 2219 }

   nptSwTxPowerHigh NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "User defined Tx Power High"
        ::= { nptTrap 2220 }

   nptSwTxPowerLow NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "User defined Tx Power Low"
        ::= { nptTrap 2221 }

   nptTransceiverLicenseNotAvailable NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Transceiver-License-Not-Available"
        ::= { nptTrap 2222 }

   nptMcpStartFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MCP failed to start up"
        ::= { nptTrap 2300 }

   nptMcpStartInDebug NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The MCP is started in debug mode"
        ::= { nptTrap 2301 }

   nptHwCfgSyncSuspect NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "HW configuration may be inconsistent with configuration DB"
        ::= { nptTrap 2302 }

   nptNeRestartNotification NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NE-Restart-Notification"
        ::= { nptTrap 2303 }

   nptNeUpgradeNotification NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NE-Upgrade-Notification"
        ::= { nptTrap 2304 }

   nptStandbySwMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Standby-SW-Mismatch"
        ::= { nptTrap 2305 }

   nptStandbyCfgSyncFailed NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Standby-CFG-Sync-Failed"
        ::= { nptTrap 2306 }

   nptNeDbUpdate NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NE-DB-update"
        ::= { nptTrap 2307 }

   nptPatchUpdate NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Patch-update"
        ::= { nptTrap 2308 }

   nptSystemError NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "System-Error"
        ::= { nptTrap 2309 }

   nptSystemFault NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "System-Fault"
        ::= { nptTrap 2310 }

   nptCfgSaveFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Cfg-Save-Fail"
        ::= { nptTrap 2311 }

   nptCfgDbIntegrity NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CFG-DB-Integrity"
        ::= { nptTrap 2312 }

   nptVersionActivationFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Version-activation-fail"
        ::= { nptTrap 2313 }

   nptPatchActivationFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Patch-activation-fail"
        ::= { nptTrap 2314 }

   nptLctMasterLogin NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LCT-Master-Login"
        ::= { nptTrap 2316 }

   nptLctMasterRequest NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LCT-Master-Request"
        ::= { nptTrap 2317 }

   nptLctMasterLogout NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LCT-Master-Logout"
        ::= { nptTrap 2318 }

   nptCliLogin NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CLI-Login"
        ::= { nptTrap 2319 }

   nptCliLogout NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CLI-Logout"
        ::= { nptTrap 2320 }

   nptCliInConfigMode NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CLI-In-Config-Mode"
        ::= { nptTrap 2321 }

   nptCliExitConfigMode NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CLI-Exit-Config-Mode"
        ::= { nptTrap 2322 }

   nptSecurityVerifyFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Security-verify-fail"
        ::= { nptTrap 2323 }

   nptCliConfigRequest NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CLI-Config-Request"
        ::= { nptTrap 2324 }

   nptCliConfigUpdate NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CLI-Config-Update"
        ::= { nptTrap 2325 }

   nptRtcRequest NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "RTC-Request"
        ::= { nptTrap 2326 }

   nptRtcChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "RTC-Change"
        ::= { nptTrap 2327 }

   nptMngPortDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Gateway NE uplink is down"
        ::= { nptTrap 2328 }

   nptShelfReplaced NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Shelf-Replaced"
        ::= { nptTrap 2329 }

   nptEShelfDetected NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "E-Shelf-Detected"
        ::= { nptTrap 2330 }

   nptPwrConsumptionTcAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PWR-Consumption-TC-Alarm"
        ::= { nptTrap 2331 }

   nptPwrConsumptionTcWarning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PWR-Consumption-TC-Warning"
        ::= { nptTrap 2332 }

   nptLicenseToBeExpired NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Temporary license will expire in 30 days"
        ::= { nptTrap 2333 }

   nptLicenseExpired NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "License expired"
        ::= { nptTrap 2334 }

   nptLicenseUpdate NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "License status changed"
        ::= { nptTrap 2335 }

   nptLicenseRetrieved NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Permanent License retrieved"
        ::= { nptTrap 2336 }

   nptStandbyStatusSyncFailed NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Standby Status Synchronization failed"
        ::= { nptTrap 2337 }

   nptBothMatrixStandby NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Both matrix cards become standby"
        ::= { nptTrap 2338 }

   nptDbCorrupted NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NE Configuration DB corrupted"
        ::= { nptTrap 2339 }

   nptStandbyMcpSyncFailed NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Standby-RCPD-Commit-Failed"
        ::= { nptTrap 2340 }

   nptLicenseStatusUnknown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Licensing status unknown"
        ::= { nptTrap 2341 }

   nptNeUpgradeSuspended NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Upgrade getting suspended"
        ::= { nptTrap 2343 }

   nptBootFromUsb NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NE is booted from USB"
        ::= { nptTrap 2344 }

   nptUpgradePending NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Manual upgrade request is pending"
        ::= { nptTrap 2346 }

   nptMuRequestUrge NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Urge notification to complete MU ASAP"
        ::= { nptTrap 2347 }

   nptShelfNotInstalled NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "E-Shelf-Not-Installed"
        ::= { nptTrap 2450 }

   nptUnknowMbpType NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Unknow-E-MBP-Type"
        ::= { nptTrap 2451 }

   nptMbpTypeMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MBP-Type-Mismatch"
        ::= { nptTrap 2452 }

   nptZtiNptRegister NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ZTI event for EMS to adopt me"
        ::= { nptTrap 2453 }

   nptSdcCfgSyncFailed NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Configuration Sync failed in SDC"
        ::= { nptTrap 2454 }

   nptLti1 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "0th timing source: Loss of Timing Input"
        ::= { nptTrap 2500 }

   nptOor1 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "0th timing source: Input Clock frequency Out Of Range"
        ::= { nptTrap 2501 }

   nptLti2 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "1st timing source: Loss of Timing Input"
        ::= { nptTrap 2502 }

   nptOor2 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "1st timing source: Input Clock frequency Out Of Range"
        ::= { nptTrap 2503 }

   nptLti3 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "3rd: timing source: Loss of Timing Input"
        ::= { nptTrap 2504 }

   nptOor3 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "2nd timing source: Input Clock frequency Out Of Range"
        ::= { nptTrap 2505 }

   nptLti4 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "3rd timing source: Loss of Timing Input"
        ::= { nptTrap 2506 }

   nptOor4 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "3rd timing source: Input Clock frequency Out Of Range"
        ::= { nptTrap 2507 }

   nptT3Lof NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of frame on E1/T1"
        ::= { nptTrap 2508 }

   nptT3Ais NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "T3 AIS on 2048Kbit/s or 1544Kbit/s"
        ::= { nptTrap 2509 }

   nptT3BitLos NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "T3  Input LOS on E1 or T1;"
        ::= { nptTrap 2510 }

   nptT3HzLos NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "T3  Input LOS on 2048KHz"
        ::= { nptTrap 2511 }

   nptT4Lto NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "T4 output cut-off"
        ::= { nptTrap 2512 }

   nptTmuAllSourcesLost NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "No available timing source"
        ::= { nptTrap 2513 }

   nptTimingSourceSwitch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "TMU Synchronization source changed"
        ::= { nptTrap 2514 }

   nptTimingModeSwitch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "TMU work mode changed"
        ::= { nptTrap 2515 }

   nptQlChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "TMU quality level changed"
        ::= { nptTrap 2516 }

   nptLol NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of lock"
        ::= { nptTrap 2517 }

   nptQlLow1 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Quality level low of priority 1 timing source"
        ::= { nptTrap 2518 }

   nptQlLow2 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Quality level low of priority 2 timing source"
        ::= { nptTrap 2519 }

   nptQlLow3 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Quality level low of priority 3 timing source"
        ::= { nptTrap 2520 }

   nptQlLow4 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Quality level low of priority 4 timing source"
        ::= { nptTrap 2521 }

   nptT0FreqTca NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Current timing reference frequency offset TCA"
        ::= { nptTrap 2522 }

   nptTmuHwFailure NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Timing unit HW failure"
        ::= { nptTrap 2523 }

   nptPtpSlaveUnlocked NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Slave not locked to master"
        ::= { nptTrap 2600 }

   nptPtpMasterUnlocked NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Master not locked to timing source"
        ::= { nptTrap 2601 }

   nptOnePpsLoss NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "1PPS loss of signal"
        ::= { nptTrap 2602 }

   nptAnnounceLoss NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Announce Packets Loss"
        ::= { nptTrap 2604 }

   nptSyncOrFollowupLoss NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Sync or FollowUp Packets Loss"
        ::= { nptTrap 2605 }

   nptDelayRespLoss NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Delay Response Packets Loss"
        ::= { nptTrap 2606 }

   nptSlavePortSwitching NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The fails or degrade of primary time reference PTP port, the switching of synchronization source"
        ::= { nptTrap 2612 }

   nptGmSwitching NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "GM Clock Switching Event"
        ::= { nptTrap 2613 }

   nptTimeStateSwitching NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Time State Switching Event"
        ::= { nptTrap 2614 }

   nptTodLoss NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of TOD Rx"
        ::= { nptTrap 2618 }

   nptLossOf10mhz NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of 10MHz signal input"
        ::= { nptTrap 2619 }

   nptPpiLos NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of signal on PDH physical interface"
        ::= { nptTrap 3000 }

   nptPpiRAis NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Alarm Indication Signal (AIS) detected in PDH line Rx direction"
        ::= { nptTrap 3001 }

   nptPpiTAis NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Sending AIS in PDH line Tx direction"
        ::= { nptTrap 3002 }

   nptCvtc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 15 Minutes Threshold Crossing Near End"
        ::= { nptTrap 3050 }

   nptCvtc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 24 Hours Threshold Crossing Near End"
        ::= { nptTrap 3051 }

   nptE1Ais NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Alarm indication signal of E1"
        ::= { nptTrap 3100 }

   nptE1Lof NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of Frame"
        ::= { nptTrap 3101 }

   nptE1CasLomf NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of CAS multi-Frame(only For PCM30)"
        ::= { nptTrap 3102 }

   nptE1CrcLomf NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of CRC-4 multi-Frame(only For PCM with CRC)"
        ::= { nptTrap 3103 }

   nptE1Rai NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Remote Alarm Indication (only For Framed Mode)"
        ::= { nptTrap 3104 }

   nptE1Sd NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "2M Signal Degrade"
        ::= { nptTrap 3105 }

   nptE1Exc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "2M Excessive Bit Error"
        ::= { nptTrap 3106 }

   nptSpiLos NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SDH Physical Interface Loss of Signal"
        ::= { nptTrap 3200 }

   nptSpiTf NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SDH Physical InterfaceTransmit Failure"
        ::= { nptTrap 3201 }

   nptRsLof NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Regenerator Section Loss of Frame"
        ::= { nptTrap 3202 }

   nptRsOof NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Regenerator Section Out of Frame"
        ::= { nptTrap 3203 }

   nptRsTim NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Regenerator Section Trace Identification(J0) Mismatch"
        ::= { nptTrap 3204 }

   nptRsUatNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS Start Near End"
        ::= { nptTrap 3205 }

   nptRsEstc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 15 Minutes Threshold Crossing Near End"
        ::= { nptTrap 3206 }

   nptRsSestc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 15 Minutes Threshold Crossing Near End"
        ::= { nptTrap 3207 }

   nptRsBbetc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 15 Minutes Threshold Crossing Near End"
        ::= { nptTrap 3208 }

   nptRsUastc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 15 Minutes Threshold Crossing Near End"
        ::= { nptTrap 3209 }

   nptRsOfstc15m NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OFS in 15 Minutes Threshold Crossing"
        ::= { nptTrap 3210 }

   nptRsEstc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 24 Hours Threshold Crossing Near End"
        ::= { nptTrap 3211 }

   nptRsSestc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 24 Hours Threshold Crossing Near End"
        ::= { nptTrap 3212 }

   nptRsBbetc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 24 Hours Threshold Crossing Near End"
        ::= { nptTrap 3213 }

   nptRsUastc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 24 Hours Threshold Crossing Near End"
        ::= { nptTrap 3214 }

   nptRsOfstc24h NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OFS in 24 Hours Threshold Crossing"
        ::= { nptTrap 3215 }

   nptMsAis NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Multiplex Section Alarm Indication Signal"
        ::= { nptTrap 3216 }

   nptMsRdi NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Multiplex Section Remote Defect Indication"
        ::= { nptTrap 3217 }

   nptMsSd NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MS Signal Degrade due to BER exceeding SD threshold"
        ::= { nptTrap 3218 }

   nptMsExc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MS Excessive Bit Error and exceeds SF threshold"
        ::= { nptTrap 3219 }

   nptMsplPm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Linear MSP Protocol mismatch"
        ::= { nptTrap 3220 }

   nptMsplApsFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Linear MSP APS controller is not working as expected"
        ::= { nptTrap 3221 }

   nptMsProtectionSwitch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MS protection switch event(for MSP 1+1)"
        ::= { nptTrap 3222 }

   nptMsUatNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS Start Near End"
        ::= { nptTrap 3223 }

   nptMsUatFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS Start Far End"
        ::= { nptTrap 3224 }

   nptMsEstc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 15 Minutes Threshold Crossing Near End"
        ::= { nptTrap 3225 }

   nptMsSestc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 15 Minutes Threshold Crossing Near End"
        ::= { nptTrap 3226 }

   nptMsBbetc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 15 Minutes Threshold Crossing Near End"
        ::= { nptTrap 3227 }

   nptMsUastc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 15 Minutes Threshold Crossing Near End"
        ::= { nptTrap 3228 }

   nptMsEstc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 15 Minutes Threshold Crossing Far End"
        ::= { nptTrap 3229 }

   nptMsSestc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 15 Minutes Threshold Crossing Far End"
        ::= { nptTrap 3230 }

   nptMsBbetc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 15 Minutes Threshold Crossing Far End"
        ::= { nptTrap 3231 }

   nptMsUastc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 15 Minutes Threshold Crossing Far End"
        ::= { nptTrap 3232 }

   nptMsEstc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 24 Hours Threshold Crossing Near End"
        ::= { nptTrap 3233 }

   nptMsSestc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 24 Hours Threshold Crossing Near End"
        ::= { nptTrap 3234 }

   nptMsBbetc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 24 Hours Threshold Crossing Near End"
        ::= { nptTrap 3235 }

   nptMsUastc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 24 Hours Threshold Crossing Near End"
        ::= { nptTrap 3236 }

   nptMsEstc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 24 Hours Threshold Crossing Far End"
        ::= { nptTrap 3237 }

   nptMsSestc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 24 Hours Threshold Crossing Far End"
        ::= { nptTrap 3238 }

   nptMsBbetc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 24 Hours Threshold Crossing Far End"
        ::= { nptTrap 3239 }

   nptMsUastc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS IN 24 Hours Threshold Crossing Far End"
        ::= { nptTrap 3240 }

   nptSmdTxLof NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx LOF from PSN to TDM direction on TSoP Smart SFP Device"
        ::= { nptTrap 3241 }

   nptAuLop NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Administration Unit Loss of Pointer"
        ::= { nptTrap 3300 }

   nptHpLom NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "High Order Path Loss of Multi-frame"
        ::= { nptTrap 3301 }

   nptHpAis NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "High Order Path Alarm Indication Signal"
        ::= { nptTrap 3302 }

   nptHpRdi NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "High Order Path Remote Defect Indication"
        ::= { nptTrap 3303 }

   nptHpTim NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "High Order Path Trace Identification(J1) Mismatch"
        ::= { nptTrap 3304 }

   nptHpUneq NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "High Order Path Unequipped"
        ::= { nptTrap 3305 }

   nptHpSlm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "High Order Path Signal Label(C2) Mismatch"
        ::= { nptTrap 3306 }

   nptHpSd NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VC-4 Signal Degrade"
        ::= { nptTrap 3307 }

   nptHpExc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VC-4 Excessive Bit Error (Cross SF threshold)"
        ::= { nptTrap 3308 }

   nptUatNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS Start Near End"
        ::= { nptTrap 3350 }

   nptUatFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS Start Far End"
        ::= { nptTrap 3351 }

   nptEstc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 15 Minutes Threshold Crossing Near End"
        ::= { nptTrap 3352 }

   nptSestc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 15 Minutes Threshold Crossing Near End"
        ::= { nptTrap 3353 }

   nptBbetc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 15 Minutes Threshold Crossing Near End"
        ::= { nptTrap 3354 }

   nptUastc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 15 Minutes Threshold Crossing Near End"
        ::= { nptTrap 3355 }

   nptEstc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 15 Minutes Threshold Crossing Far End"
        ::= { nptTrap 3356 }

   nptSestc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 15 Minutes Threshold Crossing Far End"
        ::= { nptTrap 3357 }

   nptBbetc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 15 Minutes Threshold Crossing Far End"
        ::= { nptTrap 3358 }

   nptUastc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 15 Minutes Threshold Crossing Far End"
        ::= { nptTrap 3359 }

   nptEstc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 24 Hours Threshold Crossing Near End"
        ::= { nptTrap 3362 }

   nptSestc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 24 Hours Threshold Crossing Near End"
        ::= { nptTrap 3363 }

   nptBbetc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 24 Hours Threshold Crossing Near End"
        ::= { nptTrap 3364 }

   nptUastc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 24 Hours Threshold Crossing Near End"
        ::= { nptTrap 3365 }

   nptEstc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 24 Hours Threshold Crossing Far End"
        ::= { nptTrap 3366 }

   nptSestc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 24 Hours Threshold Crossing Far End"
        ::= { nptTrap 3367 }

   nptBbetc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BBE in 24 Hours Threshold Crossing Far End"
        ::= { nptTrap 3368 }

   nptUastc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS IN 24 Hours Threshold Crossing Far End"
        ::= { nptTrap 3369 }

   nptTuLop NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tributary Unit Loss of Pointer"
        ::= { nptTrap 3400 }

   nptLpAis NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Low Order Path Alarm Indication Signal"
        ::= { nptTrap 3401 }

   nptLpRdi NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Low Order Path Remote Defect Indication"
        ::= { nptTrap 3402 }

   nptLpTim NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Low Order Path Trace Identification Mismatch"
        ::= { nptTrap 3403 }

   nptLpUneq NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Low Order Path Unequipped"
        ::= { nptTrap 3404 }

   nptLpSlm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Low Order Path Signal Label Mismatch"
        ::= { nptTrap 3405 }

   nptLpSd NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VC-3/VC-12 Signal Degrade"
        ::= { nptTrap 3406 }

   nptLpExc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VC-3/VC-12  Excessive Bit Error"
        ::= { nptTrap 3407 }

   nptPcmPortLos NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of signal on interface"
        ::= { nptTrap 3500 }

   nptLineRxInactivity NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "No actvity is detected on Rx port of  V.24 or V.35/v.11"
        ::= { nptTrap 3501 }

   nptYellow NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Remote defect indication"
        ::= { nptTrap 3502 }

   nptNMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Received N from line is bigger than N configured"
        ::= { nptTrap 3503 }

   nptLineNError NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The N value received from line is not a valid value"
        ::= { nptTrap 3504 }

   nptE1NError NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Unable to get valid OH (N and signaling) from E1 channel"
        ::= { nptTrap 3505 }

   nptExternalAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Alarm occurs on Dry contact input port"
        ::= { nptTrap 3506 }

   nptExternalEvent NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Event occurs on Dry contact input port"
        ::= { nptTrap 3507 }

   nptRxPsnLops NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LOPS alarm at PSN to TDM direction"
        ::= { nptTrap 3600 }

   nptRxPsnStrayPkts NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Excessive stray packet discards at PSN to TDM direction"
        ::= { nptTrap 3601 }

   nptRxPsnMalformPkts NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Excessive malformed packet discards at PSN to TDM direction"
        ::= { nptTrap 3602 }

   nptRxPsnBufferOverrun NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Excessive jitter buffer overruns at PSN to TDM direction"
        ::= { nptTrap 3603 }

   nptRxPsnPlr NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Excessive packet loss ratio at PSN to TDM direction"
        ::= { nptTrap 3604 }

   nptRxPsnPer NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Excessive packet error ratio at PSN to TDM direction"
        ::= { nptTrap 3605 }

   nptRxPsnFarEndLops NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Remote IWF is in LOPS state"
        ::= { nptTrap 3606 }

   nptRxPsnRecClk NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Recovered clock state is abnormal"
        ::= { nptTrap 3607 }

   nptCesCardProtectionSwitching NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CES Card Protection Group Switching"
        ::= { nptTrap 3630 }

   nptCesCardProtectionDegrade NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CES Protecting Card Fails"
        ::= { nptTrap 3631 }

   nptDs1losL NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of signal on DS1 physical interface"
        ::= { nptTrap 4000 }

   nptRDs1aisP NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS1 Path  Alarm Indication Signal in receive direction"
        ::= { nptTrap 4100 }

   nptRDs1aisCiP NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS1 Path  Alarm Indication Signal - Customer Installation"
        ::= { nptTrap 4101 }

   nptTDs1aisP NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS1-AIS is sent in line transmit direction."
        ::= { nptTrap 4102 }

   nptDs1lofP NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS1 Loss of Frame"
        ::= { nptTrap 4103 }

   nptDs1rai NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS1 Remote Alarm Indication"
        ::= { nptTrap 4104 }

   nptDs1raiCi NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Remote Alarm Indication - Customer Installation"
        ::= { nptTrap 4105 }

   nptDs1pUatNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS Start Near End"
        ::= { nptTrap 4150 }

   nptCsstc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CSS in 15 Minutes Threshold Crossing Near End"
        ::= { nptTrap 4151 }

   nptSastc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SAS in 15 Minutes Threshold Crossing Near End"
        ::= { nptTrap 4152 }

   nptCsstc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CSS in 24 Hours Threshold Crossing Near End"
        ::= { nptTrap 4153 }

   nptSastc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SAS in 24 Hours Threshold Crossing Near End"
        ::= { nptTrap 4154 }

   nptLofS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Section Loss of Frame"
        ::= { nptTrap 4200 }

   nptTimS NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Section Trace Identification(J0) Mismatch"
        ::= { nptTrap 4201 }

   nptSectionEstc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 15 Minutes Threshold Crossing Near End"
        ::= { nptTrap 4202 }

   nptSSestc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 15 Minutes Threshold Crossing Near End"
        ::= { nptTrap 4203 }

   nptSCvtc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 15 Minutes Threshold Crossing Near End"
        ::= { nptTrap 4204 }

   nptSSefstc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SEFS in 15 Minutes Threshold Crossing"
        ::= { nptTrap 4205 }

   nptSectionEstc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 24 Hours Threshold Crossing Near End"
        ::= { nptTrap 4206 }

   nptSSestc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 24 Hours Threshold Crossing Near End"
        ::= { nptTrap 4207 }

   nptSCvtc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 24 Hours Threshold Crossing Near End"
        ::= { nptTrap 4208 }

   nptSSefstc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SEFS in 24 Hours Threshold Crossing"
        ::= { nptTrap 4209 }

   nptAisL NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Line Alarm Indication Signal"
        ::= { nptTrap 4210 }

   nptRfiL NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LIne Remote Defect Indication"
        ::= { nptTrap 4211 }

   nptSdL NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Line Signal Degrade"
        ::= { nptTrap 4212 }

   nptExcL NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Line Excessive Bit Error"
        ::= { nptTrap 4213 }

   nptLUatNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS Start Near End"
        ::= { nptTrap 4214 }

   nptLUatFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS Start Far End"
        ::= { nptTrap 4215 }

   nptLEstc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 15 Minutes Threshold Crossing Near End"
        ::= { nptTrap 4216 }

   nptLSestc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 15 Minutes Threshold Crossing Near End"
        ::= { nptTrap 4217 }

   nptLCvtc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 15 Minutes Threshold Crossing Near End"
        ::= { nptTrap 4218 }

   nptLUastc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 15 Minutes Threshold Crossing Near End"
        ::= { nptTrap 4219 }

   nptLEstc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 15 Minutes Threshold Crossing Far End"
        ::= { nptTrap 4220 }

   nptLSestc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 15 Minutes Threshold Crossing Far End"
        ::= { nptTrap 4221 }

   nptLCvtc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 15 Minutes Threshold Crossing Far End"
        ::= { nptTrap 4222 }

   nptLUastc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 15 Minutes Threshold Crossing Far End"
        ::= { nptTrap 4223 }

   nptLEstc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 24 Hours Threshold Crossing Near End"
        ::= { nptTrap 4224 }

   nptLSestc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 24 Hours Threshold Crossing Near End"
        ::= { nptTrap 4225 }

   nptLCvtc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 24 Hours Threshold Crossing Near End"
        ::= { nptTrap 4226 }

   nptLCvtc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 24 Hours Threshold Crossing Far End"
        ::= { nptTrap 4227 }

   nptLUastc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 24 Hours Threshold Crossing Near End"
        ::= { nptTrap 4228 }

   nptLEstc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ES in 24 Hours Threshold Crossing Far End"
        ::= { nptTrap 4229 }

   nptLSestc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SES in 24 Hours Threshold Crossing Far End"
        ::= { nptTrap 4230 }

   nptLUastc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "UAS in 24 Hours Threshold Crossing Far End"
        ::= { nptTrap 4231 }

   nptLopP NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Administration Unit Loss of Pointer"
        ::= { nptTrap 4300 }

   nptLomP NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "STS Path Loss of Multi-frame"
        ::= { nptTrap 4301 }

   nptAisP NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "STS Path  Alarm Indication Signal"
        ::= { nptTrap 4302 }

   nptRfiP NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "STS PathRemote Defect Indication"
        ::= { nptTrap 4303 }

   nptTimP NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "STS Path Trace Identification(J1) Mismatch"
        ::= { nptTrap 4304 }

   nptUneqP NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "STS Path Unequipped"
        ::= { nptTrap 4305 }

   nptPlmP NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "STS Path STS Payload Label Mismatch"
        ::= { nptTrap 4306 }

   nptSdP NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "STS Path Signal Degrade"
        ::= { nptTrap 4307 }

   nptExcP NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "STS Path  Excessive Bit Error"
        ::= { nptTrap 4308 }

   nptPdiP NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "STS Path Payload Defect Indication"
        ::= { nptTrap 4309 }

   nptCvtc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 15 Minutes Threshold Crossing Far End"
        ::= { nptTrap 4350 }

   nptCvtc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CV in 24 Hours Threshold Crossing Near End"
        ::= { nptTrap 4351 }

   nptLopV NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VT Path Loss of Pointer"
        ::= { nptTrap 4400 }

   nptAisV NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VT Path Alarm Indication Signal"
        ::= { nptTrap 4401 }

   nptRfiV NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VT Path  Remote Defect Indication"
        ::= { nptTrap 4402 }

   nptTimV NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VT Path Trace Identification Mismatch"
        ::= { nptTrap 4403 }

   nptUneqV NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VT Path Unequipped"
        ::= { nptTrap 4404 }

   nptPlmV NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VT Path Signal Label Mismatch"
        ::= { nptTrap 4405 }

   nptSdV NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VT Path Signal Degrade"
        ::= { nptTrap 4406 }

   nptExcV NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VT Path Excessive Bit Error"
        ::= { nptTrap 4407 }

   nptDs3Los NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 loss of signal (LOS) defect"
        ::= { nptTrap 4500 }

   nptDs3Ais NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Alarm indication signal"
        ::= { nptTrap 4501 }

   nptDs3Lof NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Loss of Frame"
        ::= { nptTrap 4502 }

   nptDs3Oof NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Out of Frame"
        ::= { nptTrap 4503 }

   nptDs3Idle NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Idle signal"
        ::= { nptTrap 4504 }

   nptDs3Rai NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS1 Remote Alarm Indication"
        ::= { nptTrap 4505 }

   nptDs3FeLos NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Far End Loss of signal defect"
        ::= { nptTrap 4506 }

   nptDs3FeAis NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Far End Alarm Indication Signal"
        ::= { nptTrap 4507 }

   nptDs3FeOof NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Far End Out of Frame"
        ::= { nptTrap 4508 }

   nptDs3FeIdle NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Far End IDLE signal received"
        ::= { nptTrap 4509 }

   nptDs3FeEqfs NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Far End equipment failure that is service affecting"
        ::= { nptTrap 4510 }

   nptDs3FeEqfn NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Far End equipment failure that is non service affecting"
        ::= { nptTrap 4511 }

   nptDs3FeMds1Los NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Far End Multiple DS1 loss of signal"
        ::= { nptTrap 4512 }

   nptDs3FeSds1Los NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS3 Far End Single DS1 loss of signal"
        ::= { nptTrap 4513 }

   nptDs3FeDs1Eqfs NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS1 equipment failure in the DS3 occurred that is service affecting"
        ::= { nptTrap 4514 }

   nptDs3FeDs1Eqfn NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS1 equipment failure in the DS3 occurred that is non service affecting"
        ::= { nptTrap 4515 }

   nptDs3FeDs1Cefn NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DS1 common equipment failure in the DS3 occurred that is non service affecting"
        ::= { nptTrap 4516 }

   nptDs3LosL NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A DS3 loss of signal (LOS) defect is detected."
        ::= { nptTrap 4550 }

   nptPowerInLos NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Input power is less than the input LOS threshold."
        ::= { nptTrap 5000 }

   nptOutputPowerDegrade NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The deviation of output power from the target value exceeds the threshold."
        ::= { nptTrap 5001 }

   nptPowerInOverload NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Input power is out of overload tolerance of the EDFA receiver"
        ::= { nptTrap 5002 }

   nptPowerInDegrade NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Input power is lower than the expected degraded threshold of the EDFA receiver"
        ::= { nptTrap 5003 }

   nptPowerInLos1 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "input power is less than the input LOS threshold at the first stage"
        ::= { nptTrap 5004 }

   nptPowerOutLop1 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of output signal power at the first stage"
        ::= { nptTrap 5005 }

   nptPowerInLos2 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "input power is less than the input LOS threshold at the second stage"
        ::= { nptTrap 5006 }

   nptPowerOutLop2 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of output signal power at the second stage"
        ::= { nptTrap 5007 }

   nptMidStageLossOutOfRange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Mid-stage loss out of range"
        ::= { nptTrap 5008 }

   nptGainOor NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Out Of Required gain on semi/automatic gain control"
        ::= { nptTrap 5009 }

   nptGainOom NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Out Of Margin on semi/automatic gain control"
        ::= { nptTrap 5010 }

   nptOtuLos NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of  signal"
        ::= { nptTrap 5101 }

   nptOtuLof NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of  frame"
        ::= { nptTrap 5102 }

   nptOtuLom NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of multiframe"
        ::= { nptTrap 5103 }

   nptOtuAis NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OTU alarm Indication Signal"
        ::= { nptTrap 5104 }

   nptOtuBdi NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OTU backward Defect Indication"
        ::= { nptTrap 5105 }

   nptOtuTim NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Trace identifier mismatch in OUT"
        ::= { nptTrap 5106 }

   nptOtuDeg NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Signal Degraded defect derived from BIP8 calculation."
        ::= { nptTrap 5107 }

   nptOtuIae NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Incoming alignment error"
        ::= { nptTrap 5108 }

   nptOtuBiae NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Backward Incoming alignment error"
        ::= { nptTrap 5109 }

   nptFceExc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "FEC corrected errors - excessive errors present"
        ::= { nptTrap 5110 }

   nptFceDeg NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "FEC corrected errors - degraded errors present"
        ::= { nptTrap 5111 }

   nptOtuUatNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Unavailable time near end"
        ::= { nptTrap 5112 }

   nptOtuUatFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Unavailable time far end"
        ::= { nptTrap 5113 }

   nptOtuBbeTc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for BBE accumulated near end in 15Min"
        ::= { nptTrap 5114 }

   nptOtuBbeTc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for BBE accumulated far end in 15Min"
        ::= { nptTrap 5115 }

   nptOtuEsTc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for ES accumulated near end in 15Min"
        ::= { nptTrap 5116 }

   nptOtuEsTc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for ES accumulated far end in 15Min"
        ::= { nptTrap 5117 }

   nptOtuSesTc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for SES accumulated near end in 15Min"
        ::= { nptTrap 5118 }

   nptOtuSesTc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for SES accumulated far end in 15Min"
        ::= { nptTrap 5119 }

   nptOtuCeTc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for Corrected Errors accumulated near end in 15Min"
        ::= { nptTrap 5120 }

   nptOtuBbeTc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for BBE accumulated near end in 24 hours"
        ::= { nptTrap 5121 }

   nptOtuBbeTc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for BBE accumulated far end in 24 hours"
        ::= { nptTrap 5122 }

   nptOtuEsTc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for ES accumulated near end in 24 hours"
        ::= { nptTrap 5123 }

   nptOtuEsTc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for ES accumulated far end in 24 hours"
        ::= { nptTrap 5124 }

   nptOtuSesTc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for SES accumulated near end in 24 hours"
        ::= { nptTrap 5125 }

   nptOtuSesTc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for SES accumulated far end in 24 hours"
        ::= { nptTrap 5126 }

   nptOtuCeTc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for Corrected Errors accumulated near end in 24 hours"
        ::= { nptTrap 5127 }

   nptOduAis NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODU alarm Indication Signal"
        ::= { nptTrap 5200 }

   nptOduOci NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Open Connection Indication"
        ::= { nptTrap 5201 }

   nptOduLck NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODU Lock indication"
        ::= { nptTrap 5202 }

   nptOduTim NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODU Trace identifier mismatch"
        ::= { nptTrap 5203 }

   nptOduPlm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODU Payload Mismatch"
        ::= { nptTrap 5204 }

   nptOduBdi NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODU Backward defect indication"
        ::= { nptTrap 5205 }

   nptOduDeg NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODU Degraded indication"
        ::= { nptTrap 5206 }

   nptOduCsf NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A single-bit OPUk client signal fail"
        ::= { nptTrap 5207 }

   nptOpuPn11 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Generic AIS, Indicates client Port LOS"
        ::= { nptTrap 5208 }

   nptOduUatNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODUk Unavailable time near end"
        ::= { nptTrap 5211 }

   nptOduUatFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODUk Unavailable time near end"
        ::= { nptTrap 5212 }

   nptOduBbeTc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for BBE accumulated near end in 15Min"
        ::= { nptTrap 5213 }

   nptOduBbeTc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for BBE accumulated far end in 15Min"
        ::= { nptTrap 5214 }

   nptOduEsTc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for ES accumulated near end in 15Min"
        ::= { nptTrap 5215 }

   nptOduEsTc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for ES accumulated far end in 15Min"
        ::= { nptTrap 5216 }

   nptOduSesTc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for SES accumulated near end in 15Min"
        ::= { nptTrap 5217 }

   nptOduSesTc15mFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for SES accumulated far end in 15Min"
        ::= { nptTrap 5218 }

   nptOduBbeTc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for BBE accumulated near end in 24 hours"
        ::= { nptTrap 5220 }

   nptOduBbeTc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for BBE accumulated far end in 24 hours"
        ::= { nptTrap 5221 }

   nptOduEsTc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for ES accumulated near end in 24 hours"
        ::= { nptTrap 5222 }

   nptOduEsTc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for ES accumulated far end in 24 hours"
        ::= { nptTrap 5223 }

   nptOduSesTc24hNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for SES accumulated near end in 24 hours"
        ::= { nptTrap 5224 }

   nptOduSesTc24hFe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold-crossing alert for SES accumulated far end in 24 hours"
        ::= { nptTrap 5225 }

   nptSncProtectionSwitch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SNCP Protection switched event"
        ::= { nptTrap 5227 }

   nptOtucLos NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of  signal"
        ::= { nptTrap 5301 }

   nptOtucLof NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of  frame"
        ::= { nptTrap 5302 }

   nptOtucLom NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of multiframe"
        ::= { nptTrap 5303 }

   nptOtucAis NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OTU alarm Indication Signal"
        ::= { nptTrap 5304 }

   nptOtucBdi NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OTU backward Defect Indication"
        ::= { nptTrap 5305 }

   nptOtucTim NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Trace identifier mismatch in OTUCn"
        ::= { nptTrap 5306 }

   nptOtucDeg NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Signal Degraded defect derived from BIP8 calculation."
        ::= { nptTrap 5307 }

   nptOtucIae NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Incoming alignment error"
        ::= { nptTrap 5308 }

   nptOtucBiae NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Backward Incoming alignment error"
        ::= { nptTrap 5309 }

   nptHiPreFecBer NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Pre-FEC BER exceeded  its high threshold"
        ::= { nptTrap 5310 }

   nptOducAis NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODUCn alarm Indication Signal"
        ::= { nptTrap 5401 }

   nptOducOci NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Open Connection Indication"
        ::= { nptTrap 5402 }

   nptOducLck NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODUCn Lock indication"
        ::= { nptTrap 5403 }

   nptOducTim NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODUCn Trace identifier mismatch"
        ::= { nptTrap 5404 }

   nptOducPlm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODUCn Payload Mismatch"
        ::= { nptTrap 5405 }

   nptOducBdi NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODUCn Backward defect indication"
        ::= { nptTrap 5406 }

   nptOducDeg NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ODUCn Degraded indication"
        ::= { nptTrap 5407 }

   nptOducCsf NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A single-bit client signal fail"
        ::= { nptTrap 5408 }

   nptRxLof NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of Frame"
        ::= { nptTrap 5800 }

   nptRxLom NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of Multiple frame"
        ::= { nptTrap 5801 }

   nptLd NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Local Degrade"
        ::= { nptTrap 5802 }

   nptRd NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Remote Degrade"
        ::= { nptTrap 5803 }

   nptPortlinkdown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Link down"
        ::= { nptTrap 6000 }

   nptLinkDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Port operational state down"
        ::= { nptTrap 6001 }

   nptAnAbilityMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Auto-negotiation resulting in link capacity"
        ::= { nptTrap 6002 }

   nptAutonegFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Auto-negotiation failed"
        ::= { nptTrap 6003 }

   nptHighBer NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "High BER"
        ::= { nptTrap 6004 }

   nptLosync NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PCS loss of synchronization"
        ::= { nptTrap 6005 }

   nptPcsEstc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold Crossing Alert: Near End Errored Seconds, 15 minutes"
        ::= { nptTrap 6006 }

   nptPcsSestc15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold Crossing Alert: Near End Severely Errored Seconds, 15 minutes"
        ::= { nptTrap 6007 }

   nptPcsCv15mNe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold Crossing Alert: Near End Code Violations, 15 minutes"
        ::= { nptTrap 6008 }

   nptLocalFault NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Local fault"
        ::= { nptTrap 6009 }

   nptRemoteFault NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Remote fault"
        ::= { nptTrap 6010 }

   nptRxErrpktsTc15m NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold Crossing Alert: Rx Bad Frames, 15 minutes"
        ::= { nptTrap 6011 }

   nptRxBcpktsTc15m NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold Crossing Alert: Rx Broadcast Frames, 15 minutes"
        ::= { nptTrap 6012 }

   nptRxMcpktsTc15m NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold Crossing Alert: Rx Multicast Frames, 15 minutes"
        ::= { nptTrap 6013 }

   nptExcBer NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Excessive BER"
        ::= { nptTrap 6014 }

   nptTxPortUtilizationTc15m NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Threshold Crossing Alert: Tx Port Utilization, 15 minutes"
        ::= { nptTrap 6015 }

   nptOamDiscoveryFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OAM Discovery Failed"
        ::= { nptTrap 6050 }

   nptOamLinkLost NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OAM Lost Link"
        ::= { nptTrap 6051 }

   nptOamRemoteLinkFault NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OAM Remote Link Fault"
        ::= { nptTrap 6052 }

   nptOamLocalLinkEvent NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OAM Local Link Event"
        ::= { nptTrap 6053 }

   nptOamRemoteLinkEvent NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OAM Remote Link Event"
        ::= { nptTrap 6054 }

   nptOamLocalLoopback NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OAM Local loop back"
        ::= { nptTrap 6055 }

   nptOamLocalLoopbackRelease NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OAM Local loop back release"
        ::= { nptTrap 6056 }

   nptPortIsLooped NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Port is looped back"
        ::= { nptTrap 6057 }

   nptBfdDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BFD Down"
        ::= { nptTrap 6058 }

   nptBfdLoc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BFD LOC"
        ::= { nptTrap 6059 }

   nptBfdRdi NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BFD RDI"
        ::= { nptTrap 6060 }

   nptPdDisconnect NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PD Disconnected"
        ::= { nptTrap 6061 }

   nptPdOverCurrent NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PD Over Current"
        ::= { nptTrap 6062 }

   nptPdShortCurrent NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PD Short Current"
        ::= { nptTrap 6063 }

   nptPdStartupOverCurrent NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PD Startup Over Current"
        ::= { nptTrap 6064 }

   nptPdFault NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PD Fault"
        ::= { nptTrap 6065 }

   nptOamRemoteLinkDyinggasp NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "OAM Remote Dying Gasp"
        ::= { nptTrap 6066 }

   nptFrrInuseStateChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Frr inuse state is changed"
        ::= { nptTrap 6067 }

   nptPeerMacMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Peer MAC Mismatch"
        ::= { nptTrap 6068 }

   nptLldpRemoteChanges NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LLDP Remote Changes"
        ::= { nptTrap 6069 }

   nptLinkFlappingTca NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Link Flapping Threshold Crossing"
        ::= { nptTrap 6070 }

   nptLldpTooManyNeighbours NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LLDP Too Many Neighbours"
        ::= { nptTrap 6071 }

   nptEsmcLoss NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of ESMC packets"
        ::= { nptTrap 6072 }

   nptEthSd NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Ethernet port signal degraded, when there are CRC detected for the port in the active NPU"
        ::= { nptTrap 6073 }

   nptPhyFault NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PHY Fault, specially refers to link-down or failure on the MAC SerDes interface of the Port PHY device."
        ::= { nptTrap 6074 }

   nptLagPartialLinksDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Partial Links are down in the LAG"
        ::= { nptTrap 6100 }

   nptLagLinkDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LAG Link down due to the number fo failed ports exceeding the defined threshold"
        ::= { nptTrap 6101 }

   nptLagAllLinksDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "All ports in the LAG are down"
        ::= { nptTrap 6102 }

   nptMcLagSwitching NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MC-LAG Protection Switching event"
        ::= { nptTrap 6103 }

   nptMcLagMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MC-LAG Mismatch due to some reasons"
        ::= { nptTrap 6104 }

   nptMcLagIccpChannelDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MC-LAG ICCP Channel Down"
        ::= { nptTrap 6105 }

   nptBridgeTopologyChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Topology of span tree instance changed"
        ::= { nptTrap 6120 }

   nptRootPortChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Root port of STP change"
        ::= { nptTrap 6121 }

   nptMcLagUnknownRgDiscarded NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Unknown RG Discarded for NC-LAG"
        ::= { nptTrap 6122 }

   nptHeaderErrorTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Header error counter in 15m"
        ::= { nptTrap 6123 }

   nptTunnelResourcesAvailabilityChanges NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tunnel resources available state change events"
        ::= { nptTrap 6124 }

   nptInsertPeTimeOut NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Time out for insert PE action"
        ::= { nptTrap 6125 }

   nptSlowPathWredDropTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Wred Discard Ratio TCA of  Slow-Path TM"
        ::= { nptTrap 6126 }

   nptArpFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ARP Table is almost full"
        ::= { nptTrap 6127 }

   nptArpNhFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ARP Table for Next Hop is almost full"
        ::= { nptTrap 6128 }

   nptFibFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IPv4 Unicast FIB is full"
        ::= { nptTrap 6129 }

   nptFibAlmostFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IPv4 Unicast FIB is almost full"
        ::= { nptTrap 6130 }

   nptTxL3vpnLabelFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx-L3VPN Label utilization is full"
        ::= { nptTrap 6131 }

   nptTxL3vpnLabelAlmostFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx-L3VPN Label utilization is almost full"
        ::= { nptTrap 6132 }

   nptIpv4McFibFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IPv4 Multicast FIB is full"
        ::= { nptTrap 6133 }

   nptIpv4McFibAlmostFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IPv4 Multicast FIB is almost full"
        ::= { nptTrap 6134 }

   nptIpv6UcFibFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IPv6 Unicast FIB is full"
        ::= { nptTrap 6135 }

   nptIpv6UcFibAlmostFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IPv6 Unicast FIB is almost full"
        ::= { nptTrap 6136 }

   nptIpv6McFibFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IPv6 Multicast FIB is full"
        ::= { nptTrap 6137 }

   nptIpv6McFibAlmostFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IPv6 Multicast FIB is almost full"
        ::= { nptTrap 6138 }

   nptTmFloodWredDropTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Wred Discard Ratio TCA of  Flood TM"
        ::= { nptTrap 6139 }

   nptTmMcWredDropTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Wred Discard Ratio TCA of  Multicast service TM"
        ::= { nptTrap 6140 }

   nptBgpPicNhAlmostFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BGP PIC Next Hop is almost full"
        ::= { nptTrap 6141 }

   nptBgpPicNhFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BGP PIC Next Hop is full"
        ::= { nptTrap 6142 }

   nptNhAlmostFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IP-MPLS Next Hop is almost full"
        ::= { nptTrap 6143 }

   nptNhFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IP-MPLS Next Hop is full"
        ::= { nptTrap 6144 }

   nptScaleSubnetFibFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Scale Subnet Unicast FIB is full"
        ::= { nptTrap 6145 }

   nptScaleSubnetFibAlmostFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Scale Subnet Unicast FIB is almost full"
        ::= { nptTrap 6146 }

   nptIpv6HostArpFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IPv6 Host ARP entries in DP is full"
        ::= { nptTrap 6147 }

   nptLackOfTxmplsResources NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CFG-SYNC-FAIL errors due to lack of TxMPLS related DP resources."
        ::= { nptTrap 6148 }

   nptLackOfDpResources NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "There is an incomplete object in DP due to lack of resources."
        ::= { nptTrap 6149 }

   nptMhEsModeMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CFG-SYNC-FAIL errors due to lack of TxMPLS related DP resources."
        ::= { nptTrap 6150 }

   nptTooManyMhEsLinks NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "There is an incomplete object in DP due to lack of resources."
        ::= { nptTrap 6151 }

   nptMacTableFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MAC table is full"
        ::= { nptTrap 6152 }

   nptMacTableAlmostFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MAC table is almost full"
        ::= { nptTrap 6153 }

   nptMacMoveEvents NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MAC Move Events"
        ::= { nptTrap 6201 }

   nptErpsTopoChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ERPS Topology Change"
        ::= { nptTrap 6202 }

   nptInvalidMaid NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Invalid MA ID"
        ::= { nptTrap 6203 }

   nptLowLevelCcm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Received lower level CCM"
        ::= { nptTrap 6204 }

   nptMepNotConfigured NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Received unexpected MEP ID"
        ::= { nptTrap 6205 }

   nptMepSameMepid NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Received duplicate MEP ID"
        ::= { nptTrap 6206 }

   nptCcmIntervalMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Incorrect CCM Interval"
        ::= { nptTrap 6207 }

   nptRxCcmTimerExpired NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CCM timer expired /Connectivity Loss"
        ::= { nptTrap 6208 }

   nptMepInterfaceStatus NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "AC interface down"
        ::= { nptTrap 6209 }

   nptMepPortStatus NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "AC port down"
        ::= { nptTrap 6210 }

   nptMepRdi NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Received CCM with RDI bit"
        ::= { nptTrap 6211 }

   nptRmepFdNotCompliant15m NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "not-compliant FD"
        ::= { nptTrap 6212 }

   nptRmepFdvNotCompliant15m NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "not-compliant FDV"
        ::= { nptTrap 6213 }

   nptRmepFdvNotCompliantBck15m NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "not-compliant FDV Backward"
        ::= { nptTrap 6214 }

   nptRmepUnavailFwd NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "unavailability Forward"
        ::= { nptTrap 6215 }

   nptRmepUnavailBck NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "unavailability Backward"
        ::= { nptTrap 6216 }

   nptVfibFull NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VSI MAC table is full"
        ::= { nptTrap 6218 }

   nptLinearProtectionSwitching NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Linear Protetion switching"
        ::= { nptTrap 6300 }

   nptLinearProtectionTypeMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "there is an inconsistency for PT in this protection domain."
        ::= { nptTrap 6301 }

   nptLinearProtectionPscProtocolDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Protecting LSP does not receive PSC message in 60s"
        ::= { nptTrap 6302 }

   nptTunnelProtectionDegrade NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "primary or secondary path fails."
        ::= { nptTrap 6303 }

   nptTunnelDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "primary and secondary paths fail."
        ::= { nptTrap 6304 }

   nptPwDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PW operational state is Down"
        ::= { nptTrap 6350 }

   nptPwRedundancySwitchover NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PW Redundancy Switchover"
        ::= { nptTrap 6351 }

   nptProtectionTypeMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "there is an inconsistency for PT in this protection domain."
        ::= { nptTrap 6353 }

   nptProtectionProtocolDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Protecting Path does not receive APS message"
        ::= { nptTrap 6354 }

   nptProtectionDegrade NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "primary or secondary path fails."
        ::= { nptTrap 6355 }

   nptProtectionDomainDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "primary and secondary paths fail."
        ::= { nptTrap 6356 }

   nptPwNoMacLearning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MAC learning is disabled for traffic ingress from a PW"
        ::= { nptTrap 6359 }

   nptOspfVirtIfStateChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "a state change on OSPF virtual interface"
        ::= { nptTrap 6400 }
        
   nptOspfNbrStateChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "a state change on non-virtual OSPF neighbor"
        ::= { nptTrap 6401 }
        
   nptOspfVirtNbrStateChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "a state change on OSPF virtual neighbor"
        ::= { nptTrap 6402 }
        
   nptOspfIfConfigError NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "non-virtual interface configuration parameters conflict"
        ::= { nptTrap 6403 }
        
   nptOspfVirtIfConfigError NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "virtual interface configuration parameters conflict."
        ::= { nptTrap 6404 }
        
   nptOspfIfAuthFailure NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "non-virtual interface authentication key or authentication type conflicts"
        ::= { nptTrap 6405 }
        
   nptOspfVirtIfAuthFailure NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "virtual interface authentication key or authentication type conflicts"
        ::= { nptTrap 6406 }
        
   nptOspfTxRetransmit NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "an OSPF packet has been retransmitted on a non-virtual interface."
        ::= { nptTrap 6409 }
        
   nptOspfVirtIfTxRetransmit NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "an OSPF packet has been retransmitted on a virtual interface."
        ::= { nptTrap 6410 }
        
   nptOspfMaxAgeLsa NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "one of the LSAs in the router s link state database has aged to MaxAge"
        ::= { nptTrap 6412 }
        
   nptOspfIfStateChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "non-virtual OSPF interface state change"
        ::= { nptTrap 6415 }
        
   nptOspfRestartStatusChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "the graceful restart state change for the router"
        ::= { nptTrap 6417 }
        
   nptOspfNbrRestartHelperStatusChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "graceful restart helper state change for the neighbor."
        ::= { nptTrap 6418 }
        
   nptOspfVirtNbrRestartHelperStatusChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "graceful restart helper state change for the virtual neighbor."
        ::= { nptTrap 6419 }
        
   nptOspfFrrPrefixProtectionChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "This notification is generated when any change in the ipFrrAltProtectionAvailable attribute value for this destination is caused."
        ::= { nptTrap 6420 }

   nptOspfVirtIfStateChangeAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "a state change on OSPF virtual interface."
        ::= { nptTrap 6421 }

   nptOspfNbrStateChangeAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "a state change on non-virtual OSPF neighbor. There is P2P definitions in LIF, then there is only 1 neighbor. Only in case of P2P may be supported on LIF"
        ::= { nptTrap 6422 }

   nptOspfVirtNbrStateChangeAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "a state change on OSPF virtual neighbor"
        ::= { nptTrap 6423 }

   nptOspfIfAuthFailureAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "non-virtual interface authentication key or authentication type conflicts"
        ::= { nptTrap 6424 }

   nptOspfVirtIfAuthFailureAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "virtual interface authentication key or authentication type conflicts"
        ::= { nptTrap 6425 }

   nptOspfIfStateChangeAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "non-virtual OSPF interface state change"
        ::= { nptTrap 6426 }

   nptIsisDataBaseOverload NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "This notification is generated when the system enters or leaves the Overload state."
        ::= { nptTrap 6450 }

   nptIsisManualAddressDrops NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "This notification is generated when one of the manual areaAddresses assigned to this system is ignored when computing routes."
        ::= { nptTrap 6451 }

   nptIsisAttemptToExceedMaxSequence NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "this notification is generated when  the sequence number on an LSP we generate wraps the 32-bit sequence counter"
        ::= { nptTrap 6453 }

   nptIsisIdLenMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive a PDU with a different value for the System ID Length."
        ::= { nptTrap 6455 }

   nptIsisMaxAreaAddressesMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive a PDU with a different value for the Maximum Area Addresses."
        ::= { nptTrap 6456 }

   nptIsisOwnLspPurge NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive a PDU with our systemID and zero age"
        ::= { nptTrap 6457 }

   nptIsisSequenceNumberSkip NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive an LSP with our System ID and different contents"
        ::= { nptTrap 6458 }

   nptIsisAuthenticationTypeFailure NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive a PDU with the wrong authentication type field."
        ::= { nptTrap 6459 }

   nptIsisAuthenticationFailure NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive a PDU with an incorrect authentication information field."
        ::= { nptTrap 6460 }

   nptIsisAreaMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive a Hello PDU from an IS that does not share any area address"
        ::= { nptTrap 6462 }

   nptIsisRejectedAdjacency NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive a Hello PDU from an IS but do not establish an adjacency for some reason."
        ::= { nptTrap 6463 }

   nptIsisLspTooLargeToPropagate NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we attempt to propagate an LSP that is larger than the dataLinkBlockSize for the circuit."
        ::= { nptTrap 6464 }

   nptIsisProtocolsSupportedMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when a non-pseudonode segment 0 LSP is received that has no matching protocols supported."
        ::= { nptTrap 6466 }

   nptIsisAdjacencyChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when an adjacency changes state, entering or leaving state up."
        ::= { nptTrap 6467 }

   nptIsisLspErrorDetected NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "This notification is generated when we receive an LSP with a parse error."
        ::= { nptTrap 6468 }

   nptIsisFrrPrefixProtectionChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "This notification is generated when any change in the ipFrrAltProtectionAvailable attribute value for this destination is caused."
        ::= { nptTrap 6469 }

   nptIsisDbOverload NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "This notification is generated when the system enters or leaves the Overload state."
        ::= { nptTrap 6470 }

   nptIsisAuthTypeFailure NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive a PDU with the wrong authentication type field."
        ::= { nptTrap 6471 }

   nptIsisAuthFailure NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when we receive a PDU with an incorrect authentication information field."
        ::= { nptTrap 6472 }

   nptIsisAdjChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A notification sent when an adjacency changes state, entering or leaving state up."
        ::= { nptTrap 6473 }

   nptWredDropRatio NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Wred Discard Ratio TCA of Diffserv-Block"
        ::= { nptTrap 6508 }

   nptRxDiscardPktsTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Rx Discard Packets  TCA"
        ::= { nptTrap 6520 }

   nptTxDiscardPktsTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Tx Discard Packets  TCA"
        ::= { nptTrap 6521 }

   nptArpMessageDropEvent NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ARP Message Drop Event from DAI"
        ::= { nptTrap 6522 }

   nptDhcpServerIpMacBindingContradiction NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "DHCP Server IP-MAC Binding Contradiction from DAI"
        ::= { nptTrap 6523 }

   nptLeaseExpirationEvent NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A lease time of  a specific record expires from DAI"
        ::= { nptTrap 6524 }

   nptNdpTrackingDestinationStateEvent NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Destination state event based on NDP tracking"
        ::= { nptTrap 6525 }

   nptNdpTrackingPrefixStateEvent NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Prefix state event based on NDP tracking"
        ::= { nptTrap 6526 }

   nptNdpDadFailureEvent NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Duplicate Address Detection Failure"
        ::= { nptTrap 6527 }

   nptLdpSessionUp NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LDP session up"
        ::= { nptTrap 6550 }

   nptLdpSessionDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LDP session down"
        ::= { nptTrap 6551 }

   nptLdpSessionInitializationFailure NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LDP session down"
        ::= { nptTrap 6552 }

   nptLdpSessionDownAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "LDP session down"
        ::= { nptTrap 6553 }

   nptBgpSessionDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BGP Session Down"
        ::= { nptTrap 6600 }

   nptBgpSessionUp NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BGP Session Up"
        ::= { nptTrap 6601 }


   nptMaximumPrefixTca NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Maximum Prefix TCA"
        ::= { nptTrap 6603 }

   nptBgpRibSizeTca NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BGP RIB Size TCA"
        ::= { nptTrap 6604 }

   nptMaximumPrefixExceeded NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Maximum Prefix Exceeded"
        ::= { nptTrap 6605 }

   nptBgpSessionDownAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "BGP Session Down"
        ::= { nptTrap 6606 }

   nptBgpMaxPrefixesExceeded NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Maximum Prefix Exceeded"
        ::= { nptTrap 6607 }

   nptBgpMaximumPrefixAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Maximum Prefix TCA  Alarm"
        ::= { nptTrap 6608 }

   nptBgpRibSizeAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               ""
        ::= { nptTrap 6609 }

   nptIgmpQuerierWrongVersionWarning NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IGMP Querier Wrong Version Warning"
        ::= { nptTrap 6650 }

   nptIgmpGroupMembershipCapacityExceeded NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "IGMP Group Membership Capacity Exceeded"
        ::= { nptTrap 6651 }

   nptVrrpNewVrrpMaster NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "new VRRP Master has been elected"
        ::= { nptTrap 6686 }

   nptVrrpError NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "One of VRRP error conditions is detected"
        ::= { nptTrap 6687 }

   nptVrrpNewVrrpMasterAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "new VRRP Master has been elected"
        ::= { nptTrap 6688 }

   nptVrrpErrorAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "One of VRRP error conditions is detected"
        ::= { nptTrap 6689 }

   nptPimNeighborLoss NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A pimNeighborLoss notification signifies the loss of an adjacency with a neighbor."
        ::= { nptTrap 6700 }

   nptPimInvalidRegister NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A pimInvalidRegister notification signifies that an invalid PIM Register message received by this device."
        ::= { nptTrap 6701 }

   nptPimInvalidJoinPrune NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A pimInvalidJoinPrune notification signifies that an invalid PIM Join/Prune message received by this device."
        ::= { nptTrap 6702 }

   nptPimRpmappingChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A pimRPMappingChange notification signifies a change to the active RP mapping on this device."
        ::= { nptTrap 6703 }

   nptPimInterfaceElection NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "A pimInterfaceElection notification signifies that a new DR or DF elected on a network."
        ::= { nptTrap 6704 }

   nptVrfRibSizeTca NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VRF RIB Size TCA"
        ::= { nptTrap 6720 }

   nptVrfIpv4FibTca NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VRF IPV4 FIB TCA"
        ::= { nptTrap 6721 }

   nptVrfIpv6FibTca NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VRF IPV6 FIB TCA"
        ::= { nptTrap 6722 }

   nptVrfIpv4InactiveRoute NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VRF IPV4 Inactive Route"
        ::= { nptTrap 6723 }

   nptVrfIpv6InactiveRoute NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "VRF IPV6 Inactive Route"
        ::= { nptTrap 6724 }

   nptOspfv3VirtIfStateChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "a state change on OSPFv3 virtual interface"
        ::= { nptTrap 6740 }
        
   nptOspfv3NbrStateChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "a state change on non-virtual OSPFv3 neighbor"
        ::= { nptTrap 6741 }
        
   nptOspfv3VirtNbrStateChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "a state change on OSPFv3 virtual neighbor"
        ::= { nptTrap 6742 }
        
   nptOspfv3IfConfigError NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "non-virtual interface configuration parameters conflict"
        ::= { nptTrap 6743 }
        
   nptOspfv3VirtIfConfigError NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "virtual interface configuration parameters conflict."
        ::= { nptTrap 6744 }
        
   nptOspfv3IfStateChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "non-virtual OSPF interface state change"
        ::= { nptTrap 6749 }
        
   nptOspfv3RestartStatusChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "the graceful restart state change for the router"
        ::= { nptTrap 6751 }
        
   nptOspfv3NbrRestartHelperStatusChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "graceful restart helper state change for the neighbor."
        ::= { nptTrap 6752 }
        
   nptOspfv3VirtNbrRestartHelperStatusChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "graceful restart helper state change for the virtual neighbor."
        ::= { nptTrap 6753 }

   nptOspfv3NbrStateChangeAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "a state change on non-virtual OSPFv3 neighbor. There is P2P definitions in LIF, then there is only 1 neighbor. Only in case of P2P may be supported on LIF"
        ::= { nptTrap 6754 }

   nptOspfv3IfStateChangeAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "non-virtual OSPFv3 interface state change"
        ::= { nptTrap 6755 }

   nptSegmentRoutingGlobalSrgbCollision NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "segment routing global srgb collision"
        ::= { nptTrap 6780 }

   nptSegmentRoutingGlobalSidCollision NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "segment routing global sid collision"
        ::= { nptTrap 6781 }

   nptSegmentRoutingIndexOutOfRange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "segment routing index out of range"
        ::= { nptTrap 6782 }

   nptSrGlobalSrgbCollisionAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "segment routing global srgb collision"
        ::= { nptTrap 6783 }

   nptSrGlobalSidCollisionAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "segment routing global sid collision"
        ::= { nptTrap 6784 }

   nptSrIndexOutOfRangeAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "segment routing index out of range"
        ::= { nptTrap 6785 }

   nptMacsecSeqOverThreshold NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MACSec Sequence over threshold"
        ::= { nptTrap 6800 }

   nptMacsecSeqRollover NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MACSec Sequence over roll from maximum value to zero"
        ::= { nptTrap 6801 }

   nptMkaSessionDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MKA Session Down Event"
        ::= { nptTrap 6802 }

   nptMkaSessionUp NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MKA Session Up Event"
        ::= { nptTrap 6803 }

   nptMkaConnectionDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MKA Session Down Alarm"
        ::= { nptTrap 6804 }

   nptLoga NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of Group Alignment Indication"
        ::= { nptTrap 7000 }

   nptGroupNumInconsistent NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Group Number Inconsistent"
        ::= { nptTrap 7001 }

   nptPhyNumInconsistent NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Phy Numbers Inconsistent"
        ::= { nptTrap 7002 }

   nptPhyMapInconsistent NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Phy Maps Inconsistent"
        ::= { nptTrap 7003 }

   nptCalendarInUseInconsistent NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Calendar in use Inconsistent"
        ::= { nptTrap 7004 }

   nptLof NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of FlexE overhead frame."
        ::= { nptTrap 7005 }

   nptLomf NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of FlexE overhead multi-frame."
        ::= { nptTrap 7006 }

   nptRpf NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Remote PHY Fault."
        ::= { nptTrap 7007 }

   nptGnm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Group Number Mismatch"
        ::= { nptTrap 7008 }

   nptPnm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Phy Number Mismatch"
        ::= { nptTrap 7009 }

   nptPmapm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Phy Map Mismatch"
        ::= { nptTrap 7010 }

   nptCm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Calendar in use Mismatch"
        ::= { nptTrap 7011 }

   nptCcm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Calendar Configuration Mismatch"
        ::= { nptTrap 7012 }

   nptScm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Sync Message Inconsistent"
        ::= { nptTrap 7013 }

   nptOhBlock1Error NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Overhead anchor block error"
        ::= { nptTrap 7014 }

   nptCrc16Error NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CRC16 error of a Flexe instance"
        ::= { nptTrap 7015 }

   nptCBitError NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "C Bit error"
        ::= { nptTrap 7016 }

   nptCcmDYNAMIC NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Calendar Configuration Mismatch HW in Dynamic mode"
        ::= { nptTrap 7017 }

   nptCrAFailed NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Calendar request to use calendar A failed"
        ::= { nptTrap 7018 }

   nptCrBFailed NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Calendar request to use calendar B failed"
        ::= { nptTrap 7019 }

   nptLocFlexe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of Connectivity"
        ::= { nptTrap 7030 }

   nptRdIFLEXE NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Remote Defect Indication"
        ::= { nptTrap 7031 }

   nptCsLf NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Client Signal Local Fault"
        ::= { nptTrap 7032 }

   nptCsRf NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Client Signal Remote Fault"
        ::= { nptTrap 7033 }

   nptCsLpi NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Client Signal Low Power Indication"
        ::= { nptTrap 7034 }

   nptCsUneq NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Client Signal Un-Equipment"
        ::= { nptTrap 7035 }

   nptTimFlexe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Trace Identification Mismatch"
        ::= { nptTrap 7036 }

   nptSfFlexe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Signal Fail"
        ::= { nptTrap 7037 }

   nptSdFlexe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Signal Degard"
        ::= { nptTrap 7038 }

   nptPeriodMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "FlexE channel OAM period mismatch"
        ::= { nptTrap 7039 }

   nptLfFlexe NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Local fault on FlexE channel MAC layer"
        ::= { nptTrap 7040 }

   nptRfFlexe  NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Remote fault on FlexE channel MAC layer"
        ::= { nptTrap 7041 }

   nptSppLinkDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "SPP Link Down"
        ::= { nptTrap 7050 }

   nptFlexeChannelSwitchover NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Flexe channel switchover"
        ::= { nptTrap 7051 }

   nptRsvpTeLspDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "One of the configured lsps is about to enter the down state from some other state (but not from the notPresent state)"
        ::= { nptTrap 7200 }

   nptRsvpTeLspUp  NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "One of the configured lsps is about to leave the down state and transition into some other state (but not into the notPresent state)"
        ::= { nptTrap 7201 }

   nptRsvpTeLspRerouted NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "An lsp is rerouted"
        ::= { nptTrap 7202 }

   nptRsvpTeLspTeoptimized NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "An lsp is reoptimized."
        ::= { nptTrap 7203 }

   nptX148vFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "First INF Failure in NPT-2700"
        ::= { nptTrap 2078 }

   nptX248vFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Second INF Failure in NPT-2700"
        ::= { nptTrap 2079 }

   nptM3p3vFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Local PS (3.3V DC) Failure"
        ::= { nptTrap 2080 }

   nptOperstateChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Operational state change notification"
        ::= { nptTrap 2081 }

   nptT31Lof NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of frame on E1/T1"
        ::= { nptTrap 2524 }

   nptT31Ais NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "T3 AIS on 2048Kbit/s or 1544Kbit/s"
        ::= { nptTrap 2525 }

   nptT31BitLos NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "T3  Input LOS on E1 or T1;"
        ::= { nptTrap 2526 }

   nptT31HzLos NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "T3  Input LOS on 2048KHz"
        ::= { nptTrap 2527 }

   nptT41Lto NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "T4 output cut-off"
        ::= { nptTrap 2528 }

   nptT32Lof NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Loss of frame on E1/T1"
        ::= { nptTrap 2529 }

   nptT32Ais NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "T3 AIS on 2048Kbit/s or 1544Kbit/s"
        ::= { nptTrap 2530 }

   nptT32BitLos NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "T3  Input LOS on E1 or T1;"
        ::= { nptTrap 2531 }

   nptT32HzLos NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "T3  Input LOS on 2048KHz"
        ::= { nptTrap 2532 }

   nptT42Lto NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "T4 output cut-off"
        ::= { nptTrap 2533 }

   nptEext2uhLostConnection NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "eEXT shelf lost connection"
        ::= { nptTrap 2345 }

   nptLinkTrainingFail NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Link Training Fail"
        ::= { nptTrap 6075 }

   nptSegmentRoutingTeMsdExceeded NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Raised when a resulted label stack for LSP exceeds MSD"
        ::= { nptTrap 6305 }

   nptFwRevNeedConfirm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Need check if FW versions are as expected in the system"
        ::= { nptTrap 2082 }

   nptMngProtectionFailed NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "No protection available for the management interface"
        ::= { nptTrap 2083 }

   nptRxPsnNoTdmPayload NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "No TDM Payload on received packet"
        ::= { nptTrap 3608 }

   nptRxPsnLengthMismatch NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Length mismatch on received packet"
        ::= { nptTrap 3609 }

   nptRxPsnMissingPacket NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Missing packet on received side"
        ::= { nptTrap 3610 }

   nptRxPsnWrongDaMac NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Wrong DA MAC on received packet per card"
        ::= { nptTrap 3611 }

   nptRxPsnOutOfJbRange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Received packet is out of Jitter buffer range"
        ::= { nptTrap 3612 }

   nptRxPsnJbRecented NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Jitter buffer recented"
        ::= { nptTrap 3613 }

   nptEvpnVpwsRemoteEpConflict NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "EVPN VPWS Remote Endpoint Conflict"
        ::= { nptTrap 6528 }

   nptTelemetryDestUnreachable NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The destination of telemetry is not reachable"
        ::= { nptTrap 2455 }

   nptChassisBusBitFailed NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "There is inter-card traffic bus SF or SD in the chassis, i.e., the Ethernet/packet connectivity. The Ethernet connectivity includes SGMII, QSGMII, RXAUI, SFI and so on."
        ::= { nptTrap 2456 }

   nptT3T4Unavailable NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "T3/T4 Interface is unavailable"
        ::= { nptTrap 2534 }

   nptGnssUnavailable NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "GNSS unavailable"
        ::= { nptTrap 2620 }

   nptOnepps10mCoaxUnavailable NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "1PPS/10M Coax interface Unavailable"
        ::= { nptTrap 2621 }

   nptPtsfLosssync NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "lack of reception of PTP timing messages from a master (loss of the packet timing signal)"
        ::= { nptTrap 2622 }

   nptPtsfUnusable NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "unusable PTP packet timing signal received by the slave, exceeding the input tolerance of the slave (noisy packet timing signal)"
        ::= { nptTrap 2623 }

   nptMcDbFullTcSp NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MC DB High Utilization in SP"
        ::= { nptTrap 6154 }

   nptMcDbFullTcSpCos0 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MC DB High Utilization in SP CoS  0"
        ::= { nptTrap 6155 }

   nptMcDbFullTcSpCos1 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MC DB High Utilization in SP CoS  1"
        ::= { nptTrap 6156 }

   nptMcDbFullTcSpCos2 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MC DB High Utilization in SP CoS  2"
        ::= { nptTrap 6157 }

   nptMcDbFullTcSpCos3 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MC DB High Utilization in SP CoS  3"
        ::= { nptTrap 6158 }

   nptMcDbFullTcSpCos4 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MC DB High Utilization in SP CoS  4"
        ::= { nptTrap 6159 }

   nptMcDbFullTcSpCos5 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MC DB High Utilization in SP CoS  5"
        ::= { nptTrap 6160 }

   nptMcDbFullTcSpCos6 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MC DB High Utilization in SP CoS  6"
        ::= { nptTrap 6161 }

   nptMcDbFullTcSpCos7 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MC DB High Utilization in SP CoS  7"
        ::= { nptTrap 6162 }

   nptSrLdpLspResourceFull NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The SR-LDP LSP related DP resource is full"
        ::= { nptTrap 6163 }

   nptLuLspResourceFull NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The LU LSP related DP resource is full"
        ::= { nptTrap 6164 }

   nptRsvpTeLspResourceFull NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The RSVP-TE LSP related DP resource is full"
        ::= { nptTrap 6165 }

   nptSrTeLspResourceFull NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The SR-TE LSP related DP resource is full"
        ::= { nptTrap 6166 }

   nptMplsTpLspResourceFull NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The MPLS-TP LSP related DP resource is full"
        ::= { nptTrap 6167 }

   nptPcepSessionDownAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PCEP session down"
        ::= { nptTrap 7300 }

   nptHighScaleLicenseRequired NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Usage of high scale FIB requires relevant license. Please approach sales representative to obtain license."
        ::= { nptTrap 2342 }

   nptSyslogAuthFailure NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Authentication failed when connecting to SYSLOG server"
        ::= { nptTrap 2459 }

   nptMsMngLinkDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Multi-shelf management interface down"
        ::= { nptTrap 2457 }

   nptCfgSyncDelayed NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "CFG Sync is slow and delayed"
        ::= { nptTrap 2085 }

   nptSyslogServerUnreachable NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The SYSLOG server is not reachable"
        ::= { nptTrap 2458 }

   nptLocalTmuLolT0 NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The local TMU lost lock to T0"
        ::= { nptTrap 2084 }

   nptNtpSelectedServerChange NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NTP Selected Server Change"
        ::= { nptTrap 2460 }

   nptNtpServerUnavailable NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NTP Selected Server Unavailable"
        ::= { nptTrap 2461 }

   nptNtpUnsynced NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "NTP unsynced with servers"
        ::= { nptTrap 2462 }

   nptMacDuplicationDetected NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MAC Duplication is Detected"
        ::= { nptTrap 6529 }
        
   nptMacDuplicationCleared NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MAC Duplication is Cleared"
        ::= { nptTrap 6530 }

   nptEcmpGroupResourceFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ECMP Group Resource is full"
        ::= { nptTrap 6170 }

   nptMultiUseResourceFullTc NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Multi-Use Resource is full"
        ::= { nptTrap 6171 }
        
   nptRsvpTeLoadShareTunnelGroupResourceFull NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The RSVP-TE Load Share Tunnel Group related DP resource is full"
        ::= { nptTrap 6168 }

   nptLdpoRsvpLspResourceFull NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "The LDP over RSVP-LSP related DP resource is full"
        ::= { nptTrap 6169 }
        
   nptPwLoopDetected NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "PW Loop Detected"
        ::= { nptTrap 6360 }

   nptFan0Out NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "FAN0 module is not present"
        ::= { nptTrap 2086 }

   nptFan1Out NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "FAN1 module is not present"
        ::= { nptTrap 2087 }
        
   nptFan2Out NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "FAN2 module is not present"
        ::= { nptTrap 2088 }

   nptFan3Out NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "FAN3 module is not present"
        ::= { nptTrap 2089 }
        
   nptFan4Out NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "FAN4 module is not present"
        ::= { nptTrap 2090 }

   nptFan5Out NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "FAN5 module is not present"
        ::= { nptTrap 2091 }

   nptFan6Out NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "FAN6 module is not present"
        ::= { nptTrap 2092 }
        
   nptFan7Out NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "FAN7 module is not present"
        ::= { nptTrap 2093 }

   nptMsdpSaLimitTca NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "When exceeding configured threshold value of number of SA-Cache entries and/or SA messages (in %)"
        ::= { nptTrap 7250 }
        
   nptMsdpSessionDown NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "When MSDP peer state transits from 'established' state to any other state NPT  reports MSDP Session Down' event with the remote peer IP address, last error and the current peer state."
        ::= { nptTrap 7251 }

   nptMsdpSessionUp NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "When MSDP peer state transits to 'established' state from any other state, NPT shall report MSDP Session Up' event with the remote peer IP address and the current peer state"
        ::= { nptTrap 7252 }

   nptMsdpPeerStateTranstition NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "MSDP peer state from any state to any state transition"
        ::= { nptTrap 7254 }
        
   nptMsdpSaLimitTcaAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "When exceeding configured threshold value of number of SA-Cache entries and/or SA messages (in %)"
        ::= { nptTrap 7255 }

   nptMsdpSessionDownAlarm NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "When MSDP peer state transits from 'established' state to any other state NPT  reports MSDP Session Down' event with the remote peer IP address, last error and the current peer state."
        ::= { nptTrap 7257 }
        
   nptUnsupportEvpnRt5NotInstalled NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "ecursive resolution of EVPN RT-5 is not supported, route not installed"
        ::= { nptTrap 6725 }

   nptRxPsnSnOutOfJb NOTIFICATION-TYPE
      OBJECTS { nptObjectId, nptAlarmId, nptAlarmName, nptAlarmDescription, nptAlarmSeverity, nptAlarmType, nptNeId, nptAlarmTimeStamp, nptAlarmAddtionalinfo } 
      STATUS  current
       DESCRIPTION
               "Received packet is out of Jitter buffer range"
        ::= { nptTrap 3614 }

END
