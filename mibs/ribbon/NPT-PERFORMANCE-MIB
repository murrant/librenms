-- File Name : NPT-PERFORMANCE-MIB
-- Date      : Tue Jul 05 09:15:57 CST 2011
-- Author    : AdventNet Agent Toolkit C Edition - MibEditor 6



NPT-PERFORMANCE-MIB	DEFINITIONS ::= BEGIN
	IMPORTS
		nptPerformance
			FROM NPT-ROOT-MIB
		RowStatus, DisplayString
			FROM SNMPv2-TC
		DisplayString
			FROM RFC1213-MIB
		MODULE-IDENTITY, OBJECT-TYPE, Integer32, Counter64, enterprises
			FROM SNMPv2-SMI;

	nptPerformanceModule	MODULE-IDENTITY
		LAST-UPDATED	"201105240945Z"
		ORGANIZATION	"Ribbon Communications Inc."
		CONTACT-INFO	"on.support@rbbn.com 
                         Ribbon Communications Inc.,China
                         Dongxin Tower, No.398 Wensan Road, 
                         Hangzhou, 310012 P.R.China"
		DESCRIPTION		"The MIB module for NPT1800."
		REVISION		"201105240945Z"
		DESCRIPTION		""
		::=  {  nptPerformance  1  }

	org	OBJECT IDENTIFIER
		::=  {  iso  3  }

	dod	OBJECT IDENTIFIER
		::=  {  org  6  }

	internet	OBJECT IDENTIFIER
		::=  {  dod  1  }

	private	OBJECT IDENTIFIER
		::=  {  internet  4  }

	enterprises	OBJECT IDENTIFIER
		::=  {  private  1  }

	nptEthIfGroup	OBJECT IDENTIFIER
		::=  {  nptPerformanceModule  1  }
		
	nptSdhIfGroup	OBJECT IDENTIFIER
		::=  {  nptPerformanceModule  2  }
		
	nptSonetIfGroup	OBJECT IDENTIFIER
		::=  {  nptPerformanceModule  3  }
		
	nptCesIfGroup	OBJECT IDENTIFIER
		::=  {  nptPerformanceModule  4  }
		
	nptPtp1588IfGroup	OBJECT IDENTIFIER
		::=  {  nptPerformanceModule  5  }
		
	nptCfmIfGroup	OBJECT IDENTIFIER
		::=  {  nptPerformanceModule  6  }
		
	nptOTNIfGroup	OBJECT IDENTIFIER
		::=  {  nptPerformanceModule  7  }

    nptLifGroup	OBJECT IDENTIFIER
        ::=  {  nptPerformanceModule  9  }
        
    nptFlexEGroup	OBJECT IDENTIFIER
        ::=  {  nptPerformanceModule  10  }
        
    nptTMUGroup	OBJECT IDENTIFIER
        ::=  {  nptPerformanceModule  11  }
        
    nptCardGroup	OBJECT IDENTIFIER
        ::=  {  nptPerformanceModule  12  }
        
    nptOZRGroup	OBJECT IDENTIFIER
        ::=  {  nptPerformanceModule  13  }
        
	nptPmXEPort	OBJECT IDENTIFIER
		::=  {  nptEthIfGroup  1  }

	nptPmGEPort	OBJECT IDENTIFIER
		::=  {  nptEthIfGroup  2  }
		
	nptPmCEPort	OBJECT IDENTIFIER
		::=  {  nptEthIfGroup  3  }
		
	nptLagIfGroup OBJECT IDENTIFIER
		::=  {  nptEthIfGroup  4  }
		
	nptPmGE25Port	OBJECT IDENTIFIER
		::=  {  nptEthIfGroup  5  }
		
	nptPmGE50Port	OBJECT IDENTIFIER
		::=  {  nptEthIfGroup  6  }
		
	nptPmETPort	OBJECT IDENTIFIER
		::=  {  nptEthIfGroup  7  }
		
	nptStmIfGroup	OBJECT IDENTIFIER
		::=  {  nptSdhIfGroup  1  }
		
	nptVc4IfGroup	OBJECT IDENTIFIER
		::=  {  nptSdhIfGroup  2  }
		
	nptVc12IfGroup	OBJECT IDENTIFIER
		::=  {  nptSdhIfGroup  3  }
		
	nptE1ppiIfGroup	OBJECT IDENTIFIER
		::=  {  nptSdhIfGroup  4  }
		
	nptE1IfGroup	OBJECT IDENTIFIER
		::=  {  nptSdhIfGroup  5  }
		
	nptOcIfGroup	OBJECT IDENTIFIER
		::=  {  nptSonetIfGroup  1  }
		
	nptStsIfGroup	OBJECT IDENTIFIER
		::=  {  nptSonetIfGroup  2  }
		
	nptVt15IfGroup	OBJECT IDENTIFIER
		::=  {  nptSonetIfGroup  3  }
		
	nptDs1LineIfGroup	OBJECT IDENTIFIER
		::=  {  nptSonetIfGroup  4  }
		
	nptDs1PathIfGroup	OBJECT IDENTIFIER
		::=  {  nptSonetIfGroup  5  }
        
	nptDs3LineIfGroup	OBJECT IDENTIFIER
		::=  {  nptSonetIfGroup  6  }
		
	nptDs3PathIfGroup	OBJECT IDENTIFIER
		::=  {  nptSonetIfGroup  7  }
		
	nptCesServiceIfGroup	OBJECT IDENTIFIER
		::=  {  nptCesIfGroup  1  }
		
	nptPtpPortIfGroup	OBJECT IDENTIFIER
		::=  {  nptPtp1588IfGroup  1  }
		
	nptPtpSlaveIfGroup	OBJECT IDENTIFIER
		::=  {  nptPtp1588IfGroup  2  }
        
	nptPtpSlavetimeIfGroup	OBJECT IDENTIFIER
		::=  {  nptPtp1588IfGroup  3  }
        
	nptPtp1588PortIfGroup	OBJECT IDENTIFIER
		::=  {  nptPtp1588IfGroup  4  }
		
	nptMaIfGroup	OBJECT IDENTIFIER
		::=  {  nptCfmIfGroup  1  }
		
	nptLocalMepIfGroup	OBJECT IDENTIFIER
		::=  {  nptCfmIfGroup  2  }
		
	nptRemoteMepIfGroup	OBJECT IDENTIFIER
		::=  {  nptCfmIfGroup  3  }
		
	nptRemoteMepdmIfGroup	OBJECT IDENTIFIER
		::=  {  nptCfmIfGroup  4  }
		
	nptRemoteMepslmIfGroup	OBJECT IDENTIFIER
		::=  {  nptCfmIfGroup  5  }
		
	nptODU2Port	OBJECT IDENTIFIER
		::=  {  nptOTNIfGroup  1  }

	nptODU2ePort	OBJECT IDENTIFIER
		::=  {  nptOTNIfGroup  2  }
		
	nptODU4Port	OBJECT IDENTIFIER
		::=  {  nptOTNIfGroup  3  }
		
	nptOTU2Port OBJECT IDENTIFIER
		::=  {  nptOTNIfGroup  4  }
		
	nptOTU2ePort OBJECT IDENTIFIER
		::=  {  nptOTNIfGroup  5  }
	
	nptOTU4Port OBJECT IDENTIFIER
		::=  {  nptOTNIfGroup  6  }
        
    nptOTUC2Port OBJECT IDENTIFIER
        ::=  {  nptOTNIfGroup  7  }
        
    nptODUC2Port OBJECT IDENTIFIER
        ::=  {  nptOTNIfGroup  8  }     
        
	nptACLifGroup	OBJECT IDENTIFIER
		::=  {  nptLifGroup  1  }
		
	nptACLifRxCosGroup	OBJECT IDENTIFIER
		::=  {  nptLifGroup  2  }
		
	nptACLifTxCosGroup	OBJECT IDENTIFIER
		::=  {  nptLifGroup  3  }
        
	nptL3LifGroup	OBJECT IDENTIFIER
		::=  {  nptLifGroup  5  }
		
	nptL3LifRxCosGroup	OBJECT IDENTIFIER
		::=  {  nptLifGroup  6  }
		
	nptL3LifTxCosGroup	OBJECT IDENTIFIER
		::=  {  nptLifGroup  7  }
        
	nptFlexEChannelGroup	OBJECT IDENTIFIER
		::=  {  nptFlexEGroup  1  }
		
	nptSPPGroup	OBJECT IDENTIFIER
		::=  {  nptFlexEGroup  2  }
        
	nptFlexEPortGroup	OBJECT IDENTIFIER
		::=  {  nptFlexEGroup  3  }
        
	nptTMU	OBJECT IDENTIFIER
		::=  {  nptTMUGroup  1  }
        
	nptCard	OBJECT IDENTIFIER
		::=  {  nptCardGroup  1  }

	nptOZR	OBJECT IDENTIFIER
		::=  {  nptOZRGroup  1  }

	nptPmXEPortCurrentTable	OBJECT-TYPE
		SYNTAX		SEQUENCE  OF  NptPmXEPortCurrentEntry
		MAX-ACCESS	not-accessible
		STATUS		current
		DESCRIPTION	"Description"
		::=  { nptPmXEPort  1 }

	nptPmXEPortCurrentEntry	OBJECT-TYPE
		SYNTAX		NptPmXEPortCurrentEntry
		MAX-ACCESS	not-accessible
		STATUS		current
		DESCRIPTION	"Row Description"
		INDEX		{  nptPmXEPortCurrentIndex  }
		::=  { nptPmXEPortCurrentTable 1 }

	NptPmXEPortCurrentEntry  ::=  SEQUENCE {
	    nptPmXEPortCurrentIndex  Integer32,
		nptPmXEPortCurrentMoDescription  DisplayString,
	    nptPmXEPortCurrentRxOctets  Counter64,
		nptPmXEPortCurrentRxPkts  Counter64,
		nptPmXEPortCurrentRxBroadcastPkts  Counter64,
		nptPmXEPortCurrentRxMulticastPkts  Counter64,
		nptPmXEPortCurrentTxOctets  Counter64,
		nptPmXEPortCurrentTxPkts  Counter64,
		nptPmXEPortCurrentRxErrorPkts  Counter64,
		nptPmXEPortCurrentRxPkts64  Counter64,
		nptPmXEPortCurrentRxPkts127  Counter64,
		nptPmXEPortCurrentRxPkts255  Counter64,
		nptPmXEPortCurrentRxPkts511  Counter64,
		nptPmXEPortCurrentRxPkts1023  Counter64,
		nptPmXEPortCurrentRxPktsMtu  Counter64,
		nptPmXEPortCurrentRxUndersizePkts  Counter64,
		nptPmXEPortCurrentRxOversizePkts  Counter64,
		nptPmXEPortCurrentRxPausePkts  Counter64,
		nptPmXEPortCurrentRxJabberPkts  Counter64,
		nptPmXEPortCurrentRxCRCAlignErrorPkts  Counter64,
		nptPmXEPortCurrentRxFragments  Counter64,
		nptPmXEPortCurrentCollisionErrors  Counter64,
		nptPmXEPortCurrentPCSLCV  Counter64,
		nptPmXEPortCurrentPCSES  Counter64,
		nptPmXEPortCurrentPCSSES  Counter64,
		nptPmXEPortCurrentPCSUAS  Counter64,
		nptPmXEPortCurrentFECCE  Counter64,
		nptPmXEPortCurrentFECUCE  Counter64,
		nptPmXEPortCurrentPREFECBER  Counter64,
		nptPmXEPortCurrentINMaximumRate  Counter64,
		nptPmXEPortCurrentINAverageRate  Counter64,
		nptPmXEPortCurrentINCurrentRate  Counter64,
		nptPmXEPortCurrentINMaximumPPS  Counter64,
		nptPmXEPortCurrentINAveragePPS  Counter64,
		nptPmXEPortCurrentINCurrentPPS  Counter64,
		nptPmXEPortCurrentINMaximumUtilization  Counter64,
		nptPmXEPortCurrentINAverageUtilization  Counter64,
		nptPmXEPortCurrentINCurrentUtilization  Counter64,
		nptPmXEPortCurrentOUTMaximumRate  Counter64,
		nptPmXEPortCurrentOUTAverageRate  Counter64,
		nptPmXEPortCurrentOUTCurrentRate  Counter64,
		nptPmXEPortCurrentOUTMaximumPPS  Counter64,
		nptPmXEPortCurrentOUTAveragePPS  Counter64,
		nptPmXEPortCurrentOUTCurrentPPS  Counter64,
		nptPmXEPortCurrentOUTMaximumUtilization  Counter64,
		nptPmXEPortCurrentOUTAverageUtilization  Counter64,
		nptPmXEPortCurrentOUTCurrentUtilization  Counter64,
		nptPmXEPortCurrentLinkDownSeconds  Counter64,
		nptPmXEPortCurrentOSNRMax  DisplayString,
		nptPmXEPortCurrentOSNRMin  DisplayString,
		nptPmXEPortCurrentMaxRxPower  DisplayString,
		nptPmXEPortCurrentMinRxPower  DisplayString,
        nptPmXEPortCurrentTxPower   DisplayString
		}


	nptPmXEPortCurrentIndex	OBJECT-TYPE	
		SYNTAX			Integer32  ( -2147483648 .. 2147483647  ) 
		MAX-ACCESS		read-only
		STATUS			current
		DESCRIPTION		"Column Description"
		::=  {  nptPmXEPortCurrentEntry  1  }
		
	nptPmXEPortCurrentMoDescription	OBJECT-TYPE	
		SYNTAX			DisplayString 
		MAX-ACCESS		read-only
		STATUS			current
		DESCRIPTION		"Column Description"
		::=  {  nptPmXEPortCurrentEntry  2  }


	nptPmXEPortCurrentRxOctets	OBJECT-TYPE	
		SYNTAX			Counter64
		MAX-ACCESS		read-only
		STATUS			current
		DESCRIPTION		"Column Description"
		::=  {  nptPmXEPortCurrentEntry  3  }


	nptPmXEPortCurrentRxPkts	OBJECT-TYPE	
		SYNTAX			Counter64
		MAX-ACCESS		read-only
		STATUS			current
		DESCRIPTION		"Description"
		::=  {  nptPmXEPortCurrentEntry  4  }


	nptPmXEPortCurrentRxBroadcastPkts	OBJECT-TYPE	
		SYNTAX			Counter64
		MAX-ACCESS		read-only
		STATUS			current
		DESCRIPTION		"Description"
		::=  {  nptPmXEPortCurrentEntry  5  }


	nptPmXEPortCurrentRxMulticastPkts	OBJECT-TYPE	
		SYNTAX			Counter64
		MAX-ACCESS		read-only
		STATUS			current
		DESCRIPTION		"Description"
		::=  {  nptPmXEPortCurrentEntry  6  }


	nptPmXEPortCurrentTxOctets	OBJECT-TYPE	
		SYNTAX			Counter64
		MAX-ACCESS		read-only
		STATUS			current
		DESCRIPTION		"Description"
		::=  {  nptPmXEPortCurrentEntry  7  }


	nptPmXEPortCurrentTxPkts	OBJECT-TYPE	
		SYNTAX			Counter64
		MAX-ACCESS		read-only
		STATUS			current
		DESCRIPTION		"Description"
		::=  {  nptPmXEPortCurrentEntry  8  }


	nptPmXEPortCurrentRxErrorPkts	OBJECT-TYPE	
		SYNTAX			Counter64
		MAX-ACCESS		read-only
		STATUS			current
		DESCRIPTION		"Description"
		::=  {  nptPmXEPortCurrentEntry  9  }


	nptPmXEPortCurrentRxPkts64	OBJECT-TYPE	
		SYNTAX			Counter64
		MAX-ACCESS		read-only
		STATUS			current
		DESCRIPTION		"Description"
		::=  {  nptPmXEPortCurrentEntry  10  }


	nptPmXEPortCurrentRxPkts127	OBJECT-TYPE	
		SYNTAX			Counter64
		MAX-ACCESS		read-only
		STATUS			current
		DESCRIPTION		"Description"
		::=  {  nptPmXEPortCurrentEntry  11  }


	nptPmXEPortCurrentRxPkts255	OBJECT-TYPE	
		SYNTAX			Counter64
		MAX-ACCESS		read-only
		STATUS			current
		DESCRIPTION		"Description"
		::=  {  nptPmXEPortCurrentEntry  12  }


	nptPmXEPortCurrentRxPkts511	OBJECT-TYPE	
		SYNTAX			Counter64
		MAX-ACCESS		read-only
		STATUS			current
		DESCRIPTION		"Description"
		::=  {  nptPmXEPortCurrentEntry  13  }


	nptPmXEPortCurrentRxPkts1023	OBJECT-TYPE	
		SYNTAX			Counter64
		MAX-ACCESS		read-only
		STATUS			current
		DESCRIPTION		"Description"
		::=  {  nptPmXEPortCurrentEntry  14  }


	nptPmXEPortCurrentRxPktsMtu	OBJECT-TYPE	
		SYNTAX			Counter64
		MAX-ACCESS		read-only
		STATUS			current
		DESCRIPTION		"Description"
		::=  {  nptPmXEPortCurrentEntry  15  }


	nptPmXEPortCurrentRxUndersizePkts	OBJECT-TYPE	
		SYNTAX			Counter64
		MAX-ACCESS		read-only
		STATUS			current
		DESCRIPTION		"Description"
		::=  {  nptPmXEPortCurrentEntry  16  }


	nptPmXEPortCurrentRxOversizePkts	OBJECT-TYPE	
		SYNTAX			Counter64
		MAX-ACCESS		read-only
		STATUS			current
		DESCRIPTION		"Description"
		::=  {  nptPmXEPortCurrentEntry  17  }


	nptPmXEPortCurrentRxPausePkts	OBJECT-TYPE	
		SYNTAX			Counter64
		MAX-ACCESS		read-only
		STATUS			current
		DESCRIPTION		"Description"
		::=  {  nptPmXEPortCurrentEntry  18  }
		
	nptPmXEPortCurrentRxJabberPkts	OBJECT-TYPE	
		SYNTAX			Counter64
		MAX-ACCESS		read-only
		STATUS			current
		DESCRIPTION		"Description"
		::=  {  nptPmXEPortCurrentEntry  19  }


	nptPmXEPortCurrentRxCRCAlignErrorPkts	OBJECT-TYPE	
		SYNTAX			Counter64
		MAX-ACCESS		read-only
		STATUS			current
		DESCRIPTION		"Description"
		::=  {  nptPmXEPortCurrentEntry  20  }


	nptPmXEPortCurrentRxFragments	OBJECT-TYPE	
		SYNTAX			Counter64
		MAX-ACCESS		read-only
		STATUS			current
		DESCRIPTION		"Description"
		::=  {  nptPmXEPortCurrentEntry  21  }


	nptPmXEPortCurrentCollisionErrors	OBJECT-TYPE	
		SYNTAX			Counter64
		MAX-ACCESS		read-only
		STATUS			current
		DESCRIPTION		"Description"
		::=  {  nptPmXEPortCurrentEntry  22  }


	nptPmXEPortCurrentPCSLCV	OBJECT-TYPE	
		SYNTAX			Counter64
		MAX-ACCESS		read-only
		STATUS			current
		DESCRIPTION		"Description"
		::=  {  nptPmXEPortCurrentEntry  23  }


	nptPmXEPortCurrentPCSES	OBJECT-TYPE	
		SYNTAX			Counter64
		MAX-ACCESS		read-only
		STATUS			current
		DESCRIPTION		"Description"
		::=  {  nptPmXEPortCurrentEntry  24  }


	nptPmXEPortCurrentPCSSES	OBJECT-TYPE	
		SYNTAX			Counter64
		MAX-ACCESS		read-only
		STATUS			current
		DESCRIPTION		"Description"
		::=  {  nptPmXEPortCurrentEntry  25  }


	nptPmXEPortCurrentPCSUAS	OBJECT-TYPE	
		SYNTAX			Counter64
		MAX-ACCESS		read-only
		STATUS			current
		DESCRIPTION		"Description"
		::=  {  nptPmXEPortCurrentEntry  26  }
		
	nptPmXEPortCurrentFECCE	OBJECT-TYPE	
		SYNTAX			Counter64
		MAX-ACCESS		read-only
		STATUS			current
		DESCRIPTION		"Description"
		::=  {  nptPmXEPortCurrentEntry  27  }


	nptPmXEPortCurrentFECUCE	OBJECT-TYPE	
		SYNTAX			Counter64
		MAX-ACCESS		read-only
		STATUS			current
		DESCRIPTION		"Description"
		::=  {  nptPmXEPortCurrentEntry  28  }


	nptPmXEPortCurrentPREFECBER	OBJECT-TYPE	
		SYNTAX			Counter64
		MAX-ACCESS		read-only
		STATUS			current
		DESCRIPTION		"Description"
		::=  {  nptPmXEPortCurrentEntry  29  }


	nptPmXEPortCurrentINMaximumRate	OBJECT-TYPE	
		SYNTAX			Counter64
		MAX-ACCESS		read-only
		STATUS			current
		DESCRIPTION		"Description"
		::=  {  nptPmXEPortCurrentEntry  30  }
		
	nptPmXEPortCurrentINAverageRate	OBJECT-TYPE	
		SYNTAX			Counter64
		MAX-ACCESS		read-only
		STATUS			current
		DESCRIPTION		"Description"
		::=  {  nptPmXEPortCurrentEntry  31  }
		
	nptPmXEPortCurrentINCurrentRate	OBJECT-TYPE	
		SYNTAX			Counter64
		MAX-ACCESS		read-only
		STATUS			current
		DESCRIPTION		"Description"
		::=  {  nptPmXEPortCurrentEntry  32  }
		
	nptPmXEPortCurrentINMaximumPPS	OBJECT-TYPE	
		SYNTAX			Counter64
		MAX-ACCESS		read-only
		STATUS			current
		DESCRIPTION		"Description"
		::=  {  nptPmXEPortCurrentEntry  33  }
		
	nptPmXEPortCurrentINAveragePPS	OBJECT-TYPE	
		SYNTAX			Counter64
		MAX-ACCESS		read-only
		STATUS			current
		DESCRIPTION		"Description"
		::=  {  nptPmXEPortCurrentEntry  34  }
		
	nptPmXEPortCurrentINCurrentPPS	OBJECT-TYPE	
		SYNTAX			Counter64
		MAX-ACCESS		read-only
		STATUS			current
		DESCRIPTION		"Description"
		::=  {  nptPmXEPortCurrentEntry  35  }
		
	nptPmXEPortCurrentINMaximumUtilization	OBJECT-TYPE	
		SYNTAX			Counter64
		MAX-ACCESS		read-only
		STATUS			current
		DESCRIPTION		"Description"
		::=  {  nptPmXEPortCurrentEntry  36  }
		
	nptPmXEPortCurrentINAverageUtilization	OBJECT-TYPE	
		SYNTAX			Counter64
		MAX-ACCESS		read-only
		STATUS			current
		DESCRIPTION		"Description"
		::=  {  nptPmXEPortCurrentEntry  37  }
		
	nptPmXEPortCurrentINCurrentUtilization	OBJECT-TYPE	
		SYNTAX			Counter64
		MAX-ACCESS		read-only
		STATUS			current
		DESCRIPTION		"Description"
		::=  {  nptPmXEPortCurrentEntry  38  }
		
	nptPmXEPortCurrentOUTMaximumRate	OBJECT-TYPE	
		SYNTAX			Counter64
		MAX-ACCESS		read-only
		STATUS			current
		DESCRIPTION		"Description"
		::=  {  nptPmXEPortCurrentEntry  39  }
		
	nptPmXEPortCurrentOUTAverageRate	OBJECT-TYPE	
		SYNTAX			Counter64
		MAX-ACCESS		read-only
		STATUS			current
		DESCRIPTION		"Description"
		::=  {  nptPmXEPortCurrentEntry  40  }
		
	nptPmXEPortCurrentOUTCurrentRate	OBJECT-TYPE	
		SYNTAX			Counter64
		MAX-ACCESS		read-only
		STATUS			current
		DESCRIPTION		"Description"
		::=  {  nptPmXEPortCurrentEntry  41  }
		
	nptPmXEPortCurrentOUTMaximumPPS	OBJECT-TYPE	
		SYNTAX			Counter64
		MAX-ACCESS		read-only
		STATUS			current
		DESCRIPTION		"Description"
		::=  {  nptPmXEPortCurrentEntry  42  }
		
	nptPmXEPortCurrentOUTAveragePPS	OBJECT-TYPE	
		SYNTAX			Counter64
		MAX-ACCESS		read-only
		STATUS			current
		DESCRIPTION		"Description"
		::=  {  nptPmXEPortCurrentEntry  43  }
		
	nptPmXEPortCurrentOUTCurrentPPS	OBJECT-TYPE	
		SYNTAX			Counter64
		MAX-ACCESS		read-only
		STATUS			current
		DESCRIPTION		"Description"
		::=  {  nptPmXEPortCurrentEntry  44  }
		
	nptPmXEPortCurrentOUTMaximumUtilization	OBJECT-TYPE	
		SYNTAX			Counter64
		MAX-ACCESS		read-only
		STATUS			current
		DESCRIPTION		"Description"
		::=  {  nptPmXEPortCurrentEntry  45  }
		
	nptPmXEPortCurrentOUTAverageUtilization	OBJECT-TYPE	
		SYNTAX			Counter64
		MAX-ACCESS		read-only
		STATUS			current
		DESCRIPTION		"Description"
		::=  {  nptPmXEPortCurrentEntry  46  }
		
	nptPmXEPortCurrentOUTCurrentUtilization	OBJECT-TYPE	
		SYNTAX			Counter64
		MAX-ACCESS		read-only
		STATUS			current
		DESCRIPTION		"Description"
		::=  {  nptPmXEPortCurrentEntry  47  }
		
	nptPmXEPortCurrentLinkDownSeconds	OBJECT-TYPE	
		SYNTAX			Counter64
		MAX-ACCESS		read-only
		STATUS			current
		DESCRIPTION		"Description"
		::=  {  nptPmXEPortCurrentEntry  48  }
		
	nptPmXEPortCurrentOSNRMax	OBJECT-TYPE	
		SYNTAX			DisplayString
		MAX-ACCESS		read-only
		STATUS			current
		DESCRIPTION		"Description"
		::=  {  nptPmXEPortCurrentEntry  49  }
		
	nptPmXEPortCurrentOSNRMin	OBJECT-TYPE	
		SYNTAX			DisplayString
		MAX-ACCESS		read-only
		STATUS			current
		DESCRIPTION		"Description"
		::=  {  nptPmXEPortCurrentEntry  50  }
               
	nptPmXEPortCurrentMaxRxPower	OBJECT-TYPE	
		SYNTAX			DisplayString
		MAX-ACCESS		read-only
		STATUS			current
		DESCRIPTION		"Description"
		::=  {  nptPmXEPortCurrentEntry  51  }
		
	nptPmXEPortCurrentMinRxPower	OBJECT-TYPE	
		SYNTAX			DisplayString
		MAX-ACCESS		read-only
		STATUS			current
		DESCRIPTION		"Description"
		::=  {  nptPmXEPortCurrentEntry  52  }
        
	nptPmXEPortCurrentTxPower	OBJECT-TYPE	
		SYNTAX			DisplayString
		MAX-ACCESS		read-only
		STATUS			current
		DESCRIPTION		"Description"
		::=  {  nptPmXEPortCurrentEntry  53  }	
		
	nptPmXEPortTotalTable	OBJECT-TYPE
		SYNTAX		SEQUENCE  OF  NptPmXEPortTotalEntry
		MAX-ACCESS	not-accessible
		STATUS		current
		DESCRIPTION	"Description"
		::=  { nptPmXEPort  2 }

	nptPmXEPortTotalEntry	OBJECT-TYPE
		SYNTAX		NptPmXEPortTotalEntry
		MAX-ACCESS	not-accessible
		STATUS		current
		DESCRIPTION	"Row Description"
		INDEX		{  nptPmXEPortTotalIndex  }
		::=  { nptPmXEPortTotalTable 1 }

	NptPmXEPortTotalEntry  ::=  SEQUENCE {
	    nptPmXEPortTotalIndex  Integer32,
		nptPmXEPortTotalMoDescription  DisplayString,
	    nptPmXEPortTotalRxOctets  Counter64,
		nptPmXEPortTotalRxPkts  Counter64,
		nptPmXEPortTotalRxBroadcastPkts  Counter64,
		nptPmXEPortTotalRxMulticastPkts  Counter64,
		nptPmXEPortTotalTxOctets  Counter64,
		nptPmXEPortTotalTxPkts  Counter64,
		nptPmXEPortTotalRxErrorPkts  Counter64,
		nptPmXEPortTotalRxPkts64  Counter64,
		nptPmXEPortTotalRxPkts127  Counter64,
		nptPmXEPortTotalRxPkts255  Counter64,
		nptPmXEPortTotalRxPkts511  Counter64,
		nptPmXEPortTotalRxPkts1023  Counter64,
		nptPmXEPortTotalRxPktsMtu  Counter64,
		nptPmXEPortTotalRxUndersizePkts  Counter64,
		nptPmXEPortTotalRxOversizePkts  Counter64,
		nptPmXEPortTotalRxPausePkts  Counter64,
		nptPmXEPortTotalRxJabberPkts  Counter64,
		nptPmXEPortTotalRxCRCAlignErrorPkts  Counter64,
		nptPmXEPortTotalRxFragments  Counter64,
		nptPmXEPortTotalCollisionErrors  Counter64,
		nptPmXEPortTotalPCSLCV  Counter64,
		nptPmXEPortTotalPCSES  Counter64,
		nptPmXEPortTotalPCSSES  Counter64,
		nptPmXEPortTotalPCSUAS  Counter64,
		nptPmXEPortTotalFECCE  Counter64,
		nptPmXEPortTotalFECUCE  Counter64,
		nptPmXEPortTotalPREFECBER  Counter64,
		nptPmXEPortTotalINMaximumRate  Counter64,
		nptPmXEPortTotalINAverageRate  Counter64,
		nptPmXEPortTotalINTotalRate  Counter64,
		nptPmXEPortTotalINMaximumPPS  Counter64,
		nptPmXEPortTotalINAveragePPS  Counter64,
		nptPmXEPortTotalINTotalPPS  Counter64,
		nptPmXEPortTotalINMaximumUtilization  Counter64,
		nptPmXEPortTotalINAverageUtilization  Counter64,
		nptPmXEPortTotalINTotalUtilization  Counter64,
		nptPmXEPortTotalOUTMaximumRate  Counter64,
		nptPmXEPortTotalOUTAverageRate  Counter64,
		nptPmXEPortTotalOUTTotalRate  Counter64,
		nptPmXEPortTotalOUTMaximumPPS  Counter64,
		nptPmXEPortTotalOUTAveragePPS  Counter64,
		nptPmXEPortTotalOUTTotalPPS  Counter64,
		nptPmXEPortTotalOUTMaximumUtilization  Counter64,
		nptPmXEPortTotalOUTAverageUtilization  Counter64,
		nptPmXEPortTotalOUTTotalUtilization  Counter64,
		nptPmXEPortTotalLinkDownSeconds  Counter64,
		nptPmXEPortTotalOSNRMax  DisplayString,
		nptPmXEPortTotalOSNRMin  DisplayString,
		nptPmXEPortTotalMaxRxPower  DisplayString,
		nptPmXEPortTotalMinRxPower  DisplayString,
        nptPmXEPortTotalTxPower   DisplayString
		}


	nptPmXEPortTotalIndex	OBJECT-TYPE	
		SYNTAX			Integer32  ( -2147483648 .. 2147483647  ) 
		MAX-ACCESS		read-only
		STATUS			current
		DESCRIPTION		"Column Description"
		::=  {  nptPmXEPortTotalEntry  1  }
	
	
	nptPmXEPortTotalMoDescription	OBJECT-TYPE	
		SYNTAX			DisplayString 
		MAX-ACCESS		read-only
		STATUS			current
		DESCRIPTION		"Column Description"
		::=  {  nptPmXEPortTotalEntry  2  }


	nptPmXEPortTotalRxOctets	OBJECT-TYPE	
		SYNTAX			Counter64
		MAX-ACCESS		read-only
		STATUS			current
		DESCRIPTION		"Column Description"
		::=  {  nptPmXEPortTotalEntry  3  }


	nptPmXEPortTotalRxPkts	OBJECT-TYPE	
		SYNTAX			Counter64
		MAX-ACCESS		read-only
		STATUS			current
		DESCRIPTION		"Description"
		::=  {  nptPmXEPortTotalEntry  4  }


	nptPmXEPortTotalRxBroadcastPkts	OBJECT-TYPE	
		SYNTAX			Counter64
		MAX-ACCESS		read-only
		STATUS			current
		DESCRIPTION		"Description"
		::=  {  nptPmXEPortTotalEntry  5  }


	nptPmXEPortTotalRxMulticastPkts	OBJECT-TYPE	
		SYNTAX			Counter64
		MAX-ACCESS		read-only
		STATUS			current
		DESCRIPTION		"Description"
		::=  {  nptPmXEPortTotalEntry  6  }


	nptPmXEPortTotalTxOctets	OBJECT-TYPE	
		SYNTAX			Counter64
		MAX-ACCESS		read-only
		STATUS			current
		DESCRIPTION		"Description"
		::=  {  nptPmXEPortTotalEntry  7  }


	nptPmXEPortTotalTxPkts	OBJECT-TYPE	
		SYNTAX			Counter64
		MAX-ACCESS		read-only
		STATUS			current
		DESCRIPTION		"Description"
		::=  {  nptPmXEPortTotalEntry  8  }


	nptPmXEPortTotalRxErrorPkts	OBJECT-TYPE	
		SYNTAX			Counter64
		MAX-ACCESS		read-only
		STATUS			current
		DESCRIPTION		"Description"
		::=  {  nptPmXEPortTotalEntry  9  }


	nptPmXEPortTotalRxPkts64	OBJECT-TYPE	
		SYNTAX			Counter64
		MAX-ACCESS		read-only
		STATUS			current
		DESCRIPTION		"Description"
		::=  {  nptPmXEPortTotalEntry  10  }


	nptPmXEPortTotalRxPkts127	OBJECT-TYPE	
		SYNTAX			Counter64
		MAX-ACCESS		read-only
		STATUS			current
		DESCRIPTION		"Description"
		::=  {  nptPmXEPortTotalEntry  11  }


	nptPmXEPortTotalRxPkts255	OBJECT-TYPE	
		SYNTAX			Counter64
		MAX-ACCESS		read-only
		STATUS			current
		DESCRIPTION		"Description"
		::=  {  nptPmXEPortTotalEntry  12  }


	nptPmXEPortTotalRxPkts511	OBJECT-TYPE	
		SYNTAX			Counter64
		MAX-ACCESS		read-only
		STATUS			current
		DESCRIPTION		"Description"
		::=  {  nptPmXEPortTotalEntry  13  }


	nptPmXEPortTotalRxPkts1023	OBJECT-TYPE	
		SYNTAX			Counter64
		MAX-ACCESS		read-only
		STATUS			current
		DESCRIPTION		"Description"
		::=  {  nptPmXEPortTotalEntry  14  }


	nptPmXEPortTotalRxPktsMtu	OBJECT-TYPE	
		SYNTAX			Counter64
		MAX-ACCESS		read-only
		STATUS			current
		DESCRIPTION		"Description"
		::=  {  nptPmXEPortTotalEntry  15  }


	nptPmXEPortTotalRxUndersizePkts	OBJECT-TYPE	
		SYNTAX			Counter64
		MAX-ACCESS		read-only
		STATUS			current
		DESCRIPTION		"Description"
		::=  {  nptPmXEPortTotalEntry  16  }


	nptPmXEPortTotalRxOversizePkts	OBJECT-TYPE	
		SYNTAX			Counter64
		MAX-ACCESS		read-only
		STATUS			current
		DESCRIPTION		"Description"
		::=  {  nptPmXEPortTotalEntry  17  }


	nptPmXEPortTotalRxPausePkts	OBJECT-TYPE	
		SYNTAX			Counter64
		MAX-ACCESS		read-only
		STATUS			current
		DESCRIPTION		"Description"
		::=  {  nptPmXEPortTotalEntry  18  }
		
	nptPmXEPortTotalRxJabberPkts	OBJECT-TYPE	
		SYNTAX			Counter64
		MAX-ACCESS		read-only
		STATUS			current
		DESCRIPTION		"Description"
		::=  {  nptPmXEPortTotalEntry  19  }


	nptPmXEPortTotalRxCRCAlignErrorPkts	OBJECT-TYPE	
		SYNTAX			Counter64
		MAX-ACCESS		read-only
		STATUS			current
		DESCRIPTION		"Description"
		::=  {  nptPmXEPortTotalEntry  20  }


	nptPmXEPortTotalRxFragments	OBJECT-TYPE	
		SYNTAX			Counter64
		MAX-ACCESS		read-only
		STATUS			current
		DESCRIPTION		"Description"
		::=  {  nptPmXEPortTotalEntry  21  }


	nptPmXEPortTotalCollisionErrors	OBJECT-TYPE	
		SYNTAX			Counter64
		MAX-ACCESS		read-only
		STATUS			current
		DESCRIPTION		"Description"
		::=  {  nptPmXEPortTotalEntry  22  }


	nptPmXEPortTotalPCSLCV	OBJECT-TYPE	
		SYNTAX			Counter64
		MAX-ACCESS		read-only
		STATUS			current
		DESCRIPTION		"Description"
		::=  {  nptPmXEPortTotalEntry  23  }


	nptPmXEPortTotalPCSES	OBJECT-TYPE	
		SYNTAX			Counter64
		MAX-ACCESS		read-only
		STATUS			current
		DESCRIPTION		"Description"
		::=  {  nptPmXEPortTotalEntry  24  }


	nptPmXEPortTotalPCSSES	OBJECT-TYPE	
		SYNTAX			Counter64
		MAX-ACCESS		read-only
		STATUS			current
		DESCRIPTION		"Description"
		::=  {  nptPmXEPortTotalEntry  25  }


	nptPmXEPortTotalPCSUAS	OBJECT-TYPE	
		SYNTAX			Counter64
		MAX-ACCESS		read-only
		STATUS			current
		DESCRIPTION		"Description"
		::=  {  nptPmXEPortTotalEntry  26  }
		
	nptPmXEPortTotalFECCE	OBJECT-TYPE	
		SYNTAX			Counter64
		MAX-ACCESS		read-only
		STATUS			current
		DESCRIPTION		"Description"
		::=  {  nptPmXEPortTotalEntry  27  }


	nptPmXEPortTotalFECUCE	OBJECT-TYPE	
		SYNTAX			Counter64
		MAX-ACCESS		read-only
		STATUS			current
		DESCRIPTION		"Description"
		::=  {  nptPmXEPortTotalEntry  28  }


	nptPmXEPortTotalPREFECBER	OBJECT-TYPE	
		SYNTAX			Counter64
		MAX-ACCESS		read-only
		STATUS			current
		DESCRIPTION		"Description"
		::=  {  nptPmXEPortTotalEntry  29  }


	nptPmXEPortTotalINMaximumRate	OBJECT-TYPE	
		SYNTAX			Counter64
		MAX-ACCESS		read-only
		STATUS			current
		DESCRIPTION		"Description"
		::=  {  nptPmXEPortTotalEntry  30  }
		
	nptPmXEPortTotalINAverageRate	OBJECT-TYPE	
		SYNTAX			Counter64
		MAX-ACCESS		read-only
		STATUS			current
		DESCRIPTION		"Description"
		::=  {  nptPmXEPortTotalEntry  31  }
		
	nptPmXEPortTotalINTotalRate	OBJECT-TYPE	
		SYNTAX			Counter64
		MAX-ACCESS		read-only
		STATUS			current
		DESCRIPTION		"Description"
		::=  {  nptPmXEPortTotalEntry  32  }
		
	nptPmXEPortTotalINMaximumPPS	OBJECT-TYPE	
		SYNTAX			Counter64
		MAX-ACCESS		read-only
		STATUS			current
		DESCRIPTION		"Description"
		::=  {  nptPmXEPortTotalEntry  33  }
		
	nptPmXEPortTotalINAveragePPS	OBJECT-TYPE	
		SYNTAX			Counter64
		MAX-ACCESS		read-only
		STATUS			current
		DESCRIPTION		"Description"
		::=  {  nptPmXEPortTotalEntry  34  }
		
	nptPmXEPortTotalINTotalPPS	OBJECT-TYPE	
		SYNTAX			Counter64
		MAX-ACCESS		read-only
		STATUS			current
		DESCRIPTION		"Description"
		::=  {  nptPmXEPortTotalEntry  35  }
		
	nptPmXEPortTotalINMaximumUtilization	OBJECT-TYPE	
		SYNTAX			Counter64
		MAX-ACCESS		read-only
		STATUS			current
		DESCRIPTION		"Description"
		::=  {  nptPmXEPortTotalEntry  36  }
		
	nptPmXEPortTotalINAverageUtilization	OBJECT-TYPE	
		SYNTAX			Counter64
		MAX-ACCESS		read-only
		STATUS			current
		DESCRIPTION		"Description"
		::=  {  nptPmXEPortTotalEntry  37  }
		
	nptPmXEPortTotalINTotalUtilization	OBJECT-TYPE	
		SYNTAX			Counter64
		MAX-ACCESS		read-only
		STATUS			current
		DESCRIPTION		"Description"
		::=  {  nptPmXEPortTotalEntry  38  }
		
	nptPmXEPortTotalOUTMaximumRate	OBJECT-TYPE	
		SYNTAX			Counter64
		MAX-ACCESS		read-only
		STATUS			current
		DESCRIPTION		"Description"
		::=  {  nptPmXEPortTotalEntry  39  }
		
	nptPmXEPortTotalOUTAverageRate	OBJECT-TYPE	
		SYNTAX			Counter64
		MAX-ACCESS		read-only
		STATUS			current
		DESCRIPTION		"Description"
		::=  {  nptPmXEPortTotalEntry  40  }
		
	nptPmXEPortTotalOUTTotalRate	OBJECT-TYPE	
		SYNTAX			Counter64
		MAX-ACCESS		read-only
		STATUS			current
		DESCRIPTION		"Description"
		::=  {  nptPmXEPortTotalEntry  41  }
		
	nptPmXEPortTotalOUTMaximumPPS	OBJECT-TYPE	
		SYNTAX			Counter64
		MAX-ACCESS		read-only
		STATUS			current
		DESCRIPTION		"Description"
		::=  {  nptPmXEPortTotalEntry  42  }
		
	nptPmXEPortTotalOUTAveragePPS	OBJECT-TYPE	
		SYNTAX			Counter64
		MAX-ACCESS		read-only
		STATUS			current
		DESCRIPTION		"Description"
		::=  {  nptPmXEPortTotalEntry  43  }
		
	nptPmXEPortTotalOUTTotalPPS	OBJECT-TYPE	
		SYNTAX			Counter64
		MAX-ACCESS		read-only
		STATUS			current
		DESCRIPTION		"Description"
		::=  {  nptPmXEPortTotalEntry  44  }
		
	nptPmXEPortTotalOUTMaximumUtilization	OBJECT-TYPE	
		SYNTAX			Counter64
		MAX-ACCESS		read-only
		STATUS			current
		DESCRIPTION		"Description"
		::=  {  nptPmXEPortTotalEntry  45  }
		
	nptPmXEPortTotalOUTAverageUtilization	OBJECT-TYPE	
		SYNTAX			Counter64
		MAX-ACCESS		read-only
		STATUS			current
		DESCRIPTION		"Description"
		::=  {  nptPmXEPortTotalEntry  46  }
		
	nptPmXEPortTotalOUTTotalUtilization	OBJECT-TYPE	
		SYNTAX			Counter64
		MAX-ACCESS		read-only
		STATUS			current
		DESCRIPTION		"Description"
		::=  {  nptPmXEPortTotalEntry  47  }
		
	nptPmXEPortTotalLinkDownSeconds	OBJECT-TYPE	
		SYNTAX			Counter64
		MAX-ACCESS		read-only
		STATUS			current
		DESCRIPTION		"Description"
		::=  {  nptPmXEPortTotalEntry  48  }
		
	nptPmXEPortTotalOSNRMax	OBJECT-TYPE	
		SYNTAX			DisplayString
		MAX-ACCESS		read-only
		STATUS			current
		DESCRIPTION		"Description"
		::=  {  nptPmXEPortTotalEntry  49  }
		
	nptPmXEPortTotalOSNRMin	OBJECT-TYPE	
		SYNTAX			DisplayString
		MAX-ACCESS		read-only
		STATUS			current
		DESCRIPTION		"Description"
		::=  {  nptPmXEPortTotalEntry  50  }
               
	nptPmXEPortTotalMaxRxPower	OBJECT-TYPE	
		SYNTAX			DisplayString
		MAX-ACCESS		read-only
		STATUS			current
		DESCRIPTION		"Description"
		::=  {  nptPmXEPortTotalEntry  51  }
		
	nptPmXEPortTotalMinRxPower	OBJECT-TYPE	
		SYNTAX			DisplayString
		MAX-ACCESS		read-only
		STATUS			current
		DESCRIPTION		"Description"
		::=  {  nptPmXEPortTotalEntry  52  }
        
	nptPmXEPortTotalTxPower	OBJECT-TYPE	
		SYNTAX			DisplayString
		MAX-ACCESS		read-only
		STATUS			current
		DESCRIPTION		"Description"
		::=  {  nptPmXEPortTotalEntry  53  }	
		
	nptPmGEPortCurrentTable	OBJECT-TYPE
		SYNTAX		SEQUENCE  OF  NptPmGEPortCurrentEntry
		MAX-ACCESS	not-accessible
		STATUS		current
		DESCRIPTION	"Description"
		::=  { nptPmGEPort  1 }

	nptPmGEPortCurrentEntry	OBJECT-TYPE
		SYNTAX		NptPmGEPortCurrentEntry
		MAX-ACCESS	not-accessible
		STATUS		current
		DESCRIPTION	"Row Description"
		INDEX		{  nptPmGEPortCurrentIndex  }
		::=  { nptPmGEPortCurrentTable 1 }

	NptPmGEPortCurrentEntry  ::=  SEQUENCE {
	    nptPmGEPortCurrentIndex  Integer32,
		nptPmGEPortCurrentMoDescription  DisplayString,
	    nptPmGEPortCurrentRxOctets  Counter64,
		nptPmGEPortCurrentRxPkts  Counter64,
		nptPmGEPortCurrentRxBroadcastPkts  Counter64,
		nptPmGEPortCurrentRxMulticastPkts  Counter64,
		nptPmGEPortCurrentTxOctets  Counter64,
		nptPmGEPortCurrentTxPkts  Counter64,
		nptPmGEPortCurrentRxErrorPkts  Counter64,
		nptPmGEPortCurrentRxPkts64  Counter64,
		nptPmGEPortCurrentRxPkts127  Counter64,
		nptPmGEPortCurrentRxPkts255  Counter64,
		nptPmGEPortCurrentRxPkts511  Counter64,
		nptPmGEPortCurrentRxPkts1023  Counter64,
		nptPmGEPortCurrentRxPktsMtu  Counter64,
		nptPmGEPortCurrentRxUndersizePkts  Counter64,
		nptPmGEPortCurrentRxOversizePkts  Counter64,
		nptPmGEPortCurrentRxPausePkts  Counter64,
		nptPmGEPortCurrentRxJabberPkts  Counter64,
		nptPmGEPortCurrentRxCRCAlignErrorPkts  Counter64,
		nptPmGEPortCurrentRxFragments  Counter64,
		nptPmGEPortCurrentCollisionErrors  Counter64,
		nptPmGEPortCurrentPCSLCV  Counter64,
		nptPmGEPortCurrentPCSES  Counter64,
		nptPmGEPortCurrentPCSSES  Counter64,
		nptPmGEPortCurrentPCSUAS  Counter64,
		nptPmGEPortCurrentFECCE  Counter64,
		nptPmGEPortCurrentFECUCE  Counter64,
		nptPmGEPortCurrentPREFECBER  Counter64,
		nptPmGEPortCurrentINMaximumRate  Counter64,
		nptPmGEPortCurrentINAverageRate  Counter64,
		nptPmGEPortCurrentINCurrentRate  Counter64,
		nptPmGEPortCurrentINMaximumPPS  Counter64,
		nptPmGEPortCurrentINAveragePPS  Counter64,
		nptPmGEPortCurrentINCurrentPPS  Counter64,
		nptPmGEPortCurrentINMaximumUtilization  Counter64,
		nptPmGEPortCurrentINAverageUtilization  Counter64,
		nptPmGEPortCurrentINCurrentUtilization  Counter64,
		nptPmGEPortCurrentOUTMaximumRate  Counter64,
		nptPmGEPortCurrentOUTAverageRate  Counter64,
		nptPmGEPortCurrentOUTCurrentRate  Counter64,
		nptPmGEPortCurrentOUTMaximumPPS  Counter64,
		nptPmGEPortCurrentOUTAveragePPS  Counter64,
		nptPmGEPortCurrentOUTCurrentPPS  Counter64,
		nptPmGEPortCurrentOUTMaximumUtilization  Counter64,
		nptPmGEPortCurrentOUTAverageUtilization  Counter64,
		nptPmGEPortCurrentOUTCurrentUtilization  Counter64,
		nptPmGEPortCurrentLinkDownSeconds  Counter64,
		nptPmGEPortCurrentOSNRMax  DisplayString,
		nptPmGEPortCurrentOSNRMin  DisplayString,
		nptPmGEPortCurrentMaxRxPower  DisplayString,
		nptPmGEPortCurrentMinRxPower  DisplayString,
        nptPmGEPortCurrentTxPower  DisplayString
		}


	nptPmGEPortCurrentIndex	OBJECT-TYPE	
		SYNTAX			Integer32  ( -2147483648 .. 2147483647  ) 
		MAX-ACCESS		read-only
		STATUS			current
		DESCRIPTION		"Column Description"
		::=  {  nptPmGEPortCurrentEntry  1  }

		
	nptPmGEPortCurrentMoDescription	OBJECT-TYPE	
		SYNTAX			DisplayString 
		MAX-ACCESS		read-only
		STATUS			current
		DESCRIPTION		"Column Description"
		::=  {  nptPmGEPortCurrentEntry  2  }

	nptPmGEPortCurrentRxOctets	OBJECT-TYPE	
		SYNTAX			Counter64
		MAX-ACCESS		read-only
		STATUS			current
		DESCRIPTION		"Column Description"
		::=  {  nptPmGEPortCurrentEntry  3  }


	nptPmGEPortCurrentRxPkts	OBJECT-TYPE	
		SYNTAX			Counter64
		MAX-ACCESS		read-only
		STATUS			current
		DESCRIPTION		"Description"
		::=  {  nptPmGEPortCurrentEntry  4  }


	nptPmGEPortCurrentRxBroadcastPkts	OBJECT-TYPE	
		SYNTAX			Counter64
		MAX-ACCESS		read-only
		STATUS			current
		DESCRIPTION		"Description"
		::=  {  nptPmGEPortCurrentEntry  5  }


	nptPmGEPortCurrentRxMulticastPkts	OBJECT-TYPE	
		SYNTAX			Counter64
		MAX-ACCESS		read-only
		STATUS			current
		DESCRIPTION		"Description"
		::=  {  nptPmGEPortCurrentEntry  6  }


	nptPmGEPortCurrentTxOctets	OBJECT-TYPE	
		SYNTAX			Counter64
		MAX-ACCESS		read-only
		STATUS			current
		DESCRIPTION		"Description"
		::=  {  nptPmGEPortCurrentEntry  7  }


	nptPmGEPortCurrentTxPkts	OBJECT-TYPE	
		SYNTAX			Counter64
		MAX-ACCESS		read-only
		STATUS			current
		DESCRIPTION		"Description"
		::=  {  nptPmGEPortCurrentEntry  8  }


	nptPmGEPortCurrentRxErrorPkts	OBJECT-TYPE	
		SYNTAX			Counter64
		MAX-ACCESS		read-only
		STATUS			current
		DESCRIPTION		"Description"
		::=  {  nptPmGEPortCurrentEntry  9  }


	nptPmGEPortCurrentRxPkts64	OBJECT-TYPE	
		SYNTAX			Counter64
		MAX-ACCESS		read-only
		STATUS			current
		DESCRIPTION		"Description"
		::=  {  nptPmGEPortCurrentEntry  10  }


	nptPmGEPortCurrentRxPkts127	OBJECT-TYPE	
		SYNTAX			Counter64
		MAX-ACCESS		read-only
		STATUS			current
		DESCRIPTION		"Description"
		::=  {  nptPmGEPortCurrentEntry  11  }


	nptPmGEPortCurrentRxPkts255	OBJECT-TYPE	
		SYNTAX			Counter64
		MAX-ACCESS		read-only
		STATUS			current
		DESCRIPTION		"Description"
		::=  {  nptPmGEPortCurrentEntry  12  }


	nptPmGEPortCurrentRxPkts511	OBJECT-TYPE	
		SYNTAX			Counter64
		MAX-ACCESS		read-only
		STATUS			current
		DESCRIPTION		"Description"
		::=  {  nptPmGEPortCurrentEntry  13  }


	nptPmGEPortCurrentRxPkts1023	OBJECT-TYPE	
		SYNTAX			Counter64
		MAX-ACCESS		read-only
		STATUS			current
		DESCRIPTION		"Description"
		::=  {  nptPmGEPortCurrentEntry  14  }


	nptPmGEPortCurrentRxPktsMtu	OBJECT-TYPE	
		SYNTAX			Counter64
		MAX-ACCESS		read-only
		STATUS			current
		DESCRIPTION		"Description"
		::=  {  nptPmGEPortCurrentEntry  15  }


	nptPmGEPortCurrentRxUndersizePkts	OBJECT-TYPE	
		SYNTAX			Counter64
		MAX-ACCESS		read-only
		STATUS			current
		DESCRIPTION		"Description"
		::=  {  nptPmGEPortCurrentEntry  16  }


	nptPmGEPortCurrentRxOversizePkts	OBJECT-TYPE	
		SYNTAX			Counter64
		MAX-ACCESS		read-only
		STATUS			current
		DESCRIPTION		"Description"
		::=  {  nptPmGEPortCurrentEntry  17  }


	nptPmGEPortCurrentRxPausePkts	OBJECT-TYPE	
		SYNTAX			Counter64
		MAX-ACCESS		read-only
		STATUS			current
		DESCRIPTION		"Description"
		::=  {  nptPmGEPortCurrentEntry  18  }
		
	nptPmGEPortCurrentRxJabberPkts	OBJECT-TYPE	
		SYNTAX			Counter64
		MAX-ACCESS		read-only
		STATUS			current
		DESCRIPTION		"Description"
		::=  {  nptPmGEPortCurrentEntry  19  }


	nptPmGEPortCurrentRxCRCAlignErrorPkts	OBJECT-TYPE	
		SYNTAX			Counter64
		MAX-ACCESS		read-only
		STATUS			current
		DESCRIPTION		"Description"
		::=  {  nptPmGEPortCurrentEntry  20  }


	nptPmGEPortCurrentRxFragments	OBJECT-TYPE	
		SYNTAX			Counter64
		MAX-ACCESS		read-only
		STATUS			current
		DESCRIPTION		"Description"
		::=  {  nptPmGEPortCurrentEntry  21  }


	nptPmGEPortCurrentCollisionErrors	OBJECT-TYPE	
		SYNTAX			Counter64
		MAX-ACCESS		read-only
		STATUS			current
		DESCRIPTION		"Description"
		::=  {  nptPmGEPortCurrentEntry  22  }


	nptPmGEPortCurrentPCSLCV	OBJECT-TYPE	
		SYNTAX			Counter64
		MAX-ACCESS		read-only
		STATUS			current
		DESCRIPTION		"Description"
		::=  {  nptPmGEPortCurrentEntry  23  }


	nptPmGEPortCurrentPCSES	OBJECT-TYPE	
		SYNTAX			Counter64
		MAX-ACCESS		read-only
		STATUS			current
		DESCRIPTION		"Description"
		::=  {  nptPmGEPortCurrentEntry  24  }


	nptPmGEPortCurrentPCSSES	OBJECT-TYPE	
		SYNTAX			Counter64
		MAX-ACCESS		read-only
		STATUS			current
		DESCRIPTION		"Description"
		::=  {  nptPmGEPortCurrentEntry  25  }


	nptPmGEPortCurrentPCSUAS	OBJECT-TYPE	
		SYNTAX			Counter64
		MAX-ACCESS		read-only
		STATUS			current
		DESCRIPTION		"Description"
		::=  {  nptPmGEPortCurrentEntry  26  }
		
	nptPmGEPortCurrentFECCE	OBJECT-TYPE	
		SYNTAX			Counter64
		MAX-ACCESS		read-only
		STATUS			current
		DESCRIPTION		"Description"
		::=  {  nptPmGEPortCurrentEntry  27  }


	nptPmGEPortCurrentFECUCE	OBJECT-TYPE	
		SYNTAX			Counter64
		MAX-ACCESS		read-only
		STATUS			current
		DESCRIPTION		"Description"
		::=  {  nptPmGEPortCurrentEntry  28  }


	nptPmGEPortCurrentPREFECBER	OBJECT-TYPE	
		SYNTAX			Counter64
		MAX-ACCESS		read-only
		STATUS			current
		DESCRIPTION		"Description"
		::=  {  nptPmGEPortCurrentEntry  29  }


	nptPmGEPortCurrentINMaximumRate	OBJECT-TYPE	
		SYNTAX			Counter64
		MAX-ACCESS		read-only
		STATUS			current
		DESCRIPTION		"Description"
		::=  {  nptPmGEPortCurrentEntry  30  }
		
	nptPmGEPortCurrentINAverageRate	OBJECT-TYPE	
		SYNTAX			Counter64
		MAX-ACCESS		read-only
		STATUS			current
		DESCRIPTION		"Description"
		::=  {  nptPmGEPortCurrentEntry  31  }
		
	nptPmGEPortCurrentINCurrentRate	OBJECT-TYPE	
		SYNTAX			Counter64
		MAX-ACCESS		read-only
		STATUS			current
		DESCRIPTION		"Description"
		::=  {  nptPmGEPortCurrentEntry  32  }
		
	nptPmGEPortCurrentINMaximumPPS	OBJECT-TYPE	
		SYNTAX			Counter64
		MAX-ACCESS		read-only
		STATUS			current
		DESCRIPTION		"Description"
		::=  {  nptPmGEPortCurrentEntry  33  }
		
	nptPmGEPortCurrentINAveragePPS	OBJECT-TYPE	
		SYNTAX			Counter64
		MAX-ACCESS		read-only
		STATUS			current
		DESCRIPTION		"Description"
		::=  {  nptPmGEPortCurrentEntry  34  }
		
	nptPmGEPortCurrentINCurrentPPS	OBJECT-TYPE	
		SYNTAX			Counter64
		MAX-ACCESS		read-only
		STATUS			current
		DESCRIPTION		"Description"
		::=  {  nptPmGEPortCurrentEntry  35  }
		
	nptPmGEPortCurrentINMaximumUtilization	OBJECT-TYPE	
		SYNTAX			Counter64
		MAX-ACCESS		read-only
		STATUS			current
		DESCRIPTION		"Description"
		::=  {  nptPmGEPortCurrentEntry  36  }
		
	nptPmGEPortCurrentINAverageUtilization	OBJECT-TYPE	
		SYNTAX			Counter64
		MAX-ACCESS		read-only
		STATUS			current
		DESCRIPTION		"Description"
		::=  {  nptPmGEPortCurrentEntry  37  }
		
	nptPmGEPortCurrentINCurrentUtilization	OBJECT-TYPE	
		SYNTAX			Counter64
		MAX-ACCESS		read-only
		STATUS			current
		DESCRIPTION		"Description"
		::=  {  nptPmGEPortCurrentEntry  38  }
		
	nptPmGEPortCurrentOUTMaximumRate	OBJECT-TYPE	
		SYNTAX			Counter64
		MAX-ACCESS		read-only
		STATUS			current
		DESCRIPTION		"Description"
		::=  {  nptPmGEPortCurrentEntry  39  }
		
	nptPmGEPortCurrentOUTAverageRate	OBJECT-TYPE	
		SYNTAX			Counter64
		MAX-ACCESS		read-only
		STATUS			current
		DESCRIPTION		"Description"
		::=  {  nptPmGEPortCurrentEntry  40  }
		
	nptPmGEPortCurrentOUTCurrentRate	OBJECT-TYPE	
		SYNTAX			Counter64
		MAX-ACCESS		read-only
		STATUS			current
		DESCRIPTION		"Description"
		::=  {  nptPmGEPortCurrentEntry  41  }
		
	nptPmGEPortCurrentOUTMaximumPPS	OBJECT-TYPE	
		SYNTAX			Counter64
		MAX-ACCESS		read-only
		STATUS			current
		DESCRIPTION		"Description"
		::=  {  nptPmGEPortCurrentEntry  42  }
		
	nptPmGEPortCurrentOUTAveragePPS	OBJECT-TYPE	
		SYNTAX			Counter64
		MAX-ACCESS		read-only
		STATUS			current
		DESCRIPTION		"Description"
		::=  {  nptPmGEPortCurrentEntry  43  }
		
	nptPmGEPortCurrentOUTCurrentPPS	OBJECT-TYPE	
		SYNTAX			Counter64
		MAX-ACCESS		read-only
		STATUS			current
		DESCRIPTION		"Description"
		::=  {  nptPmGEPortCurrentEntry  44  }
		
	nptPmGEPortCurrentOUTMaximumUtilization	OBJECT-TYPE	
		SYNTAX			Counter64
		MAX-ACCESS		read-only
		STATUS			current
		DESCRIPTION		"Description"
		::=  {  nptPmGEPortCurrentEntry  45  }
		
	nptPmGEPortCurrentOUTAverageUtilization	OBJECT-TYPE	
		SYNTAX			Counter64
		MAX-ACCESS		read-only
		STATUS			current
		DESCRIPTION		"Description"
		::=  {  nptPmGEPortCurrentEntry  46  }
		
	nptPmGEPortCurrentOUTCurrentUtilization	OBJECT-TYPE	
		SYNTAX			Counter64
		MAX-ACCESS		read-only
		STATUS			current
		DESCRIPTION		"Description"
		::=  {  nptPmGEPortCurrentEntry  47  }
		
	nptPmGEPortCurrentLinkDownSeconds	OBJECT-TYPE	
		SYNTAX			Counter64
		MAX-ACCESS		read-only
		STATUS			current
		DESCRIPTION		"Description"
		::=  {  nptPmGEPortCurrentEntry  48  }
		
	nptPmGEPortCurrentOSNRMax	OBJECT-TYPE	
		SYNTAX			DisplayString
		MAX-ACCESS		read-only
		STATUS			current
		DESCRIPTION		"Description"
		::=  {  nptPmGEPortCurrentEntry  49  }
		
	nptPmGEPortCurrentOSNRMin	OBJECT-TYPE	
		SYNTAX			DisplayString
		MAX-ACCESS		read-only
		STATUS			current
		DESCRIPTION		"Description"
		::=  {  nptPmGEPortCurrentEntry  50  }
               
	nptPmGEPortCurrentMaxRxPower	OBJECT-TYPE	
		SYNTAX			DisplayString
		MAX-ACCESS		read-only
		STATUS			current
		DESCRIPTION		"Description"
		::=  {  nptPmGEPortCurrentEntry  51  }
		
	nptPmGEPortCurrentMinRxPower	OBJECT-TYPE	
		SYNTAX			DisplayString
		MAX-ACCESS		read-only
		STATUS			current
		DESCRIPTION		"Description"
		::=  {  nptPmGEPortCurrentEntry  52  }
        
	nptPmGEPortCurrentTxPower	OBJECT-TYPE	
		SYNTAX			DisplayString
		MAX-ACCESS		read-only
		STATUS			current
		DESCRIPTION		"Description"
		::=  {  nptPmGEPortCurrentEntry  53  }	
        
	nptPmGEPortTotalTable	OBJECT-TYPE
		SYNTAX		SEQUENCE  OF  NptPmGEPortTotalEntry
		MAX-ACCESS	not-accessible
		STATUS		current
		DESCRIPTION	"Description"
		::=  { nptPmGEPort  2 }

	nptPmGEPortTotalEntry	OBJECT-TYPE
		SYNTAX		NptPmGEPortTotalEntry
		MAX-ACCESS	not-accessible
		STATUS		current
		DESCRIPTION	"Row Description"
		INDEX		{  nptPmGEPortTotalIndex  }
		::=  { nptPmGEPortTotalTable 1 }

	NptPmGEPortTotalEntry  ::=  SEQUENCE {
	    nptPmGEPortTotalIndex  Integer32,
		nptPmGEPortTotalMoDescription  DisplayString,
	    nptPmGEPortTotalRxOctets  Counter64,
		nptPmGEPortTotalRxPkts  Counter64,
		nptPmGEPortTotalRxBroadcastPkts  Counter64,
		nptPmGEPortTotalRxMulticastPkts  Counter64,
		nptPmGEPortTotalTxOctets  Counter64,
		nptPmGEPortTotalTxPkts  Counter64,
		nptPmGEPortTotalRxErrorPkts  Counter64,
		nptPmGEPortTotalRxPkts64  Counter64,
		nptPmGEPortTotalRxPkts127  Counter64,
		nptPmGEPortTotalRxPkts255  Counter64,
		nptPmGEPortTotalRxPkts511  Counter64,
		nptPmGEPortTotalRxPkts1023  Counter64,
		nptPmGEPortTotalRxPktsMtu  Counter64,
		nptPmGEPortTotalRxUndersizePkts  Counter64,
		nptPmGEPortTotalRxOversizePkts  Counter64,
		nptPmGEPortTotalRxPausePkts  Counter64,
		nptPmGEPortTotalRxJabberPkts  Counter64,
		nptPmGEPortTotalRxCRCAlignErrorPkts  Counter64,
		nptPmGEPortTotalRxFragments  Counter64,
		nptPmGEPortTotalCollisionErrors  Counter64,
		nptPmGEPortTotalPCSLCV  Counter64,
		nptPmGEPortTotalPCSES  Counter64,
		nptPmGEPortTotalPCSSES  Counter64,
		nptPmGEPortTotalPCSUAS  Counter64,
		nptPmGEPortTotalFECCE  Counter64,
		nptPmGEPortTotalFECUCE  Counter64,
		nptPmGEPortTotalPREFECBER  Counter64,
		nptPmGEPortTotalINMaximumRate  Counter64,
		nptPmGEPortTotalINAverageRate  Counter64,
		nptPmGEPortTotalINTotalRate  Counter64,
		nptPmGEPortTotalINMaximumPPS  Counter64,
		nptPmGEPortTotalINAveragePPS  Counter64,
		nptPmGEPortTotalINTotalPPS  Counter64,
		nptPmGEPortTotalINMaximumUtilization  Counter64,
		nptPmGEPortTotalINAverageUtilization  Counter64,
		nptPmGEPortTotalINTotalUtilization  Counter64,
		nptPmGEPortTotalOUTMaximumRate  Counter64,
		nptPmGEPortTotalOUTAverageRate  Counter64,
		nptPmGEPortTotalOUTTotalRate  Counter64,
		nptPmGEPortTotalOUTMaximumPPS  Counter64,
		nptPmGEPortTotalOUTAveragePPS  Counter64,
		nptPmGEPortTotalOUTTotalPPS  Counter64,
		nptPmGEPortTotalOUTMaximumUtilization  Counter64,
		nptPmGEPortTotalOUTAverageUtilization  Counter64,
		nptPmGEPortTotalOUTTotalUtilization  Counter64,
		nptPmGEPortTotalLinkDownSeconds  Counter64,
		nptPmGEPortTotalOSNRMax  DisplayString,
		nptPmGEPortTotalOSNRMin  DisplayString,
		nptPmGEPortTotalMaxRxPower  DisplayString,
		nptPmGEPortTotalMinRxPower  DisplayString,
        nptPmGEPortTotalTxPower  DisplayString
		}


	nptPmGEPortTotalIndex	OBJECT-TYPE	
		SYNTAX			Integer32  ( -2147483648 .. 2147483647  ) 
		MAX-ACCESS		read-only
		STATUS			current
		DESCRIPTION		"Column Description"
		::=  {  nptPmGEPortTotalEntry  1  }
		
	nptPmGEPortTotalMoDescription	OBJECT-TYPE	
		SYNTAX			DisplayString 
		MAX-ACCESS		read-only
		STATUS			current
		DESCRIPTION		"Column Description"
		::=  {  nptPmGEPortTotalEntry  2  }


	nptPmGEPortTotalRxOctets	OBJECT-TYPE	
		SYNTAX			Counter64
		MAX-ACCESS		read-only
		STATUS			current
		DESCRIPTION		"Column Description"
		::=  {  nptPmGEPortTotalEntry  3  }


	nptPmGEPortTotalRxPkts	OBJECT-TYPE	
		SYNTAX			Counter64
		MAX-ACCESS		read-only
		STATUS			current
		DESCRIPTION		"Description"
		::=  {  nptPmGEPortTotalEntry  4  }


	nptPmGEPortTotalRxBroadcastPkts	OBJECT-TYPE	
		SYNTAX			Counter64
		MAX-ACCESS		read-only
		STATUS			current
		DESCRIPTION		"Description"
		::=  {  nptPmGEPortTotalEntry  5  }


	nptPmGEPortTotalRxMulticastPkts	OBJECT-TYPE	
		SYNTAX			Counter64
		MAX-ACCESS		read-only
		STATUS			current
		DESCRIPTION		"Description"
		::=  {  nptPmGEPortTotalEntry  6  }


	nptPmGEPortTotalTxOctets	OBJECT-TYPE	
		SYNTAX			Counter64
		MAX-ACCESS		read-only
		STATUS			current
		DESCRIPTION		"Description"
		::=  {  nptPmGEPortTotalEntry  7  }


	nptPmGEPortTotalTxPkts	OBJECT-TYPE	
		SYNTAX			Counter64
		MAX-ACCESS		read-only
		STATUS			current
		DESCRIPTION		"Description"
		::=  {  nptPmGEPortTotalEntry  8  }


	nptPmGEPortTotalRxErrorPkts	OBJECT-TYPE	
		SYNTAX			Counter64
		MAX-ACCESS		read-only
		STATUS			current
		DESCRIPTION		"Description"
		::=  {  nptPmGEPortTotalEntry  9  }


	nptPmGEPortTotalRxPkts64	OBJECT-TYPE	
		SYNTAX			Counter64
		MAX-ACCESS		read-only
		STATUS			current
		DESCRIPTION		"Description"
		::=  {  nptPmGEPortTotalEntry  10  }


	nptPmGEPortTotalRxPkts127	OBJECT-TYPE	
		SYNTAX			Counter64
		MAX-ACCESS		read-only
		STATUS			current
		DESCRIPTION		"Description"
		::=  {  nptPmGEPortTotalEntry  11  }


	nptPmGEPortTotalRxPkts255	OBJECT-TYPE	
		SYNTAX			Counter64
		MAX-ACCESS		read-only
		STATUS			current
		DESCRIPTION		"Description"
		::=  {  nptPmGEPortTotalEntry  12  }


	nptPmGEPortTotalRxPkts511	OBJECT-TYPE	
		SYNTAX			Counter64
		MAX-ACCESS		read-only
		STATUS			current
		DESCRIPTION		"Description"
		::=  {  nptPmGEPortTotalEntry  13  }


	nptPmGEPortTotalRxPkts1023	OBJECT-TYPE	
		SYNTAX			Counter64
		MAX-ACCESS		read-only
		STATUS			current
		DESCRIPTION		"Description"
		::=  {  nptPmGEPortTotalEntry  14  }


	nptPmGEPortTotalRxPktsMtu	OBJECT-TYPE	
		SYNTAX			Counter64
		MAX-ACCESS		read-only
		STATUS			current
		DESCRIPTION		"Description"
		::=  {  nptPmGEPortTotalEntry  15  }


	nptPmGEPortTotalRxUndersizePkts	OBJECT-TYPE	
		SYNTAX			Counter64
		MAX-ACCESS		read-only
		STATUS			current
		DESCRIPTION		"Description"
		::=  {  nptPmGEPortTotalEntry  16  }


	nptPmGEPortTotalRxOversizePkts	OBJECT-TYPE	
		SYNTAX			Counter64
		MAX-ACCESS		read-only
		STATUS			current
		DESCRIPTION		"Description"
		::=  {  nptPmGEPortTotalEntry  17  }


	nptPmGEPortTotalRxPausePkts	OBJECT-TYPE	
		SYNTAX			Counter64
		MAX-ACCESS		read-only
		STATUS			current
		DESCRIPTION		"Description"
		::=  {  nptPmGEPortTotalEntry  18  }
		
	nptPmGEPortTotalRxJabberPkts	OBJECT-TYPE	
		SYNTAX			Counter64
		MAX-ACCESS		read-only
		STATUS			current
		DESCRIPTION		"Description"
		::=  {  nptPmGEPortTotalEntry  19  }


	nptPmGEPortTotalRxCRCAlignErrorPkts	OBJECT-TYPE	
		SYNTAX			Counter64
		MAX-ACCESS		read-only
		STATUS			current
		DESCRIPTION		"Description"
		::=  {  nptPmGEPortTotalEntry  20  }


	nptPmGEPortTotalRxFragments	OBJECT-TYPE	
		SYNTAX			Counter64
		MAX-ACCESS		read-only
		STATUS			current
		DESCRIPTION		"Description"
		::=  {  nptPmGEPortTotalEntry  21  }


	nptPmGEPortTotalCollisionErrors	OBJECT-TYPE	
		SYNTAX			Counter64
		MAX-ACCESS		read-only
		STATUS			current
		DESCRIPTION		"Description"
		::=  {  nptPmGEPortTotalEntry  22  }


	nptPmGEPortTotalPCSLCV	OBJECT-TYPE	
		SYNTAX			Counter64
		MAX-ACCESS		read-only
		STATUS			current
		DESCRIPTION		"Description"
		::=  {  nptPmGEPortTotalEntry  23  }


	nptPmGEPortTotalPCSES	OBJECT-TYPE	
		SYNTAX			Counter64
		MAX-ACCESS		read-only
		STATUS			current
		DESCRIPTION		"Description"
		::=  {  nptPmGEPortTotalEntry  24  }


	nptPmGEPortTotalPCSSES	OBJECT-TYPE	
		SYNTAX			Counter64
		MAX-ACCESS		read-only
		STATUS			current
		DESCRIPTION		"Description"
		::=  {  nptPmGEPortTotalEntry  25  }


	nptPmGEPortTotalPCSUAS	OBJECT-TYPE	
		SYNTAX			Counter64
		MAX-ACCESS		read-only
		STATUS			current
		DESCRIPTION		"Description"
		::=  {  nptPmGEPortTotalEntry  26  }
		
	nptPmGEPortTotalFECCE	OBJECT-TYPE	
		SYNTAX			Counter64
		MAX-ACCESS		read-only
		STATUS			current
		DESCRIPTION		"Description"
		::=  {  nptPmGEPortTotalEntry  27  }


	nptPmGEPortTotalFECUCE	OBJECT-TYPE	
		SYNTAX			Counter64
		MAX-ACCESS		read-only
		STATUS			current
		DESCRIPTION		"Description"
		::=  {  nptPmGEPortTotalEntry  28  }


	nptPmGEPortTotalPREFECBER	OBJECT-TYPE	
		SYNTAX			Counter64
		MAX-ACCESS		read-only
		STATUS			current
		DESCRIPTION		"Description"
		::=  {  nptPmGEPortTotalEntry  29  }


	nptPmGEPortTotalINMaximumRate	OBJECT-TYPE	
		SYNTAX			Counter64
		MAX-ACCESS		read-only
		STATUS			current
		DESCRIPTION		"Description"
		::=  {  nptPmGEPortTotalEntry  30  }
		
	nptPmGEPortTotalINAverageRate	OBJECT-TYPE	
		SYNTAX			Counter64
		MAX-ACCESS		read-only
		STATUS			current
		DESCRIPTION		"Description"
		::=  {  nptPmGEPortTotalEntry  31  }
		
	nptPmGEPortTotalINTotalRate	OBJECT-TYPE	
		SYNTAX			Counter64
		MAX-ACCESS		read-only
		STATUS			current
		DESCRIPTION		"Description"
		::=  {  nptPmGEPortTotalEntry  32  }
		
	nptPmGEPortTotalINMaximumPPS	OBJECT-TYPE	
		SYNTAX			Counter64
		MAX-ACCESS		read-only
		STATUS			current
		DESCRIPTION		"Description"
		::=  {  nptPmGEPortTotalEntry  33  }
		
	nptPmGEPortTotalINAveragePPS	OBJECT-TYPE	
		SYNTAX			Counter64
		MAX-ACCESS		read-only
		STATUS			current
		DESCRIPTION		"Description"
		::=  {  nptPmGEPortTotalEntry  34  }
		
	nptPmGEPortTotalINTotalPPS	OBJECT-TYPE	
		SYNTAX			Counter64
		MAX-ACCESS		read-only
		STATUS			current
		DESCRIPTION		"Description"
		::=  {  nptPmGEPortTotalEntry  35  }
		
	nptPmGEPortTotalINMaximumUtilization	OBJECT-TYPE	
		SYNTAX			Counter64
		MAX-ACCESS		read-only
		STATUS			current
		DESCRIPTION		"Description"
		::=  {  nptPmGEPortTotalEntry  36  }
		
	nptPmGEPortTotalINAverageUtilization	OBJECT-TYPE	
		SYNTAX			Counter64
		MAX-ACCESS		read-only
		STATUS			current
		DESCRIPTION		"Description"
		::=  {  nptPmGEPortTotalEntry  37  }
		
	nptPmGEPortTotalINTotalUtilization	OBJECT-TYPE	
		SYNTAX			Counter64
		MAX-ACCESS		read-only
		STATUS			current
		DESCRIPTION		"Description"
		::=  {  nptPmGEPortTotalEntry  38  }
		
	nptPmGEPortTotalOUTMaximumRate	OBJECT-TYPE	
		SYNTAX			Counter64
		MAX-ACCESS		read-only
		STATUS			current
		DESCRIPTION		"Description"
		::=  {  nptPmGEPortTotalEntry  39  }
		
	nptPmGEPortTotalOUTAverageRate	OBJECT-TYPE	
		SYNTAX			Counter64
		MAX-ACCESS		read-only
		STATUS			current
		DESCRIPTION		"Description"
		::=  {  nptPmGEPortTotalEntry  40  }
		
	nptPmGEPortTotalOUTTotalRate	OBJECT-TYPE	
		SYNTAX			Counter64
		MAX-ACCESS		read-only
		STATUS			current
		DESCRIPTION		"Description"
		::=  {  nptPmGEPortTotalEntry  41  }
		
	nptPmGEPortTotalOUTMaximumPPS	OBJECT-TYPE	
		SYNTAX			Counter64
		MAX-ACCESS		read-only
		STATUS			current
		DESCRIPTION		"Description"
		::=  {  nptPmGEPortTotalEntry  42  }
		
	nptPmGEPortTotalOUTAveragePPS	OBJECT-TYPE	
		SYNTAX			Counter64
		MAX-ACCESS		read-only
		STATUS			current
		DESCRIPTION		"Description"
		::=  {  nptPmGEPortTotalEntry  43  }
		
	nptPmGEPortTotalOUTTotalPPS	OBJECT-TYPE	
		SYNTAX			Counter64
		MAX-ACCESS		read-only
		STATUS			current
		DESCRIPTION		"Description"
		::=  {  nptPmGEPortTotalEntry  44  }
		
	nptPmGEPortTotalOUTMaximumUtilization	OBJECT-TYPE	
		SYNTAX			Counter64
		MAX-ACCESS		read-only
		STATUS			current
		DESCRIPTION		"Description"
		::=  {  nptPmGEPortTotalEntry  45  }
		
	nptPmGEPortTotalOUTAverageUtilization	OBJECT-TYPE	
		SYNTAX			Counter64
		MAX-ACCESS		read-only
		STATUS			current
		DESCRIPTION		"Description"
		::=  {  nptPmGEPortTotalEntry  46  }
		
	nptPmGEPortTotalOUTTotalUtilization	OBJECT-TYPE	
		SYNTAX			Counter64
		MAX-ACCESS		read-only
		STATUS			current
		DESCRIPTION		"Description"
		::=  {  nptPmGEPortTotalEntry  47  }
		
	nptPmGEPortTotalLinkDownSeconds	OBJECT-TYPE	
		SYNTAX			Counter64
		MAX-ACCESS		read-only
		STATUS			current
		DESCRIPTION		"Description"
		::=  {  nptPmGEPortTotalEntry  48  }
		
	nptPmGEPortTotalOSNRMax	OBJECT-TYPE	
		SYNTAX			DisplayString
		MAX-ACCESS		read-only
		STATUS			current
		DESCRIPTION		"Description"
		::=  {  nptPmGEPortTotalEntry  49  }
		
	nptPmGEPortTotalOSNRMin	OBJECT-TYPE	
		SYNTAX			DisplayString
		MAX-ACCESS		read-only
		STATUS			current
		DESCRIPTION		"Description"
		::=  {  nptPmGEPortTotalEntry  50  }
               
	nptPmGEPortTotalMaxRxPower	OBJECT-TYPE	
		SYNTAX			DisplayString
		MAX-ACCESS		read-only
		STATUS			current
		DESCRIPTION		"Description"
		::=  {  nptPmGEPortTotalEntry  51  }
		
	nptPmGEPortTotalMinRxPower	OBJECT-TYPE	
		SYNTAX			DisplayString
		MAX-ACCESS		read-only
		STATUS			current
		DESCRIPTION		"Description"
		::=  {  nptPmGEPortTotalEntry  52  }
        
	nptPmGEPortTotalTxPower	OBJECT-TYPE	
		SYNTAX			DisplayString
		MAX-ACCESS		read-only
		STATUS			current
		DESCRIPTION		"Description"
		::=  {  nptPmGEPortTotalEntry  53  }	
		
	nptPmCEPortCurrentTable	OBJECT-TYPE
		SYNTAX		SEQUENCE  OF  NptPmCEPortCurrentEntry
		MAX-ACCESS	not-accessible
		STATUS		current
		DESCRIPTION	"Description"
		::=  { nptPmCEPort  1 }

	nptPmCEPortCurrentEntry	OBJECT-TYPE
		SYNTAX		NptPmCEPortCurrentEntry
		MAX-ACCESS	not-accessible
		STATUS		current
		DESCRIPTION	"Row Description"
		INDEX		{  nptPmCEPortCurrentIndex  }
		::=  { nptPmCEPortCurrentTable 1 }

	NptPmCEPortCurrentEntry  ::=  SEQUENCE {
	    nptPmCEPortCurrentIndex  Integer32,
		nptPmCEPortCurrentMoDescription  DisplayString,
	    nptPmCEPortCurrentRxOctets  Counter64,
		nptPmCEPortCurrentRxPkts  Counter64,
		nptPmCEPortCurrentRxBroadcastPkts  Counter64,
		nptPmCEPortCurrentRxMulticastPkts  Counter64,
		nptPmCEPortCurrentTxOctets  Counter64,
		nptPmCEPortCurrentTxPkts  Counter64,
		nptPmCEPortCurrentRxErrorPkts  Counter64,
		nptPmCEPortCurrentRxPkts64  Counter64,
		nptPmCEPortCurrentRxPkts127  Counter64,
		nptPmCEPortCurrentRxPkts255  Counter64,
		nptPmCEPortCurrentRxPkts511  Counter64,
		nptPmCEPortCurrentRxPkts1023  Counter64,
		nptPmCEPortCurrentRxPktsMtu  Counter64,
		nptPmCEPortCurrentRxUndersizePkts  Counter64,
		nptPmCEPortCurrentRxOversizePkts  Counter64,
		nptPmCEPortCurrentRxPausePkts  Counter64,
		nptPmCEPortCurrentRxJabberPkts  Counter64,
		nptPmCEPortCurrentRxCRCAlignErrorPkts  Counter64,
		nptPmCEPortCurrentRxFragments  Counter64,
		nptPmCEPortCurrentCollisionErrors  Counter64,
		nptPmCEPortCurrentPCSLCV  Counter64,
		nptPmCEPortCurrentPCSES  Counter64,
		nptPmCEPortCurrentPCSSES  Counter64,
		nptPmCEPortCurrentPCSUAS  Counter64,
		nptPmCEPortCurrentFECCE  Counter64,
		nptPmCEPortCurrentFECUCE  Counter64,
		nptPmCEPortCurrentPREFECBER  Counter64,
		nptPmCEPortCurrentINMaximumRate  Counter64,
		nptPmCEPortCurrentINAverageRate  Counter64,
		nptPmCEPortCurrentINCurrentRate  Counter64,
		nptPmCEPortCurrentINMaximumPPS  Counter64,
		nptPmCEPortCurrentINAveragePPS  Counter64,
		nptPmCEPortCurrentINCurrentPPS  Counter64,
		nptPmCEPortCurrentINMaximumUtilization  Counter64,
		nptPmCEPortCurrentINAverageUtilization  Counter64,
		nptPmCEPortCurrentINCurrentUtilization  Counter64,
		nptPmCEPortCurrentOUTMaximumRate  Counter64,
		nptPmCEPortCurrentOUTAverageRate  Counter64,
		nptPmCEPortCurrentOUTCurrentRate  Counter64,
		nptPmCEPortCurrentOUTMaximumPPS  Counter64,
		nptPmCEPortCurrentOUTAveragePPS  Counter64,
		nptPmCEPortCurrentOUTCurrentPPS  Counter64,
		nptPmCEPortCurrentOUTMaximumUtilization  Counter64,
		nptPmCEPortCurrentOUTAverageUtilization  Counter64,
		nptPmCEPortCurrentOUTCurrentUtilization  Counter64,
		nptPmCEPortCurrentLinkDownSeconds  Counter64,
		nptPmCEPortCurrentOSNRMax  DisplayString,
		nptPmCEPortCurrentOSNRMin  DisplayString,
		nptPmCEPortCurrentMaxRxPower  DisplayString,
		nptPmCEPortCurrentMinRxPower  DisplayString,
        nptPmCEPortCurrentTxPower  DisplayString
		}


	nptPmCEPortCurrentIndex	OBJECT-TYPE	
		SYNTAX			Integer32  ( -2147483648 .. 2147483647  ) 
		MAX-ACCESS		read-only
		STATUS			current
		DESCRIPTION		"Column Description"
		::=  {  nptPmCEPortCurrentEntry  1  }
		
	nptPmCEPortCurrentMoDescription	OBJECT-TYPE	
		SYNTAX			DisplayString 
		MAX-ACCESS		read-only
		STATUS			current
		DESCRIPTION		"Column Description"
		::=  {  nptPmCEPortCurrentEntry  2  }


	nptPmCEPortCurrentRxOctets	OBJECT-TYPE	
		SYNTAX			Counter64
		MAX-ACCESS		read-only
		STATUS			current
		DESCRIPTION		"Column Description"
		::=  {  nptPmCEPortCurrentEntry  3  }


	nptPmCEPortCurrentRxPkts	OBJECT-TYPE	
		SYNTAX			Counter64
		MAX-ACCESS		read-only
		STATUS			current
		DESCRIPTION		"Description"
		::=  {  nptPmCEPortCurrentEntry  4  }


	nptPmCEPortCurrentRxBroadcastPkts	OBJECT-TYPE	
		SYNTAX			Counter64
		MAX-ACCESS		read-only
		STATUS			current
		DESCRIPTION		"Description"
		::=  {  nptPmCEPortCurrentEntry  5  }


	nptPmCEPortCurrentRxMulticastPkts	OBJECT-TYPE	
		SYNTAX			Counter64
		MAX-ACCESS		read-only
		STATUS			current
		DESCRIPTION		"Description"
		::=  {  nptPmCEPortCurrentEntry  6  }


	nptPmCEPortCurrentTxOctets	OBJECT-TYPE	
		SYNTAX			Counter64
		MAX-ACCESS		read-only
		STATUS			current
		DESCRIPTION		"Description"
		::=  {  nptPmCEPortCurrentEntry  7  }


	nptPmCEPortCurrentTxPkts	OBJECT-TYPE	
		SYNTAX			Counter64
		MAX-ACCESS		read-only
		STATUS			current
		DESCRIPTION		"Description"
		::=  {  nptPmCEPortCurrentEntry  8  }


	nptPmCEPortCurrentRxErrorPkts	OBJECT-TYPE	
		SYNTAX			Counter64
		MAX-ACCESS		read-only
		STATUS			current
		DESCRIPTION		"Description"
		::=  {  nptPmCEPortCurrentEntry  9  }


	nptPmCEPortCurrentRxPkts64	OBJECT-TYPE	
		SYNTAX			Counter64
		MAX-ACCESS		read-only
		STATUS			current
		DESCRIPTION		"Description"
		::=  {  nptPmCEPortCurrentEntry  10  }


	nptPmCEPortCurrentRxPkts127	OBJECT-TYPE	
		SYNTAX			Counter64
		MAX-ACCESS		read-only
		STATUS			current
		DESCRIPTION		"Description"
		::=  {  nptPmCEPortCurrentEntry  11  }


	nptPmCEPortCurrentRxPkts255	OBJECT-TYPE	
		SYNTAX			Counter64
		MAX-ACCESS		read-only
		STATUS			current
		DESCRIPTION		"Description"
		::=  {  nptPmCEPortCurrentEntry  12  }


	nptPmCEPortCurrentRxPkts511	OBJECT-TYPE	
		SYNTAX			Counter64
		MAX-ACCESS		read-only
		STATUS			current
		DESCRIPTION		"Description"
		::=  {  nptPmCEPortCurrentEntry  13  }


	nptPmCEPortCurrentRxPkts1023	OBJECT-TYPE	
		SYNTAX			Counter64
		MAX-ACCESS		read-only
		STATUS			current
		DESCRIPTION		"Description"
		::=  {  nptPmCEPortCurrentEntry  14  }


	nptPmCEPortCurrentRxPktsMtu	OBJECT-TYPE	
		SYNTAX			Counter64
		MAX-ACCESS		read-only
		STATUS			current
		DESCRIPTION		"Description"
		::=  {  nptPmCEPortCurrentEntry  15  }


	nptPmCEPortCurrentRxUndersizePkts	OBJECT-TYPE	
		SYNTAX			Counter64
		MAX-ACCESS		read-only
		STATUS			current
		DESCRIPTION		"Description"
		::=  {  nptPmCEPortCurrentEntry  16  }


	nptPmCEPortCurrentRxOversizePkts	OBJECT-TYPE	
		SYNTAX			Counter64
		MAX-ACCESS		read-only
		STATUS			current
		DESCRIPTION		"Description"
		::=  {  nptPmCEPortCurrentEntry  17  }


	nptPmCEPortCurrentRxPausePkts	OBJECT-TYPE	
		SYNTAX			Counter64
		MAX-ACCESS		read-only
		STATUS			current
		DESCRIPTION		"Description"
		::=  {  nptPmCEPortCurrentEntry  18  }
		
	nptPmCEPortCurrentRxJabberPkts	OBJECT-TYPE	
		SYNTAX			Counter64
		MAX-ACCESS		read-only
		STATUS			current
		DESCRIPTION		"Description"
		::=  {  nptPmCEPortCurrentEntry  19  }


	nptPmCEPortCurrentRxCRCAlignErrorPkts	OBJECT-TYPE	
		SYNTAX			Counter64
		MAX-ACCESS		read-only
		STATUS			current
		DESCRIPTION		"Description"
		::=  {  nptPmCEPortCurrentEntry  20  }


	nptPmCEPortCurrentRxFragments	OBJECT-TYPE	
		SYNTAX			Counter64
		MAX-ACCESS		read-only
		STATUS			current
		DESCRIPTION		"Description"
		::=  {  nptPmCEPortCurrentEntry  21  }


	nptPmCEPortCurrentCollisionErrors	OBJECT-TYPE	
		SYNTAX			Counter64
		MAX-ACCESS		read-only
		STATUS			current
		DESCRIPTION		"Description"
		::=  {  nptPmCEPortCurrentEntry  22  }


	nptPmCEPortCurrentPCSLCV	OBJECT-TYPE	
		SYNTAX			Counter64
		MAX-ACCESS		read-only
		STATUS			current
		DESCRIPTION		"Description"
		::=  {  nptPmCEPortCurrentEntry  23  }
		


	nptPmCEPortCurrentPCSES	OBJECT-TYPE	
		SYNTAX			Counter64
		MAX-ACCESS		read-only
		STATUS			current
		DESCRIPTION		"Description"
		::=  {  nptPmCEPortCurrentEntry  24  }


	nptPmCEPortCurrentPCSSES	OBJECT-TYPE	
		SYNTAX			Counter64
		MAX-ACCESS		read-only
		STATUS			current
		DESCRIPTION		"Description"
		::=  {  nptPmCEPortCurrentEntry  25  }


	nptPmCEPortCurrentPCSUAS	OBJECT-TYPE	
		SYNTAX			Counter64
		MAX-ACCESS		read-only
		STATUS			current
		DESCRIPTION		"Description"
		::=  {  nptPmCEPortCurrentEntry  26  }
		
	nptPmCEPortCurrentFECCE	OBJECT-TYPE	
		SYNTAX			Counter64
		MAX-ACCESS		read-only
		STATUS			current
		DESCRIPTION		"Description"
		::=  {  nptPmCEPortCurrentEntry  27  }


	nptPmCEPortCurrentFECUCE	OBJECT-TYPE	
		SYNTAX			Counter64
		MAX-ACCESS		read-only
		STATUS			current
		DESCRIPTION		"Description"
		::=  {  nptPmCEPortCurrentEntry  28  }


	nptPmCEPortCurrentPREFECBER	OBJECT-TYPE	
		SYNTAX			Counter64
		MAX-ACCESS		read-only
		STATUS			current
		DESCRIPTION		"Description"
		::=  {  nptPmCEPortCurrentEntry  29  }


	nptPmCEPortCurrentINMaximumRate	OBJECT-TYPE	
		SYNTAX			Counter64
		MAX-ACCESS		read-only
		STATUS			current
		DESCRIPTION		"Description"
		::=  {  nptPmCEPortCurrentEntry  30  }
		
	nptPmCEPortCurrentINAverageRate	OBJECT-TYPE	
		SYNTAX			Counter64
		MAX-ACCESS		read-only
		STATUS			current
		DESCRIPTION		"Description"
		::=  {  nptPmCEPortCurrentEntry  31  }
		
	nptPmCEPortCurrentINCurrentRate	OBJECT-TYPE	
		SYNTAX			Counter64
		MAX-ACCESS		read-only
		STATUS			current
		DESCRIPTION		"Description"
		::=  {  nptPmCEPortCurrentEntry  32  }
		
	nptPmCEPortCurrentINMaximumPPS	OBJECT-TYPE	
		SYNTAX			Counter64
		MAX-ACCESS		read-only
		STATUS			current
		DESCRIPTION		"Description"
		::=  {  nptPmCEPortCurrentEntry  33  }
		
	nptPmCEPortCurrentINAveragePPS	OBJECT-TYPE	
		SYNTAX			Counter64
		MAX-ACCESS		read-only
		STATUS			current
		DESCRIPTION		"Description"
		::=  {  nptPmCEPortCurrentEntry  34  }
		
	nptPmCEPortCurrentINCurrentPPS	OBJECT-TYPE	
		SYNTAX			Counter64
		MAX-ACCESS		read-only
		STATUS			current
		DESCRIPTION		"Description"
		::=  {  nptPmCEPortCurrentEntry  35  }
		
	nptPmCEPortCurrentINMaximumUtilization	OBJECT-TYPE	
		SYNTAX			Counter64
		MAX-ACCESS		read-only
		STATUS			current
		DESCRIPTION		"Description"
		::=  {  nptPmCEPortCurrentEntry  36  }
		
	nptPmCEPortCurrentINAverageUtilization	OBJECT-TYPE	
		SYNTAX			Counter64
		MAX-ACCESS		read-only
		STATUS			current
		DESCRIPTION		"Description"
		::=  {  nptPmCEPortCurrentEntry  37  }
		
	nptPmCEPortCurrentINCurrentUtilization	OBJECT-TYPE	
		SYNTAX			Counter64
		MAX-ACCESS		read-only
		STATUS			current
		DESCRIPTION		"Description"
		::=  {  nptPmCEPortCurrentEntry  38  }
		
	nptPmCEPortCurrentOUTMaximumRate	OBJECT-TYPE	
		SYNTAX			Counter64
		MAX-ACCESS		read-only
		STATUS			current
		DESCRIPTION		"Description"
		::=  {  nptPmCEPortCurrentEntry  39  }
		
	nptPmCEPortCurrentOUTAverageRate	OBJECT-TYPE	
		SYNTAX			Counter64
		MAX-ACCESS		read-only
		STATUS			current
		DESCRIPTION		"Description"
		::=  {  nptPmCEPortCurrentEntry  40  }
		
	nptPmCEPortCurrentOUTCurrentRate	OBJECT-TYPE	
		SYNTAX			Counter64
		MAX-ACCESS		read-only
		STATUS			current
		DESCRIPTION		"Description"
		::=  {  nptPmCEPortCurrentEntry  41  }
		
	nptPmCEPortCurrentOUTMaximumPPS	OBJECT-TYPE	
		SYNTAX			Counter64
		MAX-ACCESS		read-only
		STATUS			current
		DESCRIPTION		"Description"
		::=  {  nptPmCEPortCurrentEntry  42  }
		
	nptPmCEPortCurrentOUTAveragePPS	OBJECT-TYPE	
		SYNTAX			Counter64
		MAX-ACCESS		read-only
		STATUS			current
		DESCRIPTION		"Description"
		::=  {  nptPmCEPortCurrentEntry  43  }
		
	nptPmCEPortCurrentOUTCurrentPPS	OBJECT-TYPE	
		SYNTAX			Counter64
		MAX-ACCESS		read-only
		STATUS			current
		DESCRIPTION		"Description"
		::=  {  nptPmCEPortCurrentEntry  44  }
		
	nptPmCEPortCurrentOUTMaximumUtilization	OBJECT-TYPE	
		SYNTAX			Counter64
		MAX-ACCESS		read-only
		STATUS			current
		DESCRIPTION		"Description"
		::=  {  nptPmCEPortCurrentEntry  45  }
		
	nptPmCEPortCurrentOUTAverageUtilization	OBJECT-TYPE	
		SYNTAX			Counter64
		MAX-ACCESS		read-only
		STATUS			current
		DESCRIPTION		"Description"
		::=  {  nptPmCEPortCurrentEntry  46  }
		
	nptPmCEPortCurrentOUTCurrentUtilization	OBJECT-TYPE	
		SYNTAX			Counter64
		MAX-ACCESS		read-only
		STATUS			current
		DESCRIPTION		"Description"
		::=  {  nptPmCEPortCurrentEntry  47  }
		
	nptPmCEPortCurrentLinkDownSeconds	OBJECT-TYPE	
		SYNTAX			Counter64
		MAX-ACCESS		read-only
		STATUS			current
		DESCRIPTION		"Description"
		::=  {  nptPmCEPortCurrentEntry  48  }
		
	nptPmCEPortCurrentOSNRMax	OBJECT-TYPE	
		SYNTAX			DisplayString
		MAX-ACCESS		read-only
		STATUS			current
		DESCRIPTION		"Description"
		::=  {  nptPmCEPortCurrentEntry  49  }
		
	nptPmCEPortCurrentOSNRMin	OBJECT-TYPE	
		SYNTAX			DisplayString
		MAX-ACCESS		read-only
		STATUS			current
		DESCRIPTION		"Description"
		::=  {  nptPmCEPortCurrentEntry  50  }
               
	nptPmCEPortCurrentMaxRxPower	OBJECT-TYPE	
		SYNTAX			DisplayString
		MAX-ACCESS		read-only
		STATUS			current
		DESCRIPTION		"Description"
		::=  {  nptPmCEPortCurrentEntry  51  }
		
	nptPmCEPortCurrentMinRxPower	OBJECT-TYPE	
		SYNTAX			DisplayString
		MAX-ACCESS		read-only
		STATUS			current
		DESCRIPTION		"Description"
		::=  {  nptPmCEPortCurrentEntry  52  }
        
	nptPmCEPortCurrentTxPower	OBJECT-TYPE	
		SYNTAX			DisplayString
		MAX-ACCESS		read-only
		STATUS			current
		DESCRIPTION		"Description"
		::=  {  nptPmCEPortCurrentEntry  53  }	
		
	nptPmCEPortTotalTable	OBJECT-TYPE
		SYNTAX		SEQUENCE  OF  NptPmCEPortTotalEntry
		MAX-ACCESS	not-accessible
		STATUS		current
		DESCRIPTION	"Description"
		::=  { nptPmCEPort  2 }

	nptPmCEPortTotalEntry	OBJECT-TYPE
		SYNTAX		NptPmCEPortTotalEntry
		MAX-ACCESS	not-accessible
		STATUS		current
		DESCRIPTION	"Row Description"
		INDEX		{  nptPmCEPortTotalIndex  }
		::=  { nptPmCEPortTotalTable 1 }

	NptPmCEPortTotalEntry  ::=  SEQUENCE {
	    nptPmCEPortTotalIndex  Integer32,
		nptPmCEPortTotalMoDescription  DisplayString,
	    nptPmCEPortTotalRxOctets  Counter64,
		nptPmCEPortTotalRxPkts  Counter64,
		nptPmCEPortTotalRxBroadcastPkts  Counter64,
		nptPmCEPortTotalRxMulticastPkts  Counter64,
		nptPmCEPortTotalTxOctets  Counter64,
		nptPmCEPortTotalTxPkts  Counter64,
		nptPmCEPortTotalRxErrorPkts  Counter64,
		nptPmCEPortTotalRxPkts64  Counter64,
		nptPmCEPortTotalRxPkts127  Counter64,
		nptPmCEPortTotalRxPkts255  Counter64,
		nptPmCEPortTotalRxPkts511  Counter64,
		nptPmCEPortTotalRxPkts1023  Counter64,
		nptPmCEPortTotalRxPktsMtu  Counter64,
		nptPmCEPortTotalRxUndersizePkts  Counter64,
		nptPmCEPortTotalRxOversizePkts  Counter64,
		nptPmCEPortTotalRxPausePkts  Counter64,
		nptPmCEPortTotalRxJabberPkts  Counter64,
		nptPmCEPortTotalRxCRCAlignErrorPkts  Counter64,
		nptPmCEPortTotalRxFragments  Counter64,
		nptPmCEPortTotalCollisionErrors  Counter64,
		nptPmCEPortTotalPCSLCV  Counter64,
		nptPmCEPortTotalPCSES  Counter64,
		nptPmCEPortTotalPCSSES  Counter64,
		nptPmCEPortTotalPCSUAS  Counter64,
		nptPmCEPortTotalFECCE  Counter64,
		nptPmCEPortTotalFECUCE  Counter64,
		nptPmCEPortTotalPREFECBER  Counter64,
		nptPmCEPortTotalINMaximumRate  Counter64,
		nptPmCEPortTotalINAverageRate  Counter64,
		nptPmCEPortTotalINTotalRate  Counter64,
		nptPmCEPortTotalINMaximumPPS  Counter64,
		nptPmCEPortTotalINAveragePPS  Counter64,
		nptPmCEPortTotalINTotalPPS  Counter64,
		nptPmCEPortTotalINMaximumUtilization  Counter64,
		nptPmCEPortTotalINAverageUtilization  Counter64,
		nptPmCEPortTotalINTotalUtilization  Counter64,
		nptPmCEPortTotalOUTMaximumRate  Counter64,
		nptPmCEPortTotalOUTAverageRate  Counter64,
		nptPmCEPortTotalOUTTotalRate  Counter64,
		nptPmCEPortTotalOUTMaximumPPS  Counter64,
		nptPmCEPortTotalOUTAveragePPS  Counter64,
		nptPmCEPortTotalOUTTotalPPS  Counter64,
		nptPmCEPortTotalOUTMaximumUtilization  Counter64,
		nptPmCEPortTotalOUTAverageUtilization  Counter64,
		nptPmCEPortTotalOUTTotalUtilization  Counter64,
		nptPmCEPortTotalLinkDownSeconds  Counter64,
		nptPmCEPortTotalOSNRMax  DisplayString,
		nptPmCEPortTotalOSNRMin  DisplayString,
		nptPmCEPortTotalMaxRxPower  DisplayString,
		nptPmCEPortTotalMinRxPower  DisplayString,
        nptPmCEPortTotalTxPower  DisplayString
		}


	nptPmCEPortTotalIndex	OBJECT-TYPE	
		SYNTAX			Integer32  ( -2147483648 .. 2147483647  ) 
		MAX-ACCESS		read-only
		STATUS			current
		DESCRIPTION		"Column Description"
		::=  {  nptPmCEPortTotalEntry  1  }
	
	
	nptPmCEPortTotalMoDescription	OBJECT-TYPE	
		SYNTAX			DisplayString 
		MAX-ACCESS		read-only
		STATUS			current
		DESCRIPTION		"Column Description"
		::=  {  nptPmCEPortTotalEntry  2  }


	nptPmCEPortTotalRxOctets	OBJECT-TYPE	
		SYNTAX			Counter64
		MAX-ACCESS		read-only
		STATUS			current
		DESCRIPTION		"Column Description"
		::=  {  nptPmCEPortTotalEntry  3  }


	nptPmCEPortTotalRxPkts	OBJECT-TYPE	
		SYNTAX			Counter64
		MAX-ACCESS		read-only
		STATUS			current
		DESCRIPTION		"Description"
		::=  {  nptPmCEPortTotalEntry  4  }


	nptPmCEPortTotalRxBroadcastPkts	OBJECT-TYPE	
		SYNTAX			Counter64
		MAX-ACCESS		read-only
		STATUS			current
		DESCRIPTION		"Description"
		::=  {  nptPmCEPortTotalEntry  5  }


	nptPmCEPortTotalRxMulticastPkts	OBJECT-TYPE	
		SYNTAX			Counter64
		MAX-ACCESS		read-only
		STATUS			current
		DESCRIPTION		"Description"
		::=  {  nptPmCEPortTotalEntry  6  }


	nptPmCEPortTotalTxOctets	OBJECT-TYPE	
		SYNTAX			Counter64
		MAX-ACCESS		read-only
		STATUS			current
		DESCRIPTION		"Description"
		::=  {  nptPmCEPortTotalEntry  7  }


	nptPmCEPortTotalTxPkts	OBJECT-TYPE	
		SYNTAX			Counter64
		MAX-ACCESS		read-only
		STATUS			current
		DESCRIPTION		"Description"
		::=  {  nptPmCEPortTotalEntry  8  }


	nptPmCEPortTotalRxErrorPkts	OBJECT-TYPE	
		SYNTAX			Counter64
		MAX-ACCESS		read-only
		STATUS			current
		DESCRIPTION		"Description"
		::=  {  nptPmCEPortTotalEntry  9  }


	nptPmCEPortTotalRxPkts64	OBJECT-TYPE	
		SYNTAX			Counter64
		MAX-ACCESS		read-only
		STATUS			current
		DESCRIPTION		"Description"
		::=  {  nptPmCEPortTotalEntry  10  }


	nptPmCEPortTotalRxPkts127	OBJECT-TYPE	
		SYNTAX			Counter64
		MAX-ACCESS		read-only
		STATUS			current
		DESCRIPTION		"Description"
		::=  {  nptPmCEPortTotalEntry  11  }


	nptPmCEPortTotalRxPkts255	OBJECT-TYPE	
		SYNTAX			Counter64
		MAX-ACCESS		read-only
		STATUS			current
		DESCRIPTION		"Description"
		::=  {  nptPmCEPortTotalEntry  12  }


	nptPmCEPortTotalRxPkts511	OBJECT-TYPE	
		SYNTAX			Counter64
		MAX-ACCESS		read-only
		STATUS			current
		DESCRIPTION		"Description"
		::=  {  nptPmCEPortTotalEntry  13  }


	nptPmCEPortTotalRxPkts1023	OBJECT-TYPE	
		SYNTAX			Counter64
		MAX-ACCESS		read-only
		STATUS			current
		DESCRIPTION		"Description"
		::=  {  nptPmCEPortTotalEntry  14  }


	nptPmCEPortTotalRxPktsMtu	OBJECT-TYPE	
		SYNTAX			Counter64
		MAX-ACCESS		read-only
		STATUS			current
		DESCRIPTION		"Description"
		::=  {  nptPmCEPortTotalEntry  15  }


	nptPmCEPortTotalRxUndersizePkts	OBJECT-TYPE	
		SYNTAX			Counter64
		MAX-ACCESS		read-only
		STATUS			current
		DESCRIPTION		"Description"
		::=  {  nptPmCEPortTotalEntry  16  }


	nptPmCEPortTotalRxOversizePkts	OBJECT-TYPE	
		SYNTAX			Counter64
		MAX-ACCESS		read-only
		STATUS			current
		DESCRIPTION		"Description"
		::=  {  nptPmCEPortTotalEntry  17  }


	nptPmCEPortTotalRxPausePkts	OBJECT-TYPE	
		SYNTAX			Counter64
		MAX-ACCESS		read-only
		STATUS			current
		DESCRIPTION		"Description"
		::=  {  nptPmCEPortTotalEntry  18  }
		
	nptPmCEPortTotalRxJabberPkts	OBJECT-TYPE	
		SYNTAX			Counter64
		MAX-ACCESS		read-only
		STATUS			current
		DESCRIPTION		"Description"
		::=  {  nptPmCEPortTotalEntry  19  }


	nptPmCEPortTotalRxCRCAlignErrorPkts	OBJECT-TYPE	
		SYNTAX			Counter64
		MAX-ACCESS		read-only
		STATUS			current
		DESCRIPTION		"Description"
		::=  {  nptPmCEPortTotalEntry  20  }


	nptPmCEPortTotalRxFragments	OBJECT-TYPE	
		SYNTAX			Counter64
		MAX-ACCESS		read-only
		STATUS			current
		DESCRIPTION		"Description"
		::=  {  nptPmCEPortTotalEntry  21  }


	nptPmCEPortTotalCollisionErrors	OBJECT-TYPE	
		SYNTAX			Counter64
		MAX-ACCESS		read-only
		STATUS			current
		DESCRIPTION		"Description"
		::=  {  nptPmCEPortTotalEntry  22  }


	nptPmCEPortTotalPCSLCV	OBJECT-TYPE	
		SYNTAX			Counter64
		MAX-ACCESS		read-only
		STATUS			current
		DESCRIPTION		"Description"
		::=  {  nptPmCEPortTotalEntry  23  }


	nptPmCEPortTotalPCSES	OBJECT-TYPE	
		SYNTAX			Counter64
		MAX-ACCESS		read-only
		STATUS			current
		DESCRIPTION		"Description"
		::=  {  nptPmCEPortTotalEntry  24  }


	nptPmCEPortTotalPCSSES	OBJECT-TYPE	
		SYNTAX			Counter64
		MAX-ACCESS		read-only
		STATUS			current
		DESCRIPTION		"Description"
		::=  {  nptPmCEPortTotalEntry  25  }


	nptPmCEPortTotalPCSUAS	OBJECT-TYPE	
		SYNTAX			Counter64
		MAX-ACCESS		read-only
		STATUS			current
		DESCRIPTION		"Description"
		::=  {  nptPmCEPortTotalEntry  26  }
		
	nptPmCEPortTotalFECCE	OBJECT-TYPE	
		SYNTAX			Counter64
		MAX-ACCESS		read-only
		STATUS			current
		DESCRIPTION		"Description"
		::=  {  nptPmCEPortTotalEntry  27  }


	nptPmCEPortTotalFECUCE	OBJECT-TYPE	
		SYNTAX			Counter64
		MAX-ACCESS		read-only
		STATUS			current
		DESCRIPTION		"Description"
		::=  {  nptPmCEPortTotalEntry  28  }


	nptPmCEPortTotalPREFECBER	OBJECT-TYPE	
		SYNTAX			Counter64
		MAX-ACCESS		read-only
		STATUS			current
		DESCRIPTION		"Description"
		::=  {  nptPmCEPortTotalEntry  29  }


	nptPmCEPortTotalINMaximumRate	OBJECT-TYPE	
		SYNTAX			Counter64
		MAX-ACCESS		read-only
		STATUS			current
		DESCRIPTION		"Description"
		::=  {  nptPmCEPortTotalEntry  30  }
		
	nptPmCEPortTotalINAverageRate	OBJECT-TYPE	
		SYNTAX			Counter64
		MAX-ACCESS		read-only
		STATUS			current
		DESCRIPTION		"Description"
		::=  {  nptPmCEPortTotalEntry  31  }
		
	nptPmCEPortTotalINTotalRate	OBJECT-TYPE	
		SYNTAX			Counter64
		MAX-ACCESS		read-only
		STATUS			current
		DESCRIPTION		"Description"
		::=  {  nptPmCEPortTotalEntry  32  }
		
	nptPmCEPortTotalINMaximumPPS	OBJECT-TYPE	
		SYNTAX			Counter64
		MAX-ACCESS		read-only
		STATUS			current
		DESCRIPTION		"Description"
		::=  {  nptPmCEPortTotalEntry  33  }
		
	nptPmCEPortTotalINAveragePPS	OBJECT-TYPE	
		SYNTAX			Counter64
		MAX-ACCESS		read-only
		STATUS			current
		DESCRIPTION		"Description"
		::=  {  nptPmCEPortTotalEntry  34  }
		
	nptPmCEPortTotalINTotalPPS	OBJECT-TYPE	
		SYNTAX			Counter64
		MAX-ACCESS		read-only
		STATUS			current
		DESCRIPTION		"Description"
		::=  {  nptPmCEPortTotalEntry  35  }
		
	nptPmCEPortTotalINMaximumUtilization	OBJECT-TYPE	
		SYNTAX			Counter64
		MAX-ACCESS		read-only
		STATUS			current
		DESCRIPTION		"Description"
		::=  {  nptPmCEPortTotalEntry  36  }
		
	nptPmCEPortTotalINAverageUtilization	OBJECT-TYPE	
		SYNTAX			Counter64
		MAX-ACCESS		read-only
		STATUS			current
		DESCRIPTION		"Description"
		::=  {  nptPmCEPortTotalEntry  37  }
		
	nptPmCEPortTotalINTotalUtilization	OBJECT-TYPE	
		SYNTAX			Counter64
		MAX-ACCESS		read-only
		STATUS			current
		DESCRIPTION		"Description"
		::=  {  nptPmCEPortTotalEntry  38  }
		
	nptPmCEPortTotalOUTMaximumRate	OBJECT-TYPE	
		SYNTAX			Counter64
		MAX-ACCESS		read-only
		STATUS			current
		DESCRIPTION		"Description"
		::=  {  nptPmCEPortTotalEntry  39  }
		
	nptPmCEPortTotalOUTAverageRate	OBJECT-TYPE	
		SYNTAX			Counter64
		MAX-ACCESS		read-only
		STATUS			current
		DESCRIPTION		"Description"
		::=  {  nptPmCEPortTotalEntry  40  }
		
	nptPmCEPortTotalOUTTotalRate	OBJECT-TYPE	
		SYNTAX			Counter64
		MAX-ACCESS		read-only
		STATUS			current
		DESCRIPTION		"Description"
		::=  {  nptPmCEPortTotalEntry  41  }
		
	nptPmCEPortTotalOUTMaximumPPS	OBJECT-TYPE	
		SYNTAX			Counter64
		MAX-ACCESS		read-only
		STATUS			current
		DESCRIPTION		"Description"
		::=  {  nptPmCEPortTotalEntry  42  }
		
	nptPmCEPortTotalOUTAveragePPS	OBJECT-TYPE	
		SYNTAX			Counter64
		MAX-ACCESS		read-only
		STATUS			current
		DESCRIPTION		"Description"
		::=  {  nptPmCEPortTotalEntry  43  }
		
	nptPmCEPortTotalOUTTotalPPS	OBJECT-TYPE	
		SYNTAX			Counter64
		MAX-ACCESS		read-only
		STATUS			current
		DESCRIPTION		"Description"
		::=  {  nptPmCEPortTotalEntry  44  }
		
	nptPmCEPortTotalOUTMaximumUtilization	OBJECT-TYPE	
		SYNTAX			Counter64
		MAX-ACCESS		read-only
		STATUS			current
		DESCRIPTION		"Description"
		::=  {  nptPmCEPortTotalEntry  45  }
		
	nptPmCEPortTotalOUTAverageUtilization	OBJECT-TYPE	
		SYNTAX			Counter64
		MAX-ACCESS		read-only
		STATUS			current
		DESCRIPTION		"Description"
		::=  {  nptPmCEPortTotalEntry  46  }
		
	nptPmCEPortTotalOUTTotalUtilization	OBJECT-TYPE	
		SYNTAX			Counter64
		MAX-ACCESS		read-only
		STATUS			current
		DESCRIPTION		"Description"
		::=  {  nptPmCEPortTotalEntry  47  }
		
	nptPmCEPortTotalLinkDownSeconds	OBJECT-TYPE	
		SYNTAX			Counter64
		MAX-ACCESS		read-only
		STATUS			current
		DESCRIPTION		"Description"
		::=  {  nptPmCEPortTotalEntry  48  }
		
	nptPmCEPortTotalOSNRMax	OBJECT-TYPE	
		SYNTAX			DisplayString
		MAX-ACCESS		read-only
		STATUS			current
		DESCRIPTION		"Description"
		::=  {  nptPmCEPortTotalEntry  49  }
		
	nptPmCEPortTotalOSNRMin	OBJECT-TYPE	
		SYNTAX			DisplayString
		MAX-ACCESS		read-only
		STATUS			current
		DESCRIPTION		"Description"
		::=  {  nptPmCEPortTotalEntry  50  }
               
	nptPmCEPortTotalMaxRxPower	OBJECT-TYPE	
		SYNTAX			DisplayString
		MAX-ACCESS		read-only
		STATUS			current
		DESCRIPTION		"Description"
		::=  {  nptPmCEPortTotalEntry  51  }
		
	nptPmCEPortTotalMinRxPower	OBJECT-TYPE	
		SYNTAX			DisplayString
		MAX-ACCESS		read-only
		STATUS			current
		DESCRIPTION		"Description"
		::=  {  nptPmCEPortTotalEntry  52  }
        
	nptPmCEPortTotalTxPower	OBJECT-TYPE	
		SYNTAX			DisplayString
		MAX-ACCESS		read-only
		STATUS			current
		DESCRIPTION		"Description"
		::=  {  nptPmCEPortTotalEntry  53  }	
		
	nptPmGE25PortCurrentTable	OBJECT-TYPE
		SYNTAX		SEQUENCE  OF  NptPmGE25PortCurrentEntry
		MAX-ACCESS	not-accessible
		STATUS		current
		DESCRIPTION	"Description"
		::=  { nptPmGE25Port  1 }

	nptPmGE25PortCurrentEntry	OBJECT-TYPE
		SYNTAX		NptPmGE25PortCurrentEntry
		MAX-ACCESS	not-accessible
		STATUS		current
		DESCRIPTION	"Row Description"
		INDEX		{  nptPmGE25PortCurrentIndex  }
		::=  { nptPmGE25PortCurrentTable 1 }

	NptPmGE25PortCurrentEntry  ::=  SEQUENCE {
	    nptPmGE25PortCurrentIndex  Integer32,
		nptPmGE25PortCurrentMoDescription  DisplayString,
	    nptPmGE25PortCurrentRxOctets  Counter64,
		nptPmGE25PortCurrentRxPkts  Counter64,
		nptPmGE25PortCurrentRxBroadcastPkts  Counter64,
		nptPmGE25PortCurrentRxMulticastPkts  Counter64,
		nptPmGE25PortCurrentTxOctets  Counter64,
		nptPmGE25PortCurrentTxPkts  Counter64,
		nptPmGE25PortCurrentRxErrorPkts  Counter64,
		nptPmGE25PortCurrentRxPkts64  Counter64,
		nptPmGE25PortCurrentRxPkts127  Counter64,
		nptPmGE25PortCurrentRxPkts255  Counter64,
		nptPmGE25PortCurrentRxPkts511  Counter64,
		nptPmGE25PortCurrentRxPkts1023  Counter64,
		nptPmGE25PortCurrentRxPktsMtu  Counter64,
		nptPmGE25PortCurrentRxUndersizePkts  Counter64,
		nptPmGE25PortCurrentRxOversizePkts  Counter64,
		nptPmGE25PortCurrentRxPausePkts  Counter64,
		nptPmGE25PortCurrentRxJabberPkts  Counter64,
		nptPmGE25PortCurrentRxCRCAlignErrorPkts  Counter64,
		nptPmGE25PortCurrentRxFragments  Counter64,
		nptPmGE25PortCurrentCollisionErrors  Counter64,
		nptPmGE25PortCurrentPCSLCV  Counter64,
		nptPmGE25PortCurrentPCSES  Counter64,
		nptPmGE25PortCurrentPCSSES  Counter64,
		nptPmGE25PortCurrentPCSUAS  Counter64,
		nptPmGE25PortCurrentFECCE  Counter64,
		nptPmGE25PortCurrentFECUCE  Counter64,
		nptPmGE25PortCurrentPREFECBER  Counter64,
		nptPmGE25PortCurrentINMaximumRate  Counter64,
		nptPmGE25PortCurrentINAverageRate  Counter64,
		nptPmGE25PortCurrentINCurrentRate  Counter64,
		nptPmGE25PortCurrentINMaximumPPS  Counter64,
		nptPmGE25PortCurrentINAveragePPS  Counter64,
		nptPmGE25PortCurrentINCurrentPPS  Counter64,
		nptPmGE25PortCurrentINMaximumUtilization  Counter64,
		nptPmGE25PortCurrentINAverageUtilization  Counter64,
		nptPmGE25PortCurrentINCurrentUtilization  Counter64,
		nptPmGE25PortCurrentOUTMaximumRate  Counter64,
		nptPmGE25PortCurrentOUTAverageRate  Counter64,
		nptPmGE25PortCurrentOUTCurrentRate  Counter64,
		nptPmGE25PortCurrentOUTMaximumPPS  Counter64,
		nptPmGE25PortCurrentOUTAveragePPS  Counter64,
		nptPmGE25PortCurrentOUTCurrentPPS  Counter64,
		nptPmGE25PortCurrentOUTMaximumUtilization  Counter64,
		nptPmGE25PortCurrentOUTAverageUtilization  Counter64,
		nptPmGE25PortCurrentOUTCurrentUtilization  Counter64,
		nptPmGE25PortCurrentLinkDownSeconds  Counter64,
		nptPmGE25PortCurrentOSNRMax  DisplayString,
		nptPmGE25PortCurrentOSNRMin  DisplayString,
		nptPmGE25PortCurrentMaxRxPower  DisplayString,
		nptPmGE25PortCurrentMinRxPower  DisplayString,
        nptPmGE25PortCurrentTxPower  DisplayString
		}


	nptPmGE25PortCurrentIndex	OBJECT-TYPE	
		SYNTAX			Integer32  ( -2147483648 .. 2147483647  ) 
		MAX-ACCESS		read-only
		STATUS			current
		DESCRIPTION		"Column Description"
		::=  {  nptPmGE25PortCurrentEntry  1  }
		
	nptPmGE25PortCurrentMoDescription	OBJECT-TYPE	
		SYNTAX			DisplayString 
		MAX-ACCESS		read-only
		STATUS			current
		DESCRIPTION		"Column Description"
		::=  {  nptPmGE25PortCurrentEntry  2  }


	nptPmGE25PortCurrentRxOctets	OBJECT-TYPE	
		SYNTAX			Counter64
		MAX-ACCESS		read-only
		STATUS			current
		DESCRIPTION		"Column Description"
		::=  {  nptPmGE25PortCurrentEntry  3  }


	nptPmGE25PortCurrentRxPkts	OBJECT-TYPE	
		SYNTAX			Counter64
		MAX-ACCESS		read-only
		STATUS			current
		DESCRIPTION		"Description"
		::=  {  nptPmGE25PortCurrentEntry  4  }


	nptPmGE25PortCurrentRxBroadcastPkts	OBJECT-TYPE	
		SYNTAX			Counter64
		MAX-ACCESS		read-only
		STATUS			current
		DESCRIPTION		"Description"
		::=  {  nptPmGE25PortCurrentEntry  5  }


	nptPmGE25PortCurrentRxMulticastPkts	OBJECT-TYPE	
		SYNTAX			Counter64
		MAX-ACCESS		read-only
		STATUS			current
		DESCRIPTION		"Description"
		::=  {  nptPmGE25PortCurrentEntry  6  }


	nptPmGE25PortCurrentTxOctets	OBJECT-TYPE	
		SYNTAX			Counter64
		MAX-ACCESS		read-only
		STATUS			current
		DESCRIPTION		"Description"
		::=  {  nptPmGE25PortCurrentEntry  7  }


	nptPmGE25PortCurrentTxPkts	OBJECT-TYPE	
		SYNTAX			Counter64
		MAX-ACCESS		read-only
		STATUS			current
		DESCRIPTION		"Description"
		::=  {  nptPmGE25PortCurrentEntry  8  }


	nptPmGE25PortCurrentRxErrorPkts	OBJECT-TYPE	
		SYNTAX			Counter64
		MAX-ACCESS		read-only
		STATUS			current
		DESCRIPTION		"Description"
		::=  {  nptPmGE25PortCurrentEntry  9  }


	nptPmGE25PortCurrentRxPkts64	OBJECT-TYPE	
		SYNTAX			Counter64
		MAX-ACCESS		read-only
		STATUS			current
		DESCRIPTION		"Description"
		::=  {  nptPmGE25PortCurrentEntry  10  }


	nptPmGE25PortCurrentRxPkts127	OBJECT-TYPE	
		SYNTAX			Counter64
		MAX-ACCESS		read-only
		STATUS			current
		DESCRIPTION		"Description"
		::=  {  nptPmGE25PortCurrentEntry  11  }


	nptPmGE25PortCurrentRxPkts255	OBJECT-TYPE	
		SYNTAX			Counter64
		MAX-ACCESS		read-only
		STATUS			current
		DESCRIPTION		"Description"
		::=  {  nptPmGE25PortCurrentEntry  12  }


	nptPmGE25PortCurrentRxPkts511	OBJECT-TYPE	
		SYNTAX			Counter64
		MAX-ACCESS		read-only
		STATUS			current
		DESCRIPTION		"Description"
		::=  {  nptPmGE25PortCurrentEntry  13  }


	nptPmGE25PortCurrentRxPkts1023	OBJECT-TYPE	
		SYNTAX			Counter64
		MAX-ACCESS		read-only
		STATUS			current
		DESCRIPTION		"Description"
		::=  {  nptPmGE25PortCurrentEntry  14  }


	nptPmGE25PortCurrentRxPktsMtu	OBJECT-TYPE	
		SYNTAX			Counter64
		MAX-ACCESS		read-only
		STATUS			current
		DESCRIPTION		"Description"
		::=  {  nptPmGE25PortCurrentEntry  15  }


	nptPmGE25PortCurrentRxUndersizePkts	OBJECT-TYPE	
		SYNTAX			Counter64
		MAX-ACCESS		read-only
		STATUS			current
		DESCRIPTION		"Description"
		::=  {  nptPmGE25PortCurrentEntry  16  }


	nptPmGE25PortCurrentRxOversizePkts	OBJECT-TYPE	
		SYNTAX			Counter64
		MAX-ACCESS		read-only
		STATUS			current
		DESCRIPTION		"Description"
		::=  {  nptPmGE25PortCurrentEntry  17  }


	nptPmGE25PortCurrentRxPausePkts	OBJECT-TYPE	
		SYNTAX			Counter64
		MAX-ACCESS		read-only
		STATUS			current
		DESCRIPTION		"Description"
		::=  {  nptPmGE25PortCurrentEntry  18  }
		
	nptPmGE25PortCurrentRxJabberPkts	OBJECT-TYPE	
		SYNTAX			Counter64
		MAX-ACCESS		read-only
		STATUS			current
		DESCRIPTION		"Description"
		::=  {  nptPmGE25PortCurrentEntry  19  }


	nptPmGE25PortCurrentRxCRCAlignErrorPkts	OBJECT-TYPE	
		SYNTAX			Counter64
		MAX-ACCESS		read-only
		STATUS			current
		DESCRIPTION		"Description"
		::=  {  nptPmGE25PortCurrentEntry  20  }


	nptPmGE25PortCurrentRxFragments	OBJECT-TYPE	
		SYNTAX			Counter64
		MAX-ACCESS		read-only
		STATUS			current
		DESCRIPTION		"Description"
		::=  {  nptPmGE25PortCurrentEntry  21  }


	nptPmGE25PortCurrentCollisionErrors	OBJECT-TYPE	
		SYNTAX			Counter64
		MAX-ACCESS		read-only
		STATUS			current
		DESCRIPTION		"Description"
		::=  {  nptPmGE25PortCurrentEntry  22  }


	nptPmGE25PortCurrentPCSLCV	OBJECT-TYPE	
		SYNTAX			Counter64
		MAX-ACCESS		read-only
		STATUS			current
		DESCRIPTION		"Description"
		::=  {  nptPmGE25PortCurrentEntry  23  }
		


	nptPmGE25PortCurrentPCSES	OBJECT-TYPE	
		SYNTAX			Counter64
		MAX-ACCESS		read-only
		STATUS			current
		DESCRIPTION		"Description"
		::=  {  nptPmGE25PortCurrentEntry  24  }


	nptPmGE25PortCurrentPCSSES	OBJECT-TYPE	
		SYNTAX			Counter64
		MAX-ACCESS		read-only
		STATUS			current
		DESCRIPTION		"Description"
		::=  {  nptPmGE25PortCurrentEntry  25  }


	nptPmGE25PortCurrentPCSUAS	OBJECT-TYPE	
		SYNTAX			Counter64
		MAX-ACCESS		read-only
		STATUS			current
		DESCRIPTION		"Description"
		::=  {  nptPmGE25PortCurrentEntry  26  }
		
	nptPmGE25PortCurrentFECCE	OBJECT-TYPE	
		SYNTAX			Counter64
		MAX-ACCESS		read-only
		STATUS			current
		DESCRIPTION		"Description"
		::=  {  nptPmGE25PortCurrentEntry  27  }


	nptPmGE25PortCurrentFECUCE	OBJECT-TYPE	
		SYNTAX			Counter64
		MAX-ACCESS		read-only
		STATUS			current
		DESCRIPTION		"Description"
		::=  {  nptPmGE25PortCurrentEntry  28  }


	nptPmGE25PortCurrentPREFECBER	OBJECT-TYPE	
		SYNTAX			Counter64
		MAX-ACCESS		read-only
		STATUS			current
		DESCRIPTION		"Description"
		::=  {  nptPmGE25PortCurrentEntry  29  }


	nptPmGE25PortCurrentINMaximumRate	OBJECT-TYPE	
		SYNTAX			Counter64
		MAX-ACCESS		read-only
		STATUS			current
		DESCRIPTION		"Description"
		::=  {  nptPmGE25PortCurrentEntry  30  }
		
	nptPmGE25PortCurrentINAverageRate	OBJECT-TYPE	
		SYNTAX			Counter64
		MAX-ACCESS		read-only
		STATUS			current
		DESCRIPTION		"Description"
		::=  {  nptPmGE25PortCurrentEntry  31  }
		
	nptPmGE25PortCurrentINCurrentRate	OBJECT-TYPE	
		SYNTAX			Counter64
		MAX-ACCESS		read-only
		STATUS			current
		DESCRIPTION		"Description"
		::=  {  nptPmGE25PortCurrentEntry  32  }
		
	nptPmGE25PortCurrentINMaximumPPS	OBJECT-TYPE	
		SYNTAX			Counter64
		MAX-ACCESS		read-only
		STATUS			current
		DESCRIPTION		"Description"
		::=  {  nptPmGE25PortCurrentEntry  33  }
		
	nptPmGE25PortCurrentINAveragePPS	OBJECT-TYPE	
		SYNTAX			Counter64
		MAX-ACCESS		read-only
		STATUS			current
		DESCRIPTION		"Description"
		::=  {  nptPmGE25PortCurrentEntry  34  }
		
	nptPmGE25PortCurrentINCurrentPPS	OBJECT-TYPE	
		SYNTAX			Counter64
		MAX-ACCESS		read-only
		STATUS			current
		DESCRIPTION		"Description"
		::=  {  nptPmGE25PortCurrentEntry  35  }
		
	nptPmGE25PortCurrentINMaximumUtilization	OBJECT-TYPE	
		SYNTAX			Counter64
		MAX-ACCESS		read-only
		STATUS			current
		DESCRIPTION		"Description"
		::=  {  nptPmGE25PortCurrentEntry  36  }
		
	nptPmGE25PortCurrentINAverageUtilization	OBJECT-TYPE	
		SYNTAX			Counter64
		MAX-ACCESS		read-only
		STATUS			current
		DESCRIPTION		"Description"
		::=  {  nptPmGE25PortCurrentEntry  37  }
		
	nptPmGE25PortCurrentINCurrentUtilization	OBJECT-TYPE	
		SYNTAX			Counter64
		MAX-ACCESS		read-only
		STATUS			current
		DESCRIPTION		"Description"
		::=  {  nptPmGE25PortCurrentEntry  38  }
		
	nptPmGE25PortCurrentOUTMaximumRate	OBJECT-TYPE	
		SYNTAX			Counter64
		MAX-ACCESS		read-only
		STATUS			current
		DESCRIPTION		"Description"
		::=  {  nptPmGE25PortCurrentEntry  39  }
		
	nptPmGE25PortCurrentOUTAverageRate	OBJECT-TYPE	
		SYNTAX			Counter64
		MAX-ACCESS		read-only
		STATUS			current
		DESCRIPTION		"Description"
		::=  {  nptPmGE25PortCurrentEntry  40  }
		
	nptPmGE25PortCurrentOUTCurrentRate	OBJECT-TYPE	
		SYNTAX			Counter64
		MAX-ACCESS		read-only
		STATUS			current
		DESCRIPTION		"Description"
		::=  {  nptPmGE25PortCurrentEntry  41  }
		
	nptPmGE25PortCurrentOUTMaximumPPS	OBJECT-TYPE	
		SYNTAX			Counter64
		MAX-ACCESS		read-only
		STATUS			current
		DESCRIPTION		"Description"
		::=  {  nptPmGE25PortCurrentEntry  42  }
		
	nptPmGE25PortCurrentOUTAveragePPS	OBJECT-TYPE	
		SYNTAX			Counter64
		MAX-ACCESS		read-only
		STATUS			current
		DESCRIPTION		"Description"
		::=  {  nptPmGE25PortCurrentEntry  43  }
		
	nptPmGE25PortCurrentOUTCurrentPPS	OBJECT-TYPE	
		SYNTAX			Counter64
		MAX-ACCESS		read-only
		STATUS			current
		DESCRIPTION		"Description"
		::=  {  nptPmGE25PortCurrentEntry  44  }
		
	nptPmGE25PortCurrentOUTMaximumUtilization	OBJECT-TYPE	
		SYNTAX			Counter64
		MAX-ACCESS		read-only
		STATUS			current
		DESCRIPTION		"Description"
		::=  {  nptPmGE25PortCurrentEntry  45  }
		
	nptPmGE25PortCurrentOUTAverageUtilization	OBJECT-TYPE	
		SYNTAX			Counter64
		MAX-ACCESS		read-only
		STATUS			current
		DESCRIPTION		"Description"
		::=  {  nptPmGE25PortCurrentEntry  46  }
		
	nptPmGE25PortCurrentOUTCurrentUtilization	OBJECT-TYPE	
		SYNTAX			Counter64
		MAX-ACCESS		read-only
		STATUS			current
		DESCRIPTION		"Description"
		::=  {  nptPmGE25PortCurrentEntry  47  }
		
	nptPmGE25PortCurrentLinkDownSeconds	OBJECT-TYPE	
		SYNTAX			Counter64
		MAX-ACCESS		read-only
		STATUS			current
		DESCRIPTION		"Description"
		::=  {  nptPmGE25PortCurrentEntry  48  }
		
	nptPmGE25PortCurrentOSNRMax	OBJECT-TYPE	
		SYNTAX			DisplayString
		MAX-ACCESS		read-only
		STATUS			current
		DESCRIPTION		"Description"
		::=  {  nptPmGE25PortCurrentEntry  49  }
		
	nptPmGE25PortCurrentOSNRMin	OBJECT-TYPE	
		SYNTAX			DisplayString
		MAX-ACCESS		read-only
		STATUS			current
		DESCRIPTION		"Description"
		::=  {  nptPmGE25PortCurrentEntry  50  }
               
	nptPmGE25PortCurrentMaxRxPower	OBJECT-TYPE	
		SYNTAX			DisplayString
		MAX-ACCESS		read-only
		STATUS			current
		DESCRIPTION		"Description"
		::=  {  nptPmGE25PortCurrentEntry  51  }
		
	nptPmGE25PortCurrentMinRxPower	OBJECT-TYPE	
		SYNTAX			DisplayString
		MAX-ACCESS		read-only
		STATUS			current
		DESCRIPTION		"Description"
		::=  {  nptPmGE25PortCurrentEntry  52  }
        
	nptPmGE25PortCurrentTxPower	OBJECT-TYPE	
		SYNTAX			DisplayString
		MAX-ACCESS		read-only
		STATUS			current
		DESCRIPTION		"Description"
		::=  {  nptPmGE25PortCurrentEntry  53  }	
		
	nptPmGE25PortTotalTable	OBJECT-TYPE
		SYNTAX		SEQUENCE  OF  NptPmGE25PortTotalEntry
		MAX-ACCESS	not-accessible
		STATUS		current
		DESCRIPTION	"Description"
		::=  { nptPmGE25Port  2 }

	nptPmGE25PortTotalEntry	OBJECT-TYPE
		SYNTAX		NptPmGE25PortTotalEntry
		MAX-ACCESS	not-accessible
		STATUS		current
		DESCRIPTION	"Row Description"
		INDEX		{  nptPmGE25PortTotalIndex  }
		::=  { nptPmGE25PortTotalTable 1 }

	NptPmGE25PortTotalEntry  ::=  SEQUENCE {
	    nptPmGE25PortTotalIndex  Integer32,
		nptPmGE25PortTotalMoDescription  DisplayString,
	    nptPmGE25PortTotalRxOctets  Counter64,
		nptPmGE25PortTotalRxPkts  Counter64,
		nptPmGE25PortTotalRxBroadcastPkts  Counter64,
		nptPmGE25PortTotalRxMulticastPkts  Counter64,
		nptPmGE25PortTotalTxOctets  Counter64,
		nptPmGE25PortTotalTxPkts  Counter64,
		nptPmGE25PortTotalRxErrorPkts  Counter64,
		nptPmGE25PortTotalRxPkts64  Counter64,
		nptPmGE25PortTotalRxPkts127  Counter64,
		nptPmGE25PortTotalRxPkts255  Counter64,
		nptPmGE25PortTotalRxPkts511  Counter64,
		nptPmGE25PortTotalRxPkts1023  Counter64,
		nptPmGE25PortTotalRxPktsMtu  Counter64,
		nptPmGE25PortTotalRxUndersizePkts  Counter64,
		nptPmGE25PortTotalRxOversizePkts  Counter64,
		nptPmGE25PortTotalRxPausePkts  Counter64,
		nptPmGE25PortTotalRxJabberPkts  Counter64,
		nptPmGE25PortTotalRxCRCAlignErrorPkts  Counter64,
		nptPmGE25PortTotalRxFragments  Counter64,
		nptPmGE25PortTotalCollisionErrors  Counter64,
		nptPmGE25PortTotalPCSLCV  Counter64,
		nptPmGE25PortTotalPCSES  Counter64,
		nptPmGE25PortTotalPCSSES  Counter64,
		nptPmGE25PortTotalPCSUAS  Counter64,
		nptPmGE25PortTotalFECCE  Counter64,
		nptPmGE25PortTotalFECUCE  Counter64,
		nptPmGE25PortTotalPREFECBER  Counter64,
		nptPmGE25PortTotalINMaximumRate  Counter64,
		nptPmGE25PortTotalINAverageRate  Counter64,
		nptPmGE25PortTotalINTotalRate  Counter64,
		nptPmGE25PortTotalINMaximumPPS  Counter64,
		nptPmGE25PortTotalINAveragePPS  Counter64,
		nptPmGE25PortTotalINTotalPPS  Counter64,
		nptPmGE25PortTotalINMaximumUtilization  Counter64,
		nptPmGE25PortTotalINAverageUtilization  Counter64,
		nptPmGE25PortTotalINTotalUtilization  Counter64,
		nptPmGE25PortTotalOUTMaximumRate  Counter64,
		nptPmGE25PortTotalOUTAverageRate  Counter64,
		nptPmGE25PortTotalOUTTotalRate  Counter64,
		nptPmGE25PortTotalOUTMaximumPPS  Counter64,
		nptPmGE25PortTotalOUTAveragePPS  Counter64,
		nptPmGE25PortTotalOUTTotalPPS  Counter64,
		nptPmGE25PortTotalOUTMaximumUtilization  Counter64,
		nptPmGE25PortTotalOUTAverageUtilization  Counter64,
		nptPmGE25PortTotalOUTTotalUtilization  Counter64,
		nptPmGE25PortTotalLinkDownSeconds  Counter64,
		nptPmGE25PortTotalOSNRMax  DisplayString,
		nptPmGE25PortTotalOSNRMin  DisplayString,
		nptPmGE25PortTotalMaxRxPower  DisplayString,
		nptPmGE25PortTotalMinRxPower  DisplayString,
        nptPmGE25PortTotalTxPower  DisplayString
		}


	nptPmGE25PortTotalIndex	OBJECT-TYPE	
		SYNTAX			Integer32  ( -2147483648 .. 2147483647  ) 
		MAX-ACCESS		read-only
		STATUS			current
		DESCRIPTION		"Column Description"
		::=  {  nptPmGE25PortTotalEntry  1  }
	
	
	nptPmGE25PortTotalMoDescription	OBJECT-TYPE	
		SYNTAX			DisplayString 
		MAX-ACCESS		read-only
		STATUS			current
		DESCRIPTION		"Column Description"
		::=  {  nptPmGE25PortTotalEntry  2  }


	nptPmGE25PortTotalRxOctets	OBJECT-TYPE	
		SYNTAX			Counter64
		MAX-ACCESS		read-only
		STATUS			current
		DESCRIPTION		"Column Description"
		::=  {  nptPmGE25PortTotalEntry  3  }


	nptPmGE25PortTotalRxPkts	OBJECT-TYPE	
		SYNTAX			Counter64
		MAX-ACCESS		read-only
		STATUS			current
		DESCRIPTION		"Description"
		::=  {  nptPmGE25PortTotalEntry  4  }


	nptPmGE25PortTotalRxBroadcastPkts	OBJECT-TYPE	
		SYNTAX			Counter64
		MAX-ACCESS		read-only
		STATUS			current
		DESCRIPTION		"Description"
		::=  {  nptPmGE25PortTotalEntry  5  }


	nptPmGE25PortTotalRxMulticastPkts	OBJECT-TYPE	
		SYNTAX			Counter64
		MAX-ACCESS		read-only
		STATUS			current
		DESCRIPTION		"Description"
		::=  {  nptPmGE25PortTotalEntry  6  }


	nptPmGE25PortTotalTxOctets	OBJECT-TYPE	
		SYNTAX			Counter64
		MAX-ACCESS		read-only
		STATUS			current
		DESCRIPTION		"Description"
		::=  {  nptPmGE25PortTotalEntry  7  }


	nptPmGE25PortTotalTxPkts	OBJECT-TYPE	
		SYNTAX			Counter64
		MAX-ACCESS		read-only
		STATUS			current
		DESCRIPTION		"Description"
		::=  {  nptPmGE25PortTotalEntry  8  }


	nptPmGE25PortTotalRxErrorPkts	OBJECT-TYPE	
		SYNTAX			Counter64
		MAX-ACCESS		read-only
		STATUS			current
		DESCRIPTION		"Description"
		::=  {  nptPmGE25PortTotalEntry  9  }


	nptPmGE25PortTotalRxPkts64	OBJECT-TYPE	
		SYNTAX			Counter64
		MAX-ACCESS		read-only
		STATUS			current
		DESCRIPTION		"Description"
		::=  {  nptPmGE25PortTotalEntry  10  }


	nptPmGE25PortTotalRxPkts127	OBJECT-TYPE	
		SYNTAX			Counter64
		MAX-ACCESS		read-only
		STATUS			current
		DESCRIPTION		"Description"
		::=  {  nptPmGE25PortTotalEntry  11  }


	nptPmGE25PortTotalRxPkts255	OBJECT-TYPE	
		SYNTAX			Counter64
		MAX-ACCESS		read-only
		STATUS			current
		DESCRIPTION		"Description"
		::=  {  nptPmGE25PortTotalEntry  12  }


	nptPmGE25PortTotalRxPkts511	OBJECT-TYPE	
		SYNTAX			Counter64
		MAX-ACCESS		read-only
		STATUS			current
		DESCRIPTION		"Description"
		::=  {  nptPmGE25PortTotalEntry  13  }


	nptPmGE25PortTotalRxPkts1023	OBJECT-TYPE	
		SYNTAX			Counter64
		MAX-ACCESS		read-only
		STATUS			current
		DESCRIPTION		"Description"
		::=  {  nptPmGE25PortTotalEntry  14  }


	nptPmGE25PortTotalRxPktsMtu	OBJECT-TYPE	
		SYNTAX			Counter64
		MAX-ACCESS		read-only
		STATUS			current
		DESCRIPTION		"Description"
		::=  {  nptPmGE25PortTotalEntry  15  }


	nptPmGE25PortTotalRxUndersizePkts	OBJECT-TYPE	
		SYNTAX			Counter64
		MAX-ACCESS		read-only
		STATUS			current
		DESCRIPTION		"Description"
		::=  {  nptPmGE25PortTotalEntry  16  }


	nptPmGE25PortTotalRxOversizePkts	OBJECT-TYPE	
		SYNTAX			Counter64
		MAX-ACCESS		read-only
		STATUS			current
		DESCRIPTION		"Description"
		::=  {  nptPmGE25PortTotalEntry  17  }


	nptPmGE25PortTotalRxPausePkts	OBJECT-TYPE	
		SYNTAX			Counter64
		MAX-ACCESS		read-only
		STATUS			current
		DESCRIPTION		"Description"
		::=  {  nptPmGE25PortTotalEntry  18  }
		
	nptPmGE25PortTotalRxJabberPkts	OBJECT-TYPE	
		SYNTAX			Counter64
		MAX-ACCESS		read-only
		STATUS			current
		DESCRIPTION		"Description"
		::=  {  nptPmGE25PortTotalEntry  19  }


	nptPmGE25PortTotalRxCRCAlignErrorPkts	OBJECT-TYPE	
		SYNTAX			Counter64
		MAX-ACCESS		read-only
		STATUS			current
		DESCRIPTION		"Description"
		::=  {  nptPmGE25PortTotalEntry  20  }


	nptPmGE25PortTotalRxFragments	OBJECT-TYPE	
		SYNTAX			Counter64
		MAX-ACCESS		read-only
		STATUS			current
		DESCRIPTION		"Description"
		::=  {  nptPmGE25PortTotalEntry  21  }


	nptPmGE25PortTotalCollisionErrors	OBJECT-TYPE	
		SYNTAX			Counter64
		MAX-ACCESS		read-only
		STATUS			current
		DESCRIPTION		"Description"
		::=  {  nptPmGE25PortTotalEntry  22  }


	nptPmGE25PortTotalPCSLCV	OBJECT-TYPE	
		SYNTAX			Counter64
		MAX-ACCESS		read-only
		STATUS			current
		DESCRIPTION		"Description"
		::=  {  nptPmGE25PortTotalEntry  23  }


	nptPmGE25PortTotalPCSES	OBJECT-TYPE	
		SYNTAX			Counter64
		MAX-ACCESS		read-only
		STATUS			current
		DESCRIPTION		"Description"
		::=  {  nptPmGE25PortTotalEntry  24  }


	nptPmGE25PortTotalPCSSES	OBJECT-TYPE	
		SYNTAX			Counter64
		MAX-ACCESS		read-only
		STATUS			current
		DESCRIPTION		"Description"
		::=  {  nptPmGE25PortTotalEntry  25  }


	nptPmGE25PortTotalPCSUAS	OBJECT-TYPE	
		SYNTAX			Counter64
		MAX-ACCESS		read-only
		STATUS			current
		DESCRIPTION		"Description"
		::=  {  nptPmGE25PortTotalEntry  26  }
		
	nptPmGE25PortTotalFECCE	OBJECT-TYPE	
		SYNTAX			Counter64
		MAX-ACCESS		read-only
		STATUS			current
		DESCRIPTION		"Description"
		::=  {  nptPmGE25PortTotalEntry  27  }


	nptPmGE25PortTotalFECUCE	OBJECT-TYPE	
		SYNTAX			Counter64
		MAX-ACCESS		read-only
		STATUS			current
		DESCRIPTION		"Description"
		::=  {  nptPmGE25PortTotalEntry  28  }


	nptPmGE25PortTotalPREFECBER	OBJECT-TYPE	
		SYNTAX			Counter64
		MAX-ACCESS		read-only
		STATUS			current
		DESCRIPTION		"Description"
		::=  {  nptPmGE25PortTotalEntry  29  }


	nptPmGE25PortTotalINMaximumRate	OBJECT-TYPE	
		SYNTAX			Counter64
		MAX-ACCESS		read-only
		STATUS			current
		DESCRIPTION		"Description"
		::=  {  nptPmGE25PortTotalEntry  30  }
		
	nptPmGE25PortTotalINAverageRate	OBJECT-TYPE	
		SYNTAX			Counter64
		MAX-ACCESS		read-only
		STATUS			current
		DESCRIPTION		"Description"
		::=  {  nptPmGE25PortTotalEntry  31  }
		
	nptPmGE25PortTotalINTotalRate	OBJECT-TYPE	
		SYNTAX			Counter64
		MAX-ACCESS		read-only
		STATUS			current
		DESCRIPTION		"Description"
		::=  {  nptPmGE25PortTotalEntry  32  }
		
	nptPmGE25PortTotalINMaximumPPS	OBJECT-TYPE	
		SYNTAX			Counter64
		MAX-ACCESS		read-only
		STATUS			current
		DESCRIPTION		"Description"
		::=  {  nptPmGE25PortTotalEntry  33  }
		
	nptPmGE25PortTotalINAveragePPS	OBJECT-TYPE	
		SYNTAX			Counter64
		MAX-ACCESS		read-only
		STATUS			current
		DESCRIPTION		"Description"
		::=  {  nptPmGE25PortTotalEntry  34  }
		
	nptPmGE25PortTotalINTotalPPS	OBJECT-TYPE	
		SYNTAX			Counter64
		MAX-ACCESS		read-only
		STATUS			current
		DESCRIPTION		"Description"
		::=  {  nptPmGE25PortTotalEntry  35  }
		
	nptPmGE25PortTotalINMaximumUtilization	OBJECT-TYPE	
		SYNTAX			Counter64
		MAX-ACCESS		read-only
		STATUS			current
		DESCRIPTION		"Description"
		::=  {  nptPmGE25PortTotalEntry  36  }
		
	nptPmGE25PortTotalINAverageUtilization	OBJECT-TYPE	
		SYNTAX			Counter64
		MAX-ACCESS		read-only
		STATUS			current
		DESCRIPTION		"Description"
		::=  {  nptPmGE25PortTotalEntry  37  }
		
	nptPmGE25PortTotalINTotalUtilization	OBJECT-TYPE	
		SYNTAX			Counter64
		MAX-ACCESS		read-only
		STATUS			current
		DESCRIPTION		"Description"
		::=  {  nptPmGE25PortTotalEntry  38  }
		
	nptPmGE25PortTotalOUTMaximumRate	OBJECT-TYPE	
		SYNTAX			Counter64
		MAX-ACCESS		read-only
		STATUS			current
		DESCRIPTION		"Description"
		::=  {  nptPmGE25PortTotalEntry  39  }
		
	nptPmGE25PortTotalOUTAverageRate	OBJECT-TYPE	
		SYNTAX			Counter64
		MAX-ACCESS		read-only
		STATUS			current
		DESCRIPTION		"Description"
		::=  {  nptPmGE25PortTotalEntry  40  }
		
	nptPmGE25PortTotalOUTTotalRate	OBJECT-TYPE	
		SYNTAX			Counter64
		MAX-ACCESS		read-only
		STATUS			current
		DESCRIPTION		"Description"
		::=  {  nptPmGE25PortTotalEntry  41  }
		
	nptPmGE25PortTotalOUTMaximumPPS	OBJECT-TYPE	
		SYNTAX			Counter64
		MAX-ACCESS		read-only
		STATUS			current
		DESCRIPTION		"Description"
		::=  {  nptPmGE25PortTotalEntry  42  }
		
	nptPmGE25PortTotalOUTAveragePPS	OBJECT-TYPE	
		SYNTAX			Counter64
		MAX-ACCESS		read-only
		STATUS			current
		DESCRIPTION		"Description"
		::=  {  nptPmGE25PortTotalEntry  43  }
		
	nptPmGE25PortTotalOUTTotalPPS	OBJECT-TYPE	
		SYNTAX			Counter64
		MAX-ACCESS		read-only
		STATUS			current
		DESCRIPTION		"Description"
		::=  {  nptPmGE25PortTotalEntry  44  }
		
	nptPmGE25PortTotalOUTMaximumUtilization	OBJECT-TYPE	
		SYNTAX			Counter64
		MAX-ACCESS		read-only
		STATUS			current
		DESCRIPTION		"Description"
		::=  {  nptPmGE25PortTotalEntry  45  }
		
	nptPmGE25PortTotalOUTAverageUtilization	OBJECT-TYPE	
		SYNTAX			Counter64
		MAX-ACCESS		read-only
		STATUS			current
		DESCRIPTION		"Description"
		::=  {  nptPmGE25PortTotalEntry  46  }
		
	nptPmGE25PortTotalOUTTotalUtilization	OBJECT-TYPE	
		SYNTAX			Counter64
		MAX-ACCESS		read-only
		STATUS			current
		DESCRIPTION		"Description"
		::=  {  nptPmGE25PortTotalEntry  47  }
		
	nptPmGE25PortTotalLinkDownSeconds	OBJECT-TYPE	
		SYNTAX			Counter64
		MAX-ACCESS		read-only
		STATUS			current
		DESCRIPTION		"Description"
		::=  {  nptPmGE25PortTotalEntry  48  }
		
	nptPmGE25PortTotalOSNRMax	OBJECT-TYPE	
		SYNTAX			DisplayString
		MAX-ACCESS		read-only
		STATUS			current
		DESCRIPTION		"Description"
		::=  {  nptPmGE25PortTotalEntry  49  }
		
	nptPmGE25PortTotalOSNRMin	OBJECT-TYPE	
		SYNTAX			DisplayString
		MAX-ACCESS		read-only
		STATUS			current
		DESCRIPTION		"Description"
		::=  {  nptPmGE25PortTotalEntry  50  }
               
	nptPmGE25PortTotalMaxRxPower	OBJECT-TYPE	
		SYNTAX			DisplayString
		MAX-ACCESS		read-only
		STATUS			current
		DESCRIPTION		"Description"
		::=  {  nptPmGE25PortTotalEntry  51  }
		
	nptPmGE25PortTotalMinRxPower	OBJECT-TYPE	
		SYNTAX			DisplayString
		MAX-ACCESS		read-only
		STATUS			current
		DESCRIPTION		"Description"
		::=  {  nptPmGE25PortTotalEntry  52  }
        
	nptPmGE25PortTotalTxPower	OBJECT-TYPE	
		SYNTAX			DisplayString
		MAX-ACCESS		read-only
		STATUS			current
		DESCRIPTION		"Description"
		::=  {  nptPmGE25PortTotalEntry  53  }	
        
	nptPmGE50PortCurrentTable	OBJECT-TYPE
		SYNTAX		SEQUENCE  OF  NptPmGE50PortCurrentEntry
		MAX-ACCESS	not-accessible
		STATUS		current
		DESCRIPTION	"Description"
		::=  { nptPmGE50Port  1 }

	nptPmGE50PortCurrentEntry	OBJECT-TYPE
		SYNTAX		NptPmGE50PortCurrentEntry
		MAX-ACCESS	not-accessible
		STATUS		current
		DESCRIPTION	"Row Description"
		INDEX		{  nptPmGE50PortCurrentIndex  }
		::=  { nptPmGE50PortCurrentTable 1 }

	NptPmGE50PortCurrentEntry  ::=  SEQUENCE {
	    nptPmGE50PortCurrentIndex  Integer32,
		nptPmGE50PortCurrentMoDescription  DisplayString,
	    nptPmGE50PortCurrentRxOctets  Counter64,
		nptPmGE50PortCurrentRxPkts  Counter64,
		nptPmGE50PortCurrentRxBroadcastPkts  Counter64,
		nptPmGE50PortCurrentRxMulticastPkts  Counter64,
		nptPmGE50PortCurrentTxOctets  Counter64,
		nptPmGE50PortCurrentTxPkts  Counter64,
		nptPmGE50PortCurrentRxErrorPkts  Counter64,
		nptPmGE50PortCurrentRxPkts64  Counter64,
		nptPmGE50PortCurrentRxPkts127  Counter64,
		nptPmGE50PortCurrentRxPkts255  Counter64,
		nptPmGE50PortCurrentRxPkts511  Counter64,
		nptPmGE50PortCurrentRxPkts1023  Counter64,
		nptPmGE50PortCurrentRxPktsMtu  Counter64,
		nptPmGE50PortCurrentRxUndersizePkts  Counter64,
		nptPmGE50PortCurrentRxOversizePkts  Counter64,
		nptPmGE50PortCurrentRxPausePkts  Counter64,
		nptPmGE50PortCurrentRxJabberPkts  Counter64,
		nptPmGE50PortCurrentRxCRCAlignErrorPkts  Counter64,
		nptPmGE50PortCurrentRxFragments  Counter64,
		nptPmGE50PortCurrentCollisionErrors  Counter64,
		nptPmGE50PortCurrentPCSLCV  Counter64,
		nptPmGE50PortCurrentPCSES  Counter64,
		nptPmGE50PortCurrentPCSSES  Counter64,
		nptPmGE50PortCurrentPCSUAS  Counter64,
		nptPmGE50PortCurrentFECCE  Counter64,
		nptPmGE50PortCurrentFECUCE  Counter64,
		nptPmGE50PortCurrentPREFECBER  Counter64,
		nptPmGE50PortCurrentINMaximumRate  Counter64,
		nptPmGE50PortCurrentINAverageRate  Counter64,
		nptPmGE50PortCurrentINCurrentRate  Counter64,
		nptPmGE50PortCurrentINMaximumPPS  Counter64,
		nptPmGE50PortCurrentINAveragePPS  Counter64,
		nptPmGE50PortCurrentINCurrentPPS  Counter64,
		nptPmGE50PortCurrentINMaximumUtilization  Counter64,
		nptPmGE50PortCurrentINAverageUtilization  Counter64,
		nptPmGE50PortCurrentINCurrentUtilization  Counter64,
		nptPmGE50PortCurrentOUTMaximumRate  Counter64,
		nptPmGE50PortCurrentOUTAverageRate  Counter64,
		nptPmGE50PortCurrentOUTCurrentRate  Counter64,
		nptPmGE50PortCurrentOUTMaximumPPS  Counter64,
		nptPmGE50PortCurrentOUTAveragePPS  Counter64,
		nptPmGE50PortCurrentOUTCurrentPPS  Counter64,
		nptPmGE50PortCurrentOUTMaximumUtilization  Counter64,
		nptPmGE50PortCurrentOUTAverageUtilization  Counter64,
		nptPmGE50PortCurrentOUTCurrentUtilization  Counter64,
		nptPmGE50PortCurrentLinkDownSeconds  Counter64,
		nptPmGE50PortCurrentOSNRMax  DisplayString,
		nptPmGE50PortCurrentOSNRMin  DisplayString,
		nptPmGE50PortCurrentMaxRxPower  DisplayString,
		nptPmGE50PortCurrentMinRxPower  DisplayString,
        nptPmGE50PortCurrentTxPower  DisplayString
		}


	nptPmGE50PortCurrentIndex	OBJECT-TYPE	
		SYNTAX			Integer32  ( -2147483648 .. 2147483647  ) 
		MAX-ACCESS		read-only
		STATUS			current
		DESCRIPTION		"Column Description"
		::=  {  nptPmGE50PortCurrentEntry  1  }
		
	nptPmGE50PortCurrentMoDescription	OBJECT-TYPE	
		SYNTAX			DisplayString 
		MAX-ACCESS		read-only
		STATUS			current
		DESCRIPTION		"Column Description"
		::=  {  nptPmGE50PortCurrentEntry  2  }


	nptPmGE50PortCurrentRxOctets	OBJECT-TYPE	
		SYNTAX			Counter64
		MAX-ACCESS		read-only
		STATUS			current
		DESCRIPTION		"Column Description"
		::=  {  nptPmGE50PortCurrentEntry  3  }


	nptPmGE50PortCurrentRxPkts	OBJECT-TYPE	
		SYNTAX			Counter64
		MAX-ACCESS		read-only
		STATUS			current
		DESCRIPTION		"Description"
		::=  {  nptPmGE50PortCurrentEntry  4  }


	nptPmGE50PortCurrentRxBroadcastPkts	OBJECT-TYPE	
		SYNTAX			Counter64
		MAX-ACCESS		read-only
		STATUS			current
		DESCRIPTION		"Description"
		::=  {  nptPmGE50PortCurrentEntry  5  }


	nptPmGE50PortCurrentRxMulticastPkts	OBJECT-TYPE	
		SYNTAX			Counter64
		MAX-ACCESS		read-only
		STATUS			current
		DESCRIPTION		"Description"
		::=  {  nptPmGE50PortCurrentEntry  6  }


	nptPmGE50PortCurrentTxOctets	OBJECT-TYPE	
		SYNTAX			Counter64
		MAX-ACCESS		read-only
		STATUS			current
		DESCRIPTION		"Description"
		::=  {  nptPmGE50PortCurrentEntry  7  }


	nptPmGE50PortCurrentTxPkts	OBJECT-TYPE	
		SYNTAX			Counter64
		MAX-ACCESS		read-only
		STATUS			current
		DESCRIPTION		"Description"
		::=  {  nptPmGE50PortCurrentEntry  8  }


	nptPmGE50PortCurrentRxErrorPkts	OBJECT-TYPE	
		SYNTAX			Counter64
		MAX-ACCESS		read-only
		STATUS			current
		DESCRIPTION		"Description"
		::=  {  nptPmGE50PortCurrentEntry  9  }


	nptPmGE50PortCurrentRxPkts64	OBJECT-TYPE	
		SYNTAX			Counter64
		MAX-ACCESS		read-only
		STATUS			current
		DESCRIPTION		"Description"
		::=  {  nptPmGE50PortCurrentEntry  10  }


	nptPmGE50PortCurrentRxPkts127	OBJECT-TYPE	
		SYNTAX			Counter64
		MAX-ACCESS		read-only
		STATUS			current
		DESCRIPTION		"Description"
		::=  {  nptPmGE50PortCurrentEntry  11  }


	nptPmGE50PortCurrentRxPkts255	OBJECT-TYPE	
		SYNTAX			Counter64
		MAX-ACCESS		read-only
		STATUS			current
		DESCRIPTION		"Description"
		::=  {  nptPmGE50PortCurrentEntry  12  }


	nptPmGE50PortCurrentRxPkts511	OBJECT-TYPE	
		SYNTAX			Counter64
		MAX-ACCESS		read-only
		STATUS			current
		DESCRIPTION		"Description"
		::=  {  nptPmGE50PortCurrentEntry  13  }


	nptPmGE50PortCurrentRxPkts1023	OBJECT-TYPE	
		SYNTAX			Counter64
		MAX-ACCESS		read-only
		STATUS			current
		DESCRIPTION		"Description"
		::=  {  nptPmGE50PortCurrentEntry  14  }


	nptPmGE50PortCurrentRxPktsMtu	OBJECT-TYPE	
		SYNTAX			Counter64
		MAX-ACCESS		read-only
		STATUS			current
		DESCRIPTION		"Description"
		::=  {  nptPmGE50PortCurrentEntry  15  }


	nptPmGE50PortCurrentRxUndersizePkts	OBJECT-TYPE	
		SYNTAX			Counter64
		MAX-ACCESS		read-only
		STATUS			current
		DESCRIPTION		"Description"
		::=  {  nptPmGE50PortCurrentEntry  16  }


	nptPmGE50PortCurrentRxOversizePkts	OBJECT-TYPE	
		SYNTAX			Counter64
		MAX-ACCESS		read-only
		STATUS			current
		DESCRIPTION		"Description"
		::=  {  nptPmGE50PortCurrentEntry  17  }


	nptPmGE50PortCurrentRxPausePkts	OBJECT-TYPE	
		SYNTAX			Counter64
		MAX-ACCESS		read-only
		STATUS			current
		DESCRIPTION		"Description"
		::=  {  nptPmGE50PortCurrentEntry  18  }
		
	nptPmGE50PortCurrentRxJabberPkts	OBJECT-TYPE	
		SYNTAX			Counter64
		MAX-ACCESS		read-only
		STATUS			current
		DESCRIPTION		"Description"
		::=  {  nptPmGE50PortCurrentEntry  19  }


	nptPmGE50PortCurrentRxCRCAlignErrorPkts	OBJECT-TYPE	
		SYNTAX			Counter64
		MAX-ACCESS		read-only
		STATUS			current
		DESCRIPTION		"Description"
		::=  {  nptPmGE50PortCurrentEntry  20  }


	nptPmGE50PortCurrentRxFragments	OBJECT-TYPE	
		SYNTAX			Counter64
		MAX-ACCESS		read-only
		STATUS			current
		DESCRIPTION		"Description"
		::=  {  nptPmGE50PortCurrentEntry  21  }


	nptPmGE50PortCurrentCollisionErrors	OBJECT-TYPE	
		SYNTAX			Counter64
		MAX-ACCESS		read-only
		STATUS			current
		DESCRIPTION		"Description"
		::=  {  nptPmGE50PortCurrentEntry  22  }


	nptPmGE50PortCurrentPCSLCV	OBJECT-TYPE	
		SYNTAX			Counter64
		MAX-ACCESS		read-only
		STATUS			current
		DESCRIPTION		"Description"
		::=  {  nptPmGE50PortCurrentEntry  23  }
		


	nptPmGE50PortCurrentPCSES	OBJECT-TYPE	
		SYNTAX			Counter64
		MAX-ACCESS		read-only
		STATUS			current
		DESCRIPTION		"Description"
		::=  {  nptPmGE50PortCurrentEntry  24  }


	nptPmGE50PortCurrentPCSSES	OBJECT-TYPE	
		SYNTAX			Counter64
		MAX-ACCESS		read-only
		STATUS			current
		DESCRIPTION		"Description"
		::=  {  nptPmGE50PortCurrentEntry  25  }


	nptPmGE50PortCurrentPCSUAS	OBJECT-TYPE	
		SYNTAX			Counter64
		MAX-ACCESS		read-only
		STATUS			current
		DESCRIPTION		"Description"
		::=  {  nptPmGE50PortCurrentEntry  26  }
		
	nptPmGE50PortCurrentFECCE	OBJECT-TYPE	
		SYNTAX			Counter64
		MAX-ACCESS		read-only
		STATUS			current
		DESCRIPTION		"Description"
		::=  {  nptPmGE50PortCurrentEntry  27  }


	nptPmGE50PortCurrentFECUCE	OBJECT-TYPE	
		SYNTAX			Counter64
		MAX-ACCESS		read-only
		STATUS			current
		DESCRIPTION		"Description"
		::=  {  nptPmGE50PortCurrentEntry  28  }


	nptPmGE50PortCurrentPREFECBER	OBJECT-TYPE	
		SYNTAX			Counter64
		MAX-ACCESS		read-only
		STATUS			current
		DESCRIPTION		"Description"
		::=  {  nptPmGE50PortCurrentEntry  29  }


	nptPmGE50PortCurrentINMaximumRate	OBJECT-TYPE	
		SYNTAX			Counter64
		MAX-ACCESS		read-only
		STATUS			current
		DESCRIPTION		"Description"
		::=  {  nptPmGE50PortCurrentEntry  30  }
		
	nptPmGE50PortCurrentINAverageRate	OBJECT-TYPE	
		SYNTAX			Counter64
		MAX-ACCESS		read-only
		STATUS			current
		DESCRIPTION		"Description"
		::=  {  nptPmGE50PortCurrentEntry  31  }
		
	nptPmGE50PortCurrentINCurrentRate	OBJECT-TYPE	
		SYNTAX			Counter64
		MAX-ACCESS		read-only
		STATUS			current
		DESCRIPTION		"Description"
		::=  {  nptPmGE50PortCurrentEntry  32  }
		
	nptPmGE50PortCurrentINMaximumPPS	OBJECT-TYPE	
		SYNTAX			Counter64
		MAX-ACCESS		read-only
		STATUS			current
		DESCRIPTION		"Description"
		::=  {  nptPmGE50PortCurrentEntry  33  }
		
	nptPmGE50PortCurrentINAveragePPS	OBJECT-TYPE	
		SYNTAX			Counter64
		MAX-ACCESS		read-only
		STATUS			current
		DESCRIPTION		"Description"
		::=  {  nptPmGE50PortCurrentEntry  34  }
		
	nptPmGE50PortCurrentINCurrentPPS	OBJECT-TYPE	
		SYNTAX			Counter64
		MAX-ACCESS		read-only
		STATUS			current
		DESCRIPTION		"Description"
		::=  {  nptPmGE50PortCurrentEntry  35  }
		
	nptPmGE50PortCurrentINMaximumUtilization	OBJECT-TYPE	
		SYNTAX			Counter64
		MAX-ACCESS		read-only
		STATUS			current
		DESCRIPTION		"Description"
		::=  {  nptPmGE50PortCurrentEntry  36  }
		
	nptPmGE50PortCurrentINAverageUtilization	OBJECT-TYPE	
		SYNTAX			Counter64
		MAX-ACCESS		read-only
		STATUS			current
		DESCRIPTION		"Description"
		::=  {  nptPmGE50PortCurrentEntry  37  }
		
	nptPmGE50PortCurrentINCurrentUtilization	OBJECT-TYPE	
		SYNTAX			Counter64
		MAX-ACCESS		read-only
		STATUS			current
		DESCRIPTION		"Description"
		::=  {  nptPmGE50PortCurrentEntry  38  }
		
	nptPmGE50PortCurrentOUTMaximumRate	OBJECT-TYPE	
		SYNTAX			Counter64
		MAX-ACCESS		read-only
		STATUS			current
		DESCRIPTION		"Description"
		::=  {  nptPmGE50PortCurrentEntry  39  }
		
	nptPmGE50PortCurrentOUTAverageRate	OBJECT-TYPE	
		SYNTAX			Counter64
		MAX-ACCESS		read-only
		STATUS			current
		DESCRIPTION		"Description"
		::=  {  nptPmGE50PortCurrentEntry  40  }
		
	nptPmGE50PortCurrentOUTCurrentRate	OBJECT-TYPE	
		SYNTAX			Counter64
		MAX-ACCESS		read-only
		STATUS			current
		DESCRIPTION		"Description"
		::=  {  nptPmGE50PortCurrentEntry  41  }
		
	nptPmGE50PortCurrentOUTMaximumPPS	OBJECT-TYPE	
		SYNTAX			Counter64
		MAX-ACCESS		read-only
		STATUS			current
		DESCRIPTION		"Description"
		::=  {  nptPmGE50PortCurrentEntry  42  }
		
	nptPmGE50PortCurrentOUTAveragePPS	OBJECT-TYPE	
		SYNTAX			Counter64
		MAX-ACCESS		read-only
		STATUS			current
		DESCRIPTION		"Description"
		::=  {  nptPmGE50PortCurrentEntry  43  }
		
	nptPmGE50PortCurrentOUTCurrentPPS	OBJECT-TYPE	
		SYNTAX			Counter64
		MAX-ACCESS		read-only
		STATUS			current
		DESCRIPTION		"Description"
		::=  {  nptPmGE50PortCurrentEntry  44  }
		
	nptPmGE50PortCurrentOUTMaximumUtilization	OBJECT-TYPE	
		SYNTAX			Counter64
		MAX-ACCESS		read-only
		STATUS			current
		DESCRIPTION		"Description"
		::=  {  nptPmGE50PortCurrentEntry  45  }
		
	nptPmGE50PortCurrentOUTAverageUtilization	OBJECT-TYPE	
		SYNTAX			Counter64
		MAX-ACCESS		read-only
		STATUS			current
		DESCRIPTION		"Description"
		::=  {  nptPmGE50PortCurrentEntry  46  }
		
	nptPmGE50PortCurrentOUTCurrentUtilization	OBJECT-TYPE	
		SYNTAX			Counter64
		MAX-ACCESS		read-only
		STATUS			current
		DESCRIPTION		"Description"
		::=  {  nptPmGE50PortCurrentEntry  47  }
		
	nptPmGE50PortCurrentLinkDownSeconds	OBJECT-TYPE	
		SYNTAX			Counter64
		MAX-ACCESS		read-only
		STATUS			current
		DESCRIPTION		"Description"
		::=  {  nptPmGE50PortCurrentEntry  48  }
		
	nptPmGE50PortCurrentOSNRMax	OBJECT-TYPE	
		SYNTAX			DisplayString
		MAX-ACCESS		read-only
		STATUS			current
		DESCRIPTION		"Description"
		::=  {  nptPmGE50PortCurrentEntry  49  }
		
	nptPmGE50PortCurrentOSNRMin	OBJECT-TYPE	
		SYNTAX			DisplayString
		MAX-ACCESS		read-only
		STATUS			current
		DESCRIPTION		"Description"
		::=  {  nptPmGE50PortCurrentEntry  50  }
               
	nptPmGE50PortCurrentMaxRxPower	OBJECT-TYPE	
		SYNTAX			DisplayString
		MAX-ACCESS		read-only
		STATUS			current
		DESCRIPTION		"Description"
		::=  {  nptPmGE50PortCurrentEntry  51  }
		
	nptPmGE50PortCurrentMinRxPower	OBJECT-TYPE	
		SYNTAX			DisplayString
		MAX-ACCESS		read-only
		STATUS			current
		DESCRIPTION		"Description"
		::=  {  nptPmGE50PortCurrentEntry  52  }
        
	nptPmGE50PortCurrentTxPower	OBJECT-TYPE	
		SYNTAX			DisplayString
		MAX-ACCESS		read-only
		STATUS			current
		DESCRIPTION		"Description"
		::=  {  nptPmGE50PortCurrentEntry  53  }	
		
	nptPmGE50PortTotalTable	OBJECT-TYPE
		SYNTAX		SEQUENCE  OF  NptPmGE50PortTotalEntry
		MAX-ACCESS	not-accessible
		STATUS		current
		DESCRIPTION	"Description"
		::=  { nptPmGE50Port  2 }

	nptPmGE50PortTotalEntry	OBJECT-TYPE
		SYNTAX		NptPmGE50PortTotalEntry
		MAX-ACCESS	not-accessible
		STATUS		current
		DESCRIPTION	"Row Description"
		INDEX		{  nptPmGE50PortTotalIndex  }
		::=  { nptPmGE50PortTotalTable 1 }

	NptPmGE50PortTotalEntry  ::=  SEQUENCE {
	    nptPmGE50PortTotalIndex  Integer32,
		nptPmGE50PortTotalMoDescription  DisplayString,
	    nptPmGE50PortTotalRxOctets  Counter64,
		nptPmGE50PortTotalRxPkts  Counter64,
		nptPmGE50PortTotalRxBroadcastPkts  Counter64,
		nptPmGE50PortTotalRxMulticastPkts  Counter64,
		nptPmGE50PortTotalTxOctets  Counter64,
		nptPmGE50PortTotalTxPkts  Counter64,
		nptPmGE50PortTotalRxErrorPkts  Counter64,
		nptPmGE50PortTotalRxPkts64  Counter64,
		nptPmGE50PortTotalRxPkts127  Counter64,
		nptPmGE50PortTotalRxPkts255  Counter64,
		nptPmGE50PortTotalRxPkts511  Counter64,
		nptPmGE50PortTotalRxPkts1023  Counter64,
		nptPmGE50PortTotalRxPktsMtu  Counter64,
		nptPmGE50PortTotalRxUndersizePkts  Counter64,
		nptPmGE50PortTotalRxOversizePkts  Counter64,
		nptPmGE50PortTotalRxPausePkts  Counter64,
		nptPmGE50PortTotalRxJabberPkts  Counter64,
		nptPmGE50PortTotalRxCRCAlignErrorPkts  Counter64,
		nptPmGE50PortTotalRxFragments  Counter64,
		nptPmGE50PortTotalCollisionErrors  Counter64,
		nptPmGE50PortTotalPCSLCV  Counter64,
		nptPmGE50PortTotalPCSES  Counter64,
		nptPmGE50PortTotalPCSSES  Counter64,
		nptPmGE50PortTotalPCSUAS  Counter64,
		nptPmGE50PortTotalFECCE  Counter64,
		nptPmGE50PortTotalFECUCE  Counter64,
		nptPmGE50PortTotalPREFECBER  Counter64,
		nptPmGE50PortTotalINMaximumRate  Counter64,
		nptPmGE50PortTotalINAverageRate  Counter64,
		nptPmGE50PortTotalINTotalRate  Counter64,
		nptPmGE50PortTotalINMaximumPPS  Counter64,
		nptPmGE50PortTotalINAveragePPS  Counter64,
		nptPmGE50PortTotalINTotalPPS  Counter64,
		nptPmGE50PortTotalINMaximumUtilization  Counter64,
		nptPmGE50PortTotalINAverageUtilization  Counter64,
		nptPmGE50PortTotalINTotalUtilization  Counter64,
		nptPmGE50PortTotalOUTMaximumRate  Counter64,
		nptPmGE50PortTotalOUTAverageRate  Counter64,
		nptPmGE50PortTotalOUTTotalRate  Counter64,
		nptPmGE50PortTotalOUTMaximumPPS  Counter64,
		nptPmGE50PortTotalOUTAveragePPS  Counter64,
		nptPmGE50PortTotalOUTTotalPPS  Counter64,
		nptPmGE50PortTotalOUTMaximumUtilization  Counter64,
		nptPmGE50PortTotalOUTAverageUtilization  Counter64,
		nptPmGE50PortTotalOUTTotalUtilization  Counter64,
		nptPmGE50PortTotalLinkDownSeconds  Counter64,
		nptPmGE50PortTotalOSNRMax  DisplayString,
		nptPmGE50PortTotalOSNRMin  DisplayString,
		nptPmGE50PortTotalMaxRxPower  DisplayString,
		nptPmGE50PortTotalMinRxPower  DisplayString,
        nptPmGE50PortTotalTxPower  DisplayString
		}


	nptPmGE50PortTotalIndex	OBJECT-TYPE	
		SYNTAX			Integer32  ( -2147483648 .. 2147483647  ) 
		MAX-ACCESS		read-only
		STATUS			current
		DESCRIPTION		"Column Description"
		::=  {  nptPmGE50PortTotalEntry  1  }
	
	
	nptPmGE50PortTotalMoDescription	OBJECT-TYPE	
		SYNTAX			DisplayString 
		MAX-ACCESS		read-only
		STATUS			current
		DESCRIPTION		"Column Description"
		::=  {  nptPmGE50PortTotalEntry  2  }


	nptPmGE50PortTotalRxOctets	OBJECT-TYPE	
		SYNTAX			Counter64
		MAX-ACCESS		read-only
		STATUS			current
		DESCRIPTION		"Column Description"
		::=  {  nptPmGE50PortTotalEntry  3  }


	nptPmGE50PortTotalRxPkts	OBJECT-TYPE	
		SYNTAX			Counter64
		MAX-ACCESS		read-only
		STATUS			current
		DESCRIPTION		"Description"
		::=  {  nptPmGE50PortTotalEntry  4  }


	nptPmGE50PortTotalRxBroadcastPkts	OBJECT-TYPE	
		SYNTAX			Counter64
		MAX-ACCESS		read-only
		STATUS			current
		DESCRIPTION		"Description"
		::=  {  nptPmGE50PortTotalEntry  5  }


	nptPmGE50PortTotalRxMulticastPkts	OBJECT-TYPE	
		SYNTAX			Counter64
		MAX-ACCESS		read-only
		STATUS			current
		DESCRIPTION		"Description"
		::=  {  nptPmGE50PortTotalEntry  6  }


	nptPmGE50PortTotalTxOctets	OBJECT-TYPE	
		SYNTAX			Counter64
		MAX-ACCESS		read-only
		STATUS			current
		DESCRIPTION		"Description"
		::=  {  nptPmGE50PortTotalEntry  7  }


	nptPmGE50PortTotalTxPkts	OBJECT-TYPE	
		SYNTAX			Counter64
		MAX-ACCESS		read-only
		STATUS			current
		DESCRIPTION		"Description"
		::=  {  nptPmGE50PortTotalEntry  8  }


	nptPmGE50PortTotalRxErrorPkts	OBJECT-TYPE	
		SYNTAX			Counter64
		MAX-ACCESS		read-only
		STATUS			current
		DESCRIPTION		"Description"
		::=  {  nptPmGE50PortTotalEntry  9  }


	nptPmGE50PortTotalRxPkts64	OBJECT-TYPE	
		SYNTAX			Counter64
		MAX-ACCESS		read-only
		STATUS			current
		DESCRIPTION		"Description"
		::=  {  nptPmGE50PortTotalEntry  10  }


	nptPmGE50PortTotalRxPkts127	OBJECT-TYPE	
		SYNTAX			Counter64
		MAX-ACCESS		read-only
		STATUS			current
		DESCRIPTION		"Description"
		::=  {  nptPmGE50PortTotalEntry  11  }


	nptPmGE50PortTotalRxPkts255	OBJECT-TYPE	
		SYNTAX			Counter64
		MAX-ACCESS		read-only
		STATUS			current
		DESCRIPTION		"Description"
		::=  {  nptPmGE50PortTotalEntry  12  }


	nptPmGE50PortTotalRxPkts511	OBJECT-TYPE	
		SYNTAX			Counter64
		MAX-ACCESS		read-only
		STATUS			current
		DESCRIPTION		"Description"
		::=  {  nptPmGE50PortTotalEntry  13  }


	nptPmGE50PortTotalRxPkts1023	OBJECT-TYPE	
		SYNTAX			Counter64
		MAX-ACCESS		read-only
		STATUS			current
		DESCRIPTION		"Description"
		::=  {  nptPmGE50PortTotalEntry  14  }


	nptPmGE50PortTotalRxPktsMtu	OBJECT-TYPE	
		SYNTAX			Counter64
		MAX-ACCESS		read-only
		STATUS			current
		DESCRIPTION		"Description"
		::=  {  nptPmGE50PortTotalEntry  15  }


	nptPmGE50PortTotalRxUndersizePkts	OBJECT-TYPE	
		SYNTAX			Counter64
		MAX-ACCESS		read-only
		STATUS			current
		DESCRIPTION		"Description"
		::=  {  nptPmGE50PortTotalEntry  16  }


	nptPmGE50PortTotalRxOversizePkts	OBJECT-TYPE	
		SYNTAX			Counter64
		MAX-ACCESS		read-only
		STATUS			current
		DESCRIPTION		"Description"
		::=  {  nptPmGE50PortTotalEntry  17  }


	nptPmGE50PortTotalRxPausePkts	OBJECT-TYPE	
		SYNTAX			Counter64
		MAX-ACCESS		read-only
		STATUS			current
		DESCRIPTION		"Description"
		::=  {  nptPmGE50PortTotalEntry  18  }
		
	nptPmGE50PortTotalRxJabberPkts	OBJECT-TYPE	
		SYNTAX			Counter64
		MAX-ACCESS		read-only
		STATUS			current
		DESCRIPTION		"Description"
		::=  {  nptPmGE50PortTotalEntry  19  }


	nptPmGE50PortTotalRxCRCAlignErrorPkts	OBJECT-TYPE	
		SYNTAX			Counter64
		MAX-ACCESS		read-only
		STATUS			current
		DESCRIPTION		"Description"
		::=  {  nptPmGE50PortTotalEntry  20  }


	nptPmGE50PortTotalRxFragments	OBJECT-TYPE	
		SYNTAX			Counter64
		MAX-ACCESS		read-only
		STATUS			current
		DESCRIPTION		"Description"
		::=  {  nptPmGE50PortTotalEntry  21  }


	nptPmGE50PortTotalCollisionErrors	OBJECT-TYPE	
		SYNTAX			Counter64
		MAX-ACCESS		read-only
		STATUS			current
		DESCRIPTION		"Description"
		::=  {  nptPmGE50PortTotalEntry  22  }


	nptPmGE50PortTotalPCSLCV	OBJECT-TYPE	
		SYNTAX			Counter64
		MAX-ACCESS		read-only
		STATUS			current
		DESCRIPTION		"Description"
		::=  {  nptPmGE50PortTotalEntry  23  }


	nptPmGE50PortTotalPCSES	OBJECT-TYPE	
		SYNTAX			Counter64
		MAX-ACCESS		read-only
		STATUS			current
		DESCRIPTION		"Description"
		::=  {  nptPmGE50PortTotalEntry  24  }


	nptPmGE50PortTotalPCSSES	OBJECT-TYPE	
		SYNTAX			Counter64
		MAX-ACCESS		read-only
		STATUS			current
		DESCRIPTION		"Description"
		::=  {  nptPmGE50PortTotalEntry  25  }


	nptPmGE50PortTotalPCSUAS	OBJECT-TYPE	
		SYNTAX			Counter64
		MAX-ACCESS		read-only
		STATUS			current
		DESCRIPTION		"Description"
		::=  {  nptPmGE50PortTotalEntry  26  }
		
	nptPmGE50PortTotalFECCE	OBJECT-TYPE	
		SYNTAX			Counter64
		MAX-ACCESS		read-only
		STATUS			current
		DESCRIPTION		"Description"
		::=  {  nptPmGE50PortTotalEntry  27  }


	nptPmGE50PortTotalFECUCE	OBJECT-TYPE	
		SYNTAX			Counter64
		MAX-ACCESS		read-only
		STATUS			current
		DESCRIPTION		"Description"
		::=  {  nptPmGE50PortTotalEntry  28  }


	nptPmGE50PortTotalPREFECBER	OBJECT-TYPE	
		SYNTAX			Counter64
		MAX-ACCESS		read-only
		STATUS			current
		DESCRIPTION		"Description"
		::=  {  nptPmGE50PortTotalEntry  29  }


	nptPmGE50PortTotalINMaximumRate	OBJECT-TYPE	
		SYNTAX			Counter64
		MAX-ACCESS		read-only
		STATUS			current
		DESCRIPTION		"Description"
		::=  {  nptPmGE50PortTotalEntry  30  }
		
	nptPmGE50PortTotalINAverageRate	OBJECT-TYPE	
		SYNTAX			Counter64
		MAX-ACCESS		read-only
		STATUS			current
		DESCRIPTION		"Description"
		::=  {  nptPmGE50PortTotalEntry  31  }
		
	nptPmGE50PortTotalINTotalRate	OBJECT-TYPE	
		SYNTAX			Counter64
		MAX-ACCESS		read-only
		STATUS			current
		DESCRIPTION		"Description"
		::=  {  nptPmGE50PortTotalEntry  32  }
		
	nptPmGE50PortTotalINMaximumPPS	OBJECT-TYPE	
		SYNTAX			Counter64
		MAX-ACCESS		read-only
		STATUS			current
		DESCRIPTION		"Description"
		::=  {  nptPmGE50PortTotalEntry  33  }
		
	nptPmGE50PortTotalINAveragePPS	OBJECT-TYPE	
		SYNTAX			Counter64
		MAX-ACCESS		read-only
		STATUS			current
		DESCRIPTION		"Description"
		::=  {  nptPmGE50PortTotalEntry  34  }
		
	nptPmGE50PortTotalINTotalPPS	OBJECT-TYPE	
		SYNTAX			Counter64
		MAX-ACCESS		read-only
		STATUS			current
		DESCRIPTION		"Description"
		::=  {  nptPmGE50PortTotalEntry  35  }
		
	nptPmGE50PortTotalINMaximumUtilization	OBJECT-TYPE	
		SYNTAX			Counter64
		MAX-ACCESS		read-only
		STATUS			current
		DESCRIPTION		"Description"
		::=  {  nptPmGE50PortTotalEntry  36  }
		
	nptPmGE50PortTotalINAverageUtilization	OBJECT-TYPE	
		SYNTAX			Counter64
		MAX-ACCESS		read-only
		STATUS			current
		DESCRIPTION		"Description"
		::=  {  nptPmGE50PortTotalEntry  37  }
		
	nptPmGE50PortTotalINTotalUtilization	OBJECT-TYPE	
		SYNTAX			Counter64
		MAX-ACCESS		read-only
		STATUS			current
		DESCRIPTION		"Description"
		::=  {  nptPmGE50PortTotalEntry  38  }
		
	nptPmGE50PortTotalOUTMaximumRate	OBJECT-TYPE	
		SYNTAX			Counter64
		MAX-ACCESS		read-only
		STATUS			current
		DESCRIPTION		"Description"
		::=  {  nptPmGE50PortTotalEntry  39  }
		
	nptPmGE50PortTotalOUTAverageRate	OBJECT-TYPE	
		SYNTAX			Counter64
		MAX-ACCESS		read-only
		STATUS			current
		DESCRIPTION		"Description"
		::=  {  nptPmGE50PortTotalEntry  40  }
		
	nptPmGE50PortTotalOUTTotalRate	OBJECT-TYPE	
		SYNTAX			Counter64
		MAX-ACCESS		read-only
		STATUS			current
		DESCRIPTION		"Description"
		::=  {  nptPmGE50PortTotalEntry  41  }
		
	nptPmGE50PortTotalOUTMaximumPPS	OBJECT-TYPE	
		SYNTAX			Counter64
		MAX-ACCESS		read-only
		STATUS			current
		DESCRIPTION		"Description"
		::=  {  nptPmGE50PortTotalEntry  42  }
		
	nptPmGE50PortTotalOUTAveragePPS	OBJECT-TYPE	
		SYNTAX			Counter64
		MAX-ACCESS		read-only
		STATUS			current
		DESCRIPTION		"Description"
		::=  {  nptPmGE50PortTotalEntry  43  }
		
	nptPmGE50PortTotalOUTTotalPPS	OBJECT-TYPE	
		SYNTAX			Counter64
		MAX-ACCESS		read-only
		STATUS			current
		DESCRIPTION		"Description"
		::=  {  nptPmGE50PortTotalEntry  44  }
		
	nptPmGE50PortTotalOUTMaximumUtilization	OBJECT-TYPE	
		SYNTAX			Counter64
		MAX-ACCESS		read-only
		STATUS			current
		DESCRIPTION		"Description"
		::=  {  nptPmGE50PortTotalEntry  45  }
		
	nptPmGE50PortTotalOUTAverageUtilization	OBJECT-TYPE	
		SYNTAX			Counter64
		MAX-ACCESS		read-only
		STATUS			current
		DESCRIPTION		"Description"
		::=  {  nptPmGE50PortTotalEntry  46  }
		
	nptPmGE50PortTotalOUTTotalUtilization	OBJECT-TYPE	
		SYNTAX			Counter64
		MAX-ACCESS		read-only
		STATUS			current
		DESCRIPTION		"Description"
		::=  {  nptPmGE50PortTotalEntry  47  }
		
	nptPmGE50PortTotalLinkDownSeconds	OBJECT-TYPE	
		SYNTAX			Counter64
		MAX-ACCESS		read-only
		STATUS			current
		DESCRIPTION		"Description"
		::=  {  nptPmGE50PortTotalEntry  48  }
		
	nptPmGE50PortTotalOSNRMax	OBJECT-TYPE	
		SYNTAX			DisplayString
		MAX-ACCESS		read-only
		STATUS			current
		DESCRIPTION		"Description"
		::=  {  nptPmGE50PortTotalEntry  49  }
		
	nptPmGE50PortTotalOSNRMin	OBJECT-TYPE	
		SYNTAX			DisplayString
		MAX-ACCESS		read-only
		STATUS			current
		DESCRIPTION		"Description"
		::=  {  nptPmGE50PortTotalEntry  50  }
               
	nptPmGE50PortTotalMaxRxPower	OBJECT-TYPE	
		SYNTAX			DisplayString
		MAX-ACCESS		read-only
		STATUS			current
		DESCRIPTION		"Description"
		::=  {  nptPmGE50PortTotalEntry  51  }
		
	nptPmGE50PortTotalMinRxPower	OBJECT-TYPE	
		SYNTAX			DisplayString
		MAX-ACCESS		read-only
		STATUS			current
		DESCRIPTION		"Description"
		::=  {  nptPmGE50PortTotalEntry  52  }
        
	nptPmGE50PortTotalTxPower	OBJECT-TYPE	
		SYNTAX			DisplayString
		MAX-ACCESS		read-only
		STATUS			current
		DESCRIPTION		"Description"
		::=  {  nptPmGE50PortTotalEntry  53  }	
		
		
	nptPmETPortCurrentTable	OBJECT-TYPE
		SYNTAX		SEQUENCE  OF  NptPmETPortCurrentEntry
		MAX-ACCESS	not-accessible
		STATUS		current
		DESCRIPTION	"Description"
		::=  { nptPmETPort  1 }

	nptPmETPortCurrentEntry	OBJECT-TYPE
		SYNTAX		NptPmETPortCurrentEntry
		MAX-ACCESS	not-accessible
		STATUS		current
		DESCRIPTION	"Row Description"
		INDEX		{  nptPmETPortCurrentIndex  }
		::=  { nptPmETPortCurrentTable 1 }

	NptPmETPortCurrentEntry  ::=  SEQUENCE {
	    nptPmETPortCurrentIndex  Integer32,
		nptPmETPortCurrentMoDescription  DisplayString,
	    nptPmETPortCurrentRxOctets  Counter64,
		nptPmETPortCurrentRxPkts  Counter64,
		nptPmETPortCurrentRxBroadcastPkts  Counter64,
		nptPmETPortCurrentRxMulticastPkts  Counter64,
		nptPmETPortCurrentTxOctets  Counter64,
		nptPmETPortCurrentTxPkts  Counter64,
		nptPmETPortCurrentRxErrorPkts  Counter64,
		nptPmETPortCurrentRxPkts64  Counter64,
		nptPmETPortCurrentRxPkts127  Counter64,
		nptPmETPortCurrentRxPkts255  Counter64,
		nptPmETPortCurrentRxPkts511  Counter64,
		nptPmETPortCurrentRxPkts1023  Counter64,
		nptPmETPortCurrentRxPktsMtu  Counter64,
		nptPmETPortCurrentRxUndersizePkts  Counter64,
		nptPmETPortCurrentRxOversizePkts  Counter64,
		nptPmETPortCurrentRxPausePkts  Counter64,
		nptPmETPortCurrentRxJabberPkts  Counter64,
		nptPmETPortCurrentRxCRCAlignErrorPkts  Counter64,
		nptPmETPortCurrentRxFragments  Counter64,
		nptPmETPortCurrentCollisionErrors  Counter64,
		nptPmETPortCurrentPCSLCV  Counter64,
		nptPmETPortCurrentPCSES  Counter64,
		nptPmETPortCurrentPCSSES  Counter64,
		nptPmETPortCurrentPCSUAS  Counter64,
		nptPmETPortCurrentFECCE  Counter64,
		nptPmETPortCurrentFECUCE  Counter64,
		nptPmETPortCurrentPREFECBER  Counter64,
		nptPmETPortCurrentINMaximumRate  Counter64,
		nptPmETPortCurrentINAverageRate  Counter64,
		nptPmETPortCurrentINCurrentRate  Counter64,
		nptPmETPortCurrentINMaximumPPS  Counter64,
		nptPmETPortCurrentINAveragePPS  Counter64,
		nptPmETPortCurrentINCurrentPPS  Counter64,
		nptPmETPortCurrentINMaximumUtilization  Counter64,
		nptPmETPortCurrentINAverageUtilization  Counter64,
		nptPmETPortCurrentINCurrentUtilization  Counter64,
		nptPmETPortCurrentOUTMaximumRate  Counter64,
		nptPmETPortCurrentOUTAverageRate  Counter64,
		nptPmETPortCurrentOUTCurrentRate  Counter64,
		nptPmETPortCurrentOUTMaximumPPS  Counter64,
		nptPmETPortCurrentOUTAveragePPS  Counter64,
		nptPmETPortCurrentOUTCurrentPPS  Counter64,
		nptPmETPortCurrentOUTMaximumUtilization  Counter64,
		nptPmETPortCurrentOUTAverageUtilization  Counter64,
		nptPmETPortCurrentOUTCurrentUtilization  Counter64,
		nptPmETPortCurrentLinkDownSeconds  Counter64,
		nptPmETPortCurrentOSNRMax  DisplayString,
		nptPmETPortCurrentOSNRMin  DisplayString,
		nptPmETPortCurrentMaxRxPower  DisplayString,
		nptPmETPortCurrentMinRxPower  DisplayString,
        nptPmETPortCurrentTxPower  DisplayString
		}


	nptPmETPortCurrentIndex	OBJECT-TYPE	
		SYNTAX			Integer32  ( -2147483648 .. 2147483647  ) 
		MAX-ACCESS		read-only
		STATUS			current
		DESCRIPTION		"Column Description"
		::=  {  nptPmETPortCurrentEntry  1  }
		
	nptPmETPortCurrentMoDescription	OBJECT-TYPE	
		SYNTAX			DisplayString 
		MAX-ACCESS		read-only
		STATUS			current
		DESCRIPTION		"Column Description"
		::=  {  nptPmETPortCurrentEntry  2  }


	nptPmETPortCurrentRxOctets	OBJECT-TYPE	
		SYNTAX			Counter64
		MAX-ACCESS		read-only
		STATUS			current
		DESCRIPTION		"Column Description"
		::=  {  nptPmETPortCurrentEntry  3  }


	nptPmETPortCurrentRxPkts	OBJECT-TYPE	
		SYNTAX			Counter64
		MAX-ACCESS		read-only
		STATUS			current
		DESCRIPTION		"Description"
		::=  {  nptPmETPortCurrentEntry  4  }


	nptPmETPortCurrentRxBroadcastPkts	OBJECT-TYPE	
		SYNTAX			Counter64
		MAX-ACCESS		read-only
		STATUS			current
		DESCRIPTION		"Description"
		::=  {  nptPmETPortCurrentEntry  5  }


	nptPmETPortCurrentRxMulticastPkts	OBJECT-TYPE	
		SYNTAX			Counter64
		MAX-ACCESS		read-only
		STATUS			current
		DESCRIPTION		"Description"
		::=  {  nptPmETPortCurrentEntry  6  }


	nptPmETPortCurrentTxOctets	OBJECT-TYPE	
		SYNTAX			Counter64
		MAX-ACCESS		read-only
		STATUS			current
		DESCRIPTION		"Description"
		::=  {  nptPmETPortCurrentEntry  7  }


	nptPmETPortCurrentTxPkts	OBJECT-TYPE	
		SYNTAX			Counter64
		MAX-ACCESS		read-only
		STATUS			current
		DESCRIPTION		"Description"
		::=  {  nptPmETPortCurrentEntry  8  }


	nptPmETPortCurrentRxErrorPkts	OBJECT-TYPE	
		SYNTAX			Counter64
		MAX-ACCESS		read-only
		STATUS			current
		DESCRIPTION		"Description"
		::=  {  nptPmETPortCurrentEntry  9  }


	nptPmETPortCurrentRxPkts64	OBJECT-TYPE	
		SYNTAX			Counter64
		MAX-ACCESS		read-only
		STATUS			current
		DESCRIPTION		"Description"
		::=  {  nptPmETPortCurrentEntry  10  }


	nptPmETPortCurrentRxPkts127	OBJECT-TYPE	
		SYNTAX			Counter64
		MAX-ACCESS		read-only
		STATUS			current
		DESCRIPTION		"Description"
		::=  {  nptPmETPortCurrentEntry  11  }


	nptPmETPortCurrentRxPkts255	OBJECT-TYPE	
		SYNTAX			Counter64
		MAX-ACCESS		read-only
		STATUS			current
		DESCRIPTION		"Description"
		::=  {  nptPmETPortCurrentEntry  12  }


	nptPmETPortCurrentRxPkts511	OBJECT-TYPE	
		SYNTAX			Counter64
		MAX-ACCESS		read-only
		STATUS			current
		DESCRIPTION		"Description"
		::=  {  nptPmETPortCurrentEntry  13  }


	nptPmETPortCurrentRxPkts1023	OBJECT-TYPE	
		SYNTAX			Counter64
		MAX-ACCESS		read-only
		STATUS			current
		DESCRIPTION		"Description"
		::=  {  nptPmETPortCurrentEntry  14  }


	nptPmETPortCurrentRxPktsMtu	OBJECT-TYPE	
		SYNTAX			Counter64
		MAX-ACCESS		read-only
		STATUS			current
		DESCRIPTION		"Description"
		::=  {  nptPmETPortCurrentEntry  15  }


	nptPmETPortCurrentRxUndersizePkts	OBJECT-TYPE	
		SYNTAX			Counter64
		MAX-ACCESS		read-only
		STATUS			current
		DESCRIPTION		"Description"
		::=  {  nptPmETPortCurrentEntry  16  }


	nptPmETPortCurrentRxOversizePkts	OBJECT-TYPE	
		SYNTAX			Counter64
		MAX-ACCESS		read-only
		STATUS			current
		DESCRIPTION		"Description"
		::=  {  nptPmETPortCurrentEntry  17  }


	nptPmETPortCurrentRxPausePkts	OBJECT-TYPE	
		SYNTAX			Counter64
		MAX-ACCESS		read-only
		STATUS			current
		DESCRIPTION		"Description"
		::=  {  nptPmETPortCurrentEntry  18  }
		
	nptPmETPortCurrentRxJabberPkts	OBJECT-TYPE	
		SYNTAX			Counter64
		MAX-ACCESS		read-only
		STATUS			current
		DESCRIPTION		"Description"
		::=  {  nptPmETPortCurrentEntry  19  }


	nptPmETPortCurrentRxCRCAlignErrorPkts	OBJECT-TYPE	
		SYNTAX			Counter64
		MAX-ACCESS		read-only
		STATUS			current
		DESCRIPTION		"Description"
		::=  {  nptPmETPortCurrentEntry  20  }


	nptPmETPortCurrentRxFragments	OBJECT-TYPE	
		SYNTAX			Counter64
		MAX-ACCESS		read-only
		STATUS			current
		DESCRIPTION		"Description"
		::=  {  nptPmETPortCurrentEntry  21  }


	nptPmETPortCurrentCollisionErrors	OBJECT-TYPE	
		SYNTAX			Counter64
		MAX-ACCESS		read-only
		STATUS			current
		DESCRIPTION		"Description"
		::=  {  nptPmETPortCurrentEntry  22  }


	nptPmETPortCurrentPCSLCV	OBJECT-TYPE	
		SYNTAX			Counter64
		MAX-ACCESS		read-only
		STATUS			current
		DESCRIPTION		"Description"
		::=  {  nptPmETPortCurrentEntry  23  }
		


	nptPmETPortCurrentPCSES	OBJECT-TYPE	
		SYNTAX			Counter64
		MAX-ACCESS		read-only
		STATUS			current
		DESCRIPTION		"Description"
		::=  {  nptPmETPortCurrentEntry  24  }


	nptPmETPortCurrentPCSSES	OBJECT-TYPE	
		SYNTAX			Counter64
		MAX-ACCESS		read-only
		STATUS			current
		DESCRIPTION		"Description"
		::=  {  nptPmETPortCurrentEntry  25  }


	nptPmETPortCurrentPCSUAS	OBJECT-TYPE	
		SYNTAX			Counter64
		MAX-ACCESS		read-only
		STATUS			current
		DESCRIPTION		"Description"
		::=  {  nptPmETPortCurrentEntry  26  }
		
	nptPmETPortCurrentFECCE	OBJECT-TYPE	
		SYNTAX			Counter64
		MAX-ACCESS		read-only
		STATUS			current
		DESCRIPTION		"Description"
		::=  {  nptPmETPortCurrentEntry  27  }


	nptPmETPortCurrentFECUCE	OBJECT-TYPE	
		SYNTAX			Counter64
		MAX-ACCESS		read-only
		STATUS			current
		DESCRIPTION		"Description"
		::=  {  nptPmETPortCurrentEntry  28  }


	nptPmETPortCurrentPREFECBER	OBJECT-TYPE	
		SYNTAX			Counter64
		MAX-ACCESS		read-only
		STATUS			current
		DESCRIPTION		"Description"
		::=  {  nptPmETPortCurrentEntry  29  }


	nptPmETPortCurrentINMaximumRate	OBJECT-TYPE	
		SYNTAX			Counter64
		MAX-ACCESS		read-only
		STATUS			current
		DESCRIPTION		"Description"
		::=  {  nptPmETPortCurrentEntry  30  }
		
	nptPmETPortCurrentINAverageRate	OBJECT-TYPE	
		SYNTAX			Counter64
		MAX-ACCESS		read-only
		STATUS			current
		DESCRIPTION		"Description"
		::=  {  nptPmETPortCurrentEntry  31  }
		
	nptPmETPortCurrentINCurrentRate	OBJECT-TYPE	
		SYNTAX			Counter64
		MAX-ACCESS		read-only
		STATUS			current
		DESCRIPTION		"Description"
		::=  {  nptPmETPortCurrentEntry  32  }
		
	nptPmETPortCurrentINMaximumPPS	OBJECT-TYPE	
		SYNTAX			Counter64
		MAX-ACCESS		read-only
		STATUS			current
		DESCRIPTION		"Description"
		::=  {  nptPmETPortCurrentEntry  33  }
		
	nptPmETPortCurrentINAveragePPS	OBJECT-TYPE	
		SYNTAX			Counter64
		MAX-ACCESS		read-only
		STATUS			current
		DESCRIPTION		"Description"
		::=  {  nptPmETPortCurrentEntry  34  }
		
	nptPmETPortCurrentINCurrentPPS	OBJECT-TYPE	
		SYNTAX			Counter64
		MAX-ACCESS		read-only
		STATUS			current
		DESCRIPTION		"Description"
		::=  {  nptPmETPortCurrentEntry  35  }
		
	nptPmETPortCurrentINMaximumUtilization	OBJECT-TYPE	
		SYNTAX			Counter64
		MAX-ACCESS		read-only
		STATUS			current
		DESCRIPTION		"Description"
		::=  {  nptPmETPortCurrentEntry  36  }
		
	nptPmETPortCurrentINAverageUtilization	OBJECT-TYPE	
		SYNTAX			Counter64
		MAX-ACCESS		read-only
		STATUS			current
		DESCRIPTION		"Description"
		::=  {  nptPmETPortCurrentEntry  37  }
		
	nptPmETPortCurrentINCurrentUtilization	OBJECT-TYPE	
		SYNTAX			Counter64
		MAX-ACCESS		read-only
		STATUS			current
		DESCRIPTION		"Description"
		::=  {  nptPmETPortCurrentEntry  38  }
		
	nptPmETPortCurrentOUTMaximumRate	OBJECT-TYPE	
		SYNTAX			Counter64
		MAX-ACCESS		read-only
		STATUS			current
		DESCRIPTION		"Description"
		::=  {  nptPmETPortCurrentEntry  39  }
		
	nptPmETPortCurrentOUTAverageRate	OBJECT-TYPE	
		SYNTAX			Counter64
		MAX-ACCESS		read-only
		STATUS			current
		DESCRIPTION		"Description"
		::=  {  nptPmETPortCurrentEntry  40  }
		
	nptPmETPortCurrentOUTCurrentRate	OBJECT-TYPE	
		SYNTAX			Counter64
		MAX-ACCESS		read-only
		STATUS			current
		DESCRIPTION		"Description"
		::=  {  nptPmETPortCurrentEntry  41  }
		
	nptPmETPortCurrentOUTMaximumPPS	OBJECT-TYPE	
		SYNTAX			Counter64
		MAX-ACCESS		read-only
		STATUS			current
		DESCRIPTION		"Description"
		::=  {  nptPmETPortCurrentEntry  42  }
		
	nptPmETPortCurrentOUTAveragePPS	OBJECT-TYPE	
		SYNTAX			Counter64
		MAX-ACCESS		read-only
		STATUS			current
		DESCRIPTION		"Description"
		::=  {  nptPmETPortCurrentEntry  43  }
		
	nptPmETPortCurrentOUTCurrentPPS	OBJECT-TYPE	
		SYNTAX			Counter64
		MAX-ACCESS		read-only
		STATUS			current
		DESCRIPTION		"Description"
		::=  {  nptPmETPortCurrentEntry  44  }
		
	nptPmETPortCurrentOUTMaximumUtilization	OBJECT-TYPE	
		SYNTAX			Counter64
		MAX-ACCESS		read-only
		STATUS			current
		DESCRIPTION		"Description"
		::=  {  nptPmETPortCurrentEntry  45  }
		
	nptPmETPortCurrentOUTAverageUtilization	OBJECT-TYPE	
		SYNTAX			Counter64
		MAX-ACCESS		read-only
		STATUS			current
		DESCRIPTION		"Description"
		::=  {  nptPmETPortCurrentEntry  46  }
		
	nptPmETPortCurrentOUTCurrentUtilization	OBJECT-TYPE	
		SYNTAX			Counter64
		MAX-ACCESS		read-only
		STATUS			current
		DESCRIPTION		"Description"
		::=  {  nptPmETPortCurrentEntry  47  }
		
	nptPmETPortCurrentLinkDownSeconds	OBJECT-TYPE	
		SYNTAX			Counter64
		MAX-ACCESS		read-only
		STATUS			current
		DESCRIPTION		"Description"
		::=  {  nptPmETPortCurrentEntry  48  }
		
	nptPmETPortCurrentOSNRMax	OBJECT-TYPE	
		SYNTAX			DisplayString
		MAX-ACCESS		read-only
		STATUS			current
		DESCRIPTION		"Description"
		::=  {  nptPmETPortCurrentEntry  49  }
		
	nptPmETPortCurrentOSNRMin	OBJECT-TYPE	
		SYNTAX			DisplayString
		MAX-ACCESS		read-only
		STATUS			current
		DESCRIPTION		"Description"
		::=  {  nptPmETPortCurrentEntry  50  }
               
	nptPmETPortCurrentMaxRxPower	OBJECT-TYPE	
		SYNTAX			DisplayString
		MAX-ACCESS		read-only
		STATUS			current
		DESCRIPTION		"Description"
		::=  {  nptPmETPortCurrentEntry  51  }
		
	nptPmETPortCurrentMinRxPower	OBJECT-TYPE	
		SYNTAX			DisplayString
		MAX-ACCESS		read-only
		STATUS			current
		DESCRIPTION		"Description"
		::=  {  nptPmETPortCurrentEntry  52  }
        
	nptPmETPortCurrentTxPower	OBJECT-TYPE	
		SYNTAX			DisplayString
		MAX-ACCESS		read-only
		STATUS			current
		DESCRIPTION		"Description"
		::=  {  nptPmETPortCurrentEntry  53  }	
		
	nptPmETPortTotalTable	OBJECT-TYPE
		SYNTAX		SEQUENCE  OF  NptPmETPortTotalEntry
		MAX-ACCESS	not-accessible
		STATUS		current
		DESCRIPTION	"Description"
		::=  { nptPmETPort  2 }

	nptPmETPortTotalEntry	OBJECT-TYPE
		SYNTAX		NptPmETPortTotalEntry
		MAX-ACCESS	not-accessible
		STATUS		current
		DESCRIPTION	"Row Description"
		INDEX		{  nptPmETPortTotalIndex  }
		::=  { nptPmETPortTotalTable 1 }

	NptPmETPortTotalEntry  ::=  SEQUENCE {
	    nptPmETPortTotalIndex  Integer32,
		nptPmETPortTotalMoDescription  DisplayString,
	    nptPmETPortTotalRxOctets  Counter64,
		nptPmETPortTotalRxPkts  Counter64,
		nptPmETPortTotalRxBroadcastPkts  Counter64,
		nptPmETPortTotalRxMulticastPkts  Counter64,
		nptPmETPortTotalTxOctets  Counter64,
		nptPmETPortTotalTxPkts  Counter64,
		nptPmETPortTotalRxErrorPkts  Counter64,
		nptPmETPortTotalRxPkts64  Counter64,
		nptPmETPortTotalRxPkts127  Counter64,
		nptPmETPortTotalRxPkts255  Counter64,
		nptPmETPortTotalRxPkts511  Counter64,
		nptPmETPortTotalRxPkts1023  Counter64,
		nptPmETPortTotalRxPktsMtu  Counter64,
		nptPmETPortTotalRxUndersizePkts  Counter64,
		nptPmETPortTotalRxOversizePkts  Counter64,
		nptPmETPortTotalRxPausePkts  Counter64,
		nptPmETPortTotalRxJabberPkts  Counter64,
		nptPmETPortTotalRxCRCAlignErrorPkts  Counter64,
		nptPmETPortTotalRxFragments  Counter64,
		nptPmETPortTotalCollisionErrors  Counter64,
		nptPmETPortTotalPCSLCV  Counter64,
		nptPmETPortTotalPCSES  Counter64,
		nptPmETPortTotalPCSSES  Counter64,
		nptPmETPortTotalPCSUAS  Counter64,
		nptPmETPortTotalFECCE  Counter64,
		nptPmETPortTotalFECUCE  Counter64,
		nptPmETPortTotalPREFECBER  Counter64,
		nptPmETPortTotalINMaximumRate  Counter64,
		nptPmETPortTotalINAverageRate  Counter64,
		nptPmETPortTotalINTotalRate  Counter64,
		nptPmETPortTotalINMaximumPPS  Counter64,
		nptPmETPortTotalINAveragePPS  Counter64,
		nptPmETPortTotalINTotalPPS  Counter64,
		nptPmETPortTotalINMaximumUtilization  Counter64,
		nptPmETPortTotalINAverageUtilization  Counter64,
		nptPmETPortTotalINTotalUtilization  Counter64,
		nptPmETPortTotalOUTMaximumRate  Counter64,
		nptPmETPortTotalOUTAverageRate  Counter64,
		nptPmETPortTotalOUTTotalRate  Counter64,
		nptPmETPortTotalOUTMaximumPPS  Counter64,
		nptPmETPortTotalOUTAveragePPS  Counter64,
		nptPmETPortTotalOUTTotalPPS  Counter64,
		nptPmETPortTotalOUTMaximumUtilization  Counter64,
		nptPmETPortTotalOUTAverageUtilization  Counter64,
		nptPmETPortTotalOUTTotalUtilization  Counter64,
		nptPmETPortTotalLinkDownSeconds  Counter64,
		nptPmETPortTotalOSNRMax  DisplayString,
		nptPmETPortTotalOSNRMin  DisplayString,
		nptPmETPortTotalMaxRxPower  DisplayString,
		nptPmETPortTotalMinRxPower  DisplayString,
        nptPmETPortTotalTxPower  DisplayString
		}


	nptPmETPortTotalIndex	OBJECT-TYPE	
		SYNTAX			Integer32  ( -2147483648 .. 2147483647  ) 
		MAX-ACCESS		read-only
		STATUS			current
		DESCRIPTION		"Column Description"
		::=  {  nptPmETPortTotalEntry  1  }
	
	
	nptPmETPortTotalMoDescription	OBJECT-TYPE	
		SYNTAX			DisplayString 
		MAX-ACCESS		read-only
		STATUS			current
		DESCRIPTION		"Column Description"
		::=  {  nptPmETPortTotalEntry  2  }


	nptPmETPortTotalRxOctets	OBJECT-TYPE	
		SYNTAX			Counter64
		MAX-ACCESS		read-only
		STATUS			current
		DESCRIPTION		"Column Description"
		::=  {  nptPmETPortTotalEntry  3  }


	nptPmETPortTotalRxPkts	OBJECT-TYPE	
		SYNTAX			Counter64
		MAX-ACCESS		read-only
		STATUS			current
		DESCRIPTION		"Description"
		::=  {  nptPmETPortTotalEntry  4  }


	nptPmETPortTotalRxBroadcastPkts	OBJECT-TYPE	
		SYNTAX			Counter64
		MAX-ACCESS		read-only
		STATUS			current
		DESCRIPTION		"Description"
		::=  {  nptPmETPortTotalEntry  5  }


	nptPmETPortTotalRxMulticastPkts	OBJECT-TYPE	
		SYNTAX			Counter64
		MAX-ACCESS		read-only
		STATUS			current
		DESCRIPTION		"Description"
		::=  {  nptPmETPortTotalEntry  6  }


	nptPmETPortTotalTxOctets	OBJECT-TYPE	
		SYNTAX			Counter64
		MAX-ACCESS		read-only
		STATUS			current
		DESCRIPTION		"Description"
		::=  {  nptPmETPortTotalEntry  7  }


	nptPmETPortTotalTxPkts	OBJECT-TYPE	
		SYNTAX			Counter64
		MAX-ACCESS		read-only
		STATUS			current
		DESCRIPTION		"Description"
		::=  {  nptPmETPortTotalEntry  8  }


	nptPmETPortTotalRxErrorPkts	OBJECT-TYPE	
		SYNTAX			Counter64
		MAX-ACCESS		read-only
		STATUS			current
		DESCRIPTION		"Description"
		::=  {  nptPmETPortTotalEntry  9  }


	nptPmETPortTotalRxPkts64	OBJECT-TYPE	
		SYNTAX			Counter64
		MAX-ACCESS		read-only
		STATUS			current
		DESCRIPTION		"Description"
		::=  {  nptPmETPortTotalEntry  10  }


	nptPmETPortTotalRxPkts127	OBJECT-TYPE	
		SYNTAX			Counter64
		MAX-ACCESS		read-only
		STATUS			current
		DESCRIPTION		"Description"
		::=  {  nptPmETPortTotalEntry  11  }


	nptPmETPortTotalRxPkts255	OBJECT-TYPE	
		SYNTAX			Counter64
		MAX-ACCESS		read-only
		STATUS			current
		DESCRIPTION		"Description"
		::=  {  nptPmETPortTotalEntry  12  }


	nptPmETPortTotalRxPkts511	OBJECT-TYPE	
		SYNTAX			Counter64
		MAX-ACCESS		read-only
		STATUS			current
		DESCRIPTION		"Description"
		::=  {  nptPmETPortTotalEntry  13  }


	nptPmETPortTotalRxPkts1023	OBJECT-TYPE	
		SYNTAX			Counter64
		MAX-ACCESS		read-only
		STATUS			current
		DESCRIPTION		"Description"
		::=  {  nptPmETPortTotalEntry  14  }


	nptPmETPortTotalRxPktsMtu	OBJECT-TYPE	
		SYNTAX			Counter64
		MAX-ACCESS		read-only
		STATUS			current
		DESCRIPTION		"Description"
		::=  {  nptPmETPortTotalEntry  15  }


	nptPmETPortTotalRxUndersizePkts	OBJECT-TYPE	
		SYNTAX			Counter64
		MAX-ACCESS		read-only
		STATUS			current
		DESCRIPTION		"Description"
		::=  {  nptPmETPortTotalEntry  16  }


	nptPmETPortTotalRxOversizePkts	OBJECT-TYPE	
		SYNTAX			Counter64
		MAX-ACCESS		read-only
		STATUS			current
		DESCRIPTION		"Description"
		::=  {  nptPmETPortTotalEntry  17  }


	nptPmETPortTotalRxPausePkts	OBJECT-TYPE	
		SYNTAX			Counter64
		MAX-ACCESS		read-only
		STATUS			current
		DESCRIPTION		"Description"
		::=  {  nptPmETPortTotalEntry  18  }
		
	nptPmETPortTotalRxJabberPkts	OBJECT-TYPE	
		SYNTAX			Counter64
		MAX-ACCESS		read-only
		STATUS			current
		DESCRIPTION		"Description"
		::=  {  nptPmETPortTotalEntry  19  }


	nptPmETPortTotalRxCRCAlignErrorPkts	OBJECT-TYPE	
		SYNTAX			Counter64
		MAX-ACCESS		read-only
		STATUS			current
		DESCRIPTION		"Description"
		::=  {  nptPmETPortTotalEntry  20  }


	nptPmETPortTotalRxFragments	OBJECT-TYPE	
		SYNTAX			Counter64
		MAX-ACCESS		read-only
		STATUS			current
		DESCRIPTION		"Description"
		::=  {  nptPmETPortTotalEntry  21  }


	nptPmETPortTotalCollisionErrors	OBJECT-TYPE	
		SYNTAX			Counter64
		MAX-ACCESS		read-only
		STATUS			current
		DESCRIPTION		"Description"
		::=  {  nptPmETPortTotalEntry  22  }


	nptPmETPortTotalPCSLCV	OBJECT-TYPE	
		SYNTAX			Counter64
		MAX-ACCESS		read-only
		STATUS			current
		DESCRIPTION		"Description"
		::=  {  nptPmETPortTotalEntry  23  }


	nptPmETPortTotalPCSES	OBJECT-TYPE	
		SYNTAX			Counter64
		MAX-ACCESS		read-only
		STATUS			current
		DESCRIPTION		"Description"
		::=  {  nptPmETPortTotalEntry  24  }


	nptPmETPortTotalPCSSES	OBJECT-TYPE	
		SYNTAX			Counter64
		MAX-ACCESS		read-only
		STATUS			current
		DESCRIPTION		"Description"
		::=  {  nptPmETPortTotalEntry  25  }


	nptPmETPortTotalPCSUAS	OBJECT-TYPE	
		SYNTAX			Counter64
		MAX-ACCESS		read-only
		STATUS			current
		DESCRIPTION		"Description"
		::=  {  nptPmETPortTotalEntry  26  }
		
	nptPmETPortTotalFECCE	OBJECT-TYPE	
		SYNTAX			Counter64
		MAX-ACCESS		read-only
		STATUS			current
		DESCRIPTION		"Description"
		::=  {  nptPmETPortTotalEntry  27  }


	nptPmETPortTotalFECUCE	OBJECT-TYPE	
		SYNTAX			Counter64
		MAX-ACCESS		read-only
		STATUS			current
		DESCRIPTION		"Description"
		::=  {  nptPmETPortTotalEntry  28  }


	nptPmETPortTotalPREFECBER	OBJECT-TYPE	
		SYNTAX			Counter64
		MAX-ACCESS		read-only
		STATUS			current
		DESCRIPTION		"Description"
		::=  {  nptPmETPortTotalEntry  29  }


	nptPmETPortTotalINMaximumRate	OBJECT-TYPE	
		SYNTAX			Counter64
		MAX-ACCESS		read-only
		STATUS			current
		DESCRIPTION		"Description"
		::=  {  nptPmETPortTotalEntry  30  }
		
	nptPmETPortTotalINAverageRate	OBJECT-TYPE	
		SYNTAX			Counter64
		MAX-ACCESS		read-only
		STATUS			current
		DESCRIPTION		"Description"
		::=  {  nptPmETPortTotalEntry  31  }
		
	nptPmETPortTotalINTotalRate	OBJECT-TYPE	
		SYNTAX			Counter64
		MAX-ACCESS		read-only
		STATUS			current
		DESCRIPTION		"Description"
		::=  {  nptPmETPortTotalEntry  32  }
		
	nptPmETPortTotalINMaximumPPS	OBJECT-TYPE	
		SYNTAX			Counter64
		MAX-ACCESS		read-only
		STATUS			current
		DESCRIPTION		"Description"
		::=  {  nptPmETPortTotalEntry  33  }
		
	nptPmETPortTotalINAveragePPS	OBJECT-TYPE	
		SYNTAX			Counter64
		MAX-ACCESS		read-only
		STATUS			current
		DESCRIPTION		"Description"
		::=  {  nptPmETPortTotalEntry  34  }
		
	nptPmETPortTotalINTotalPPS	OBJECT-TYPE	
		SYNTAX			Counter64
		MAX-ACCESS		read-only
		STATUS			current
		DESCRIPTION		"Description"
		::=  {  nptPmETPortTotalEntry  35  }
		
	nptPmETPortTotalINMaximumUtilization	OBJECT-TYPE	
		SYNTAX			Counter64
		MAX-ACCESS		read-only
		STATUS			current
		DESCRIPTION		"Description"
		::=  {  nptPmETPortTotalEntry  36  }
		
	nptPmETPortTotalINAverageUtilization	OBJECT-TYPE	
		SYNTAX			Counter64
		MAX-ACCESS		read-only
		STATUS			current
		DESCRIPTION		"Description"
		::=  {  nptPmETPortTotalEntry  37  }
		
	nptPmETPortTotalINTotalUtilization	OBJECT-TYPE	
		SYNTAX			Counter64
		MAX-ACCESS		read-only
		STATUS			current
		DESCRIPTION		"Description"
		::=  {  nptPmETPortTotalEntry  38  }
		
	nptPmETPortTotalOUTMaximumRate	OBJECT-TYPE	
		SYNTAX			Counter64
		MAX-ACCESS		read-only
		STATUS			current
		DESCRIPTION		"Description"
		::=  {  nptPmETPortTotalEntry  39  }
		
	nptPmETPortTotalOUTAverageRate	OBJECT-TYPE	
		SYNTAX			Counter64
		MAX-ACCESS		read-only
		STATUS			current
		DESCRIPTION		"Description"
		::=  {  nptPmETPortTotalEntry  40  }
		
	nptPmETPortTotalOUTTotalRate	OBJECT-TYPE	
		SYNTAX			Counter64
		MAX-ACCESS		read-only
		STATUS			current
		DESCRIPTION		"Description"
		::=  {  nptPmETPortTotalEntry  41  }
		
	nptPmETPortTotalOUTMaximumPPS	OBJECT-TYPE	
		SYNTAX			Counter64
		MAX-ACCESS		read-only
		STATUS			current
		DESCRIPTION		"Description"
		::=  {  nptPmETPortTotalEntry  42  }
		
	nptPmETPortTotalOUTAveragePPS	OBJECT-TYPE	
		SYNTAX			Counter64
		MAX-ACCESS		read-only
		STATUS			current
		DESCRIPTION		"Description"
		::=  {  nptPmETPortTotalEntry  43  }
		
	nptPmETPortTotalOUTTotalPPS	OBJECT-TYPE	
		SYNTAX			Counter64
		MAX-ACCESS		read-only
		STATUS			current
		DESCRIPTION		"Description"
		::=  {  nptPmETPortTotalEntry  44  }
		
	nptPmETPortTotalOUTMaximumUtilization	OBJECT-TYPE	
		SYNTAX			Counter64
		MAX-ACCESS		read-only
		STATUS			current
		DESCRIPTION		"Description"
		::=  {  nptPmETPortTotalEntry  45  }
		
	nptPmETPortTotalOUTAverageUtilization	OBJECT-TYPE	
		SYNTAX			Counter64
		MAX-ACCESS		read-only
		STATUS			current
		DESCRIPTION		"Description"
		::=  {  nptPmETPortTotalEntry  46  }
		
	nptPmETPortTotalOUTTotalUtilization	OBJECT-TYPE	
		SYNTAX			Counter64
		MAX-ACCESS		read-only
		STATUS			current
		DESCRIPTION		"Description"
		::=  {  nptPmETPortTotalEntry  47  }
		
	nptPmETPortTotalLinkDownSeconds	OBJECT-TYPE	
		SYNTAX			Counter64
		MAX-ACCESS		read-only
		STATUS			current
		DESCRIPTION		"Description"
		::=  {  nptPmETPortTotalEntry  48  }
		
	nptPmETPortTotalOSNRMax	OBJECT-TYPE	
		SYNTAX			DisplayString
		MAX-ACCESS		read-only
		STATUS			current
		DESCRIPTION		"Description"
		::=  {  nptPmETPortTotalEntry  49  }
		
	nptPmETPortTotalOSNRMin	OBJECT-TYPE	
		SYNTAX			DisplayString
		MAX-ACCESS		read-only
		STATUS			current
		DESCRIPTION		"Description"
		::=  {  nptPmETPortTotalEntry  50  }
               
	nptPmETPortTotalMaxRxPower	OBJECT-TYPE	
		SYNTAX			DisplayString
		MAX-ACCESS		read-only
		STATUS			current
		DESCRIPTION		"Description"
		::=  {  nptPmETPortTotalEntry  51  }
		
	nptPmETPortTotalMinRxPower	OBJECT-TYPE	
		SYNTAX			DisplayString
		MAX-ACCESS		read-only
		STATUS			current
		DESCRIPTION		"Description"
		::=  {  nptPmETPortTotalEntry  52  }
        
	nptPmETPortTotalTxPower	OBJECT-TYPE	
		SYNTAX			DisplayString
		MAX-ACCESS		read-only
		STATUS			current
		DESCRIPTION		"Description"
		::=  {  nptPmETPortTotalEntry  53  }	
		
	nptLagIfGroupCurrentTable	OBJECT-TYPE
		SYNTAX		SEQUENCE  OF  NptLagIfGroupCurrentEntry
		MAX-ACCESS	not-accessible
		STATUS		current
		DESCRIPTION	"Description"
		::=  { nptLagIfGroup  1 }

	nptLagIfGroupCurrentEntry	OBJECT-TYPE
		SYNTAX		NptLagIfGroupCurrentEntry
		MAX-ACCESS	not-accessible
		STATUS		current
		DESCRIPTION	"Row Description"
		INDEX		{  nptLagIfGroupCurrentIndex  }
		::=  { nptLagIfGroupCurrentTable 1 }
        

	NptLagIfGroupCurrentEntry  ::=  SEQUENCE {
	    nptLagIfGroupCurrentIndex  Integer32,
		nptLagIfGroupCurrentMoDescription  DisplayString,
	    nptLagIfGroupCurrentRxOctets  Counter64,
		nptLagIfGroupCurrentRxPkts  Counter64,
		nptLagIfGroupCurrentRxBroadcastPkts  Counter64,
		nptLagIfGroupCurrentRxMulticastPkts  Counter64,
		nptLagIfGroupCurrentTxOctets  Counter64,
		nptLagIfGroupCurrentTxPkts  Counter64,
		nptLagIfGroupCurrentRxErrorPkts  Counter64,
		nptLagIfGroupCurrentRxPkts64  Counter64,
		nptLagIfGroupCurrentRxPkts127  Counter64,
		nptLagIfGroupCurrentRxPkts255  Counter64,
		nptLagIfGroupCurrentRxPkts511  Counter64,
		nptLagIfGroupCurrentRxPkts1023  Counter64,
		nptLagIfGroupCurrentRxPktsMtu  Counter64,
		nptLagIfGroupCurrentRxUndersizePkts  Counter64,
		nptLagIfGroupCurrentRxOversizePkts  Counter64,
		nptLagIfGroupCurrentRxPausePkts  Counter64
		}


	nptLagIfGroupCurrentIndex	OBJECT-TYPE	
		SYNTAX			Integer32  ( -2147483648 .. 2147483647  ) 
		MAX-ACCESS		read-only
		STATUS			current
		DESCRIPTION		"Column Description"
		::=  {  nptLagIfGroupCurrentEntry  1  }

		
	nptLagIfGroupCurrentMoDescription	OBJECT-TYPE	
		SYNTAX			DisplayString 
		MAX-ACCESS		read-only
		STATUS			current
		DESCRIPTION		"Column Description"
		::=  {  nptLagIfGroupCurrentEntry  2  }

	nptLagIfGroupCurrentRxOctets	OBJECT-TYPE	
		SYNTAX			Counter64
		MAX-ACCESS		read-only
		STATUS			current
		DESCRIPTION		"Column Description"
		::=  {  nptLagIfGroupCurrentEntry  3  }


	nptLagIfGroupCurrentRxPkts	OBJECT-TYPE	
		SYNTAX			Counter64
		MAX-ACCESS		read-only
		STATUS			current
		DESCRIPTION		"Description"
		::=  {  nptLagIfGroupCurrentEntry  4  }


	nptLagIfGroupCurrentRxBroadcastPkts	OBJECT-TYPE	
		SYNTAX			Counter64
		MAX-ACCESS		read-only
		STATUS			current
		DESCRIPTION		"Description"
		::=  {  nptLagIfGroupCurrentEntry  5  }


	nptLagIfGroupCurrentRxMulticastPkts	OBJECT-TYPE	
		SYNTAX			Counter64
		MAX-ACCESS		read-only
		STATUS			current
		DESCRIPTION		"Description"
		::=  {  nptLagIfGroupCurrentEntry  6  }


	nptLagIfGroupCurrentTxOctets	OBJECT-TYPE	
		SYNTAX			Counter64
		MAX-ACCESS		read-only
		STATUS			current
		DESCRIPTION		"Description"
		::=  {  nptLagIfGroupCurrentEntry  7  }


	nptLagIfGroupCurrentTxPkts	OBJECT-TYPE	
		SYNTAX			Counter64
		MAX-ACCESS		read-only
		STATUS			current
		DESCRIPTION		"Description"
		::=  {  nptLagIfGroupCurrentEntry  8  }


	nptLagIfGroupCurrentRxErrorPkts	OBJECT-TYPE	
		SYNTAX			Counter64
		MAX-ACCESS		read-only
		STATUS			current
		DESCRIPTION		"Description"
		::=  {  nptLagIfGroupCurrentEntry  9  }


	nptLagIfGroupCurrentRxPkts64	OBJECT-TYPE	
		SYNTAX			Counter64
		MAX-ACCESS		read-only
		STATUS			current
		DESCRIPTION		"Description"
		::=  {  nptLagIfGroupCurrentEntry  10  }


	nptLagIfGroupCurrentRxPkts127	OBJECT-TYPE	
		SYNTAX			Counter64
		MAX-ACCESS		read-only
		STATUS			current
		DESCRIPTION		"Description"
		::=  {  nptLagIfGroupCurrentEntry  11  }


	nptLagIfGroupCurrentRxPkts255	OBJECT-TYPE	
		SYNTAX			Counter64
		MAX-ACCESS		read-only
		STATUS			current
		DESCRIPTION		"Description"
		::=  {  nptLagIfGroupCurrentEntry  12  }


	nptLagIfGroupCurrentRxPkts511	OBJECT-TYPE	
		SYNTAX			Counter64
		MAX-ACCESS		read-only
		STATUS			current
		DESCRIPTION		"Description"
		::=  {  nptLagIfGroupCurrentEntry  13  }


	nptLagIfGroupCurrentRxPkts1023	OBJECT-TYPE	
		SYNTAX			Counter64
		MAX-ACCESS		read-only
		STATUS			current
		DESCRIPTION		"Description"
		::=  {  nptLagIfGroupCurrentEntry  14  }


	nptLagIfGroupCurrentRxPktsMtu	OBJECT-TYPE	
		SYNTAX			Counter64
		MAX-ACCESS		read-only
		STATUS			current
		DESCRIPTION		"Description"
		::=  {  nptLagIfGroupCurrentEntry  15  }


	nptLagIfGroupCurrentRxUndersizePkts	OBJECT-TYPE	
		SYNTAX			Counter64
		MAX-ACCESS		read-only
		STATUS			current
		DESCRIPTION		"Description"
		::=  {  nptLagIfGroupCurrentEntry  16  }


	nptLagIfGroupCurrentRxOversizePkts	OBJECT-TYPE	
		SYNTAX			Counter64
		MAX-ACCESS		read-only
		STATUS			current
		DESCRIPTION		"Description"
		::=  {  nptLagIfGroupCurrentEntry  17  }


	nptLagIfGroupCurrentRxPausePkts	OBJECT-TYPE	
		SYNTAX			Counter64
		MAX-ACCESS		read-only
		STATUS			current
		DESCRIPTION		"Description"
		::=  {  nptLagIfGroupCurrentEntry  18  }

		
	nptLagIfGroupTotalTable	OBJECT-TYPE
		SYNTAX		SEQUENCE  OF  NptLagIfGroupTotalEntry
		MAX-ACCESS	not-accessible
		STATUS		current
		DESCRIPTION	"Description"
		::=  { nptLagIfGroup  2 }

	nptLagIfGroupTotalEntry	OBJECT-TYPE
		SYNTAX		NptLagIfGroupTotalEntry
		MAX-ACCESS	not-accessible
		STATUS		current
		DESCRIPTION	"Row Description"
		INDEX		{  nptLagIfGroupTotalIndex  }
		::=  { nptLagIfGroupTotalTable 1 }

	NptLagIfGroupTotalEntry  ::=  SEQUENCE {
	    nptLagIfGroupTotalIndex  Integer32,
		nptLagIfGroupTotalMoDescription  DisplayString,
	    nptLagIfGroupTotalRxOctets  Counter64,
		nptLagIfGroupTotalRxPkts  Counter64,
		nptLagIfGroupTotalRxBroadcastPkts  Counter64,
		nptLagIfGroupTotalRxMulticastPkts  Counter64,
		nptLagIfGroupTotalTxOctets  Counter64,
		nptLagIfGroupTotalTxPkts  Counter64,
		nptLagIfGroupTotalRxErrorPkts  Counter64,
		nptLagIfGroupTotalRxPkts64  Counter64,
		nptLagIfGroupTotalRxPkts127  Counter64,
		nptLagIfGroupTotalRxPkts255  Counter64,
		nptLagIfGroupTotalRxPkts511  Counter64,
		nptLagIfGroupTotalRxPkts1023  Counter64,
		nptLagIfGroupTotalRxPktsMtu  Counter64,
		nptLagIfGroupTotalRxUndersizePkts  Counter64,
		nptLagIfGroupTotalRxOversizePkts  Counter64,
		nptLagIfGroupTotalRxPausePkts  Counter64
		}


	nptLagIfGroupTotalIndex	OBJECT-TYPE	
		SYNTAX			Integer32  ( -2147483648 .. 2147483647  ) 
		MAX-ACCESS		read-only
		STATUS			current
		DESCRIPTION		"Column Description"
		::=  {  nptLagIfGroupTotalEntry  1  }
		
	nptLagIfGroupTotalMoDescription	OBJECT-TYPE	
		SYNTAX			DisplayString 
		MAX-ACCESS		read-only
		STATUS			current
		DESCRIPTION		"Column Description"
		::=  {  nptLagIfGroupTotalEntry  2  }


	nptLagIfGroupTotalRxOctets	OBJECT-TYPE	
		SYNTAX			Counter64
		MAX-ACCESS		read-only
		STATUS			current
		DESCRIPTION		"Column Description"
		::=  {  nptLagIfGroupTotalEntry  3  }


	nptLagIfGroupTotalRxPkts	OBJECT-TYPE	
		SYNTAX			Counter64
		MAX-ACCESS		read-only
		STATUS			current
		DESCRIPTION		"Description"
		::=  {  nptLagIfGroupTotalEntry  4  }


	nptLagIfGroupTotalRxBroadcastPkts	OBJECT-TYPE	
		SYNTAX			Counter64
		MAX-ACCESS		read-only
		STATUS			current
		DESCRIPTION		"Description"
		::=  {  nptLagIfGroupTotalEntry  5  }


	nptLagIfGroupTotalRxMulticastPkts	OBJECT-TYPE	
		SYNTAX			Counter64
		MAX-ACCESS		read-only
		STATUS			current
		DESCRIPTION		"Description"
		::=  {  nptLagIfGroupTotalEntry  6  }


	nptLagIfGroupTotalTxOctets	OBJECT-TYPE	
		SYNTAX			Counter64
		MAX-ACCESS		read-only
		STATUS			current
		DESCRIPTION		"Description"
		::=  {  nptLagIfGroupTotalEntry  7  }


	nptLagIfGroupTotalTxPkts	OBJECT-TYPE	
		SYNTAX			Counter64
		MAX-ACCESS		read-only
		STATUS			current
		DESCRIPTION		"Description"
		::=  {  nptLagIfGroupTotalEntry  8  }


	nptLagIfGroupTotalRxErrorPkts	OBJECT-TYPE	
		SYNTAX			Counter64
		MAX-ACCESS		read-only
		STATUS			current
		DESCRIPTION		"Description"
		::=  {  nptLagIfGroupTotalEntry  9  }


	nptLagIfGroupTotalRxPkts64	OBJECT-TYPE	
		SYNTAX			Counter64
		MAX-ACCESS		read-only
		STATUS			current
		DESCRIPTION		"Description"
		::=  {  nptLagIfGroupTotalEntry  10  }


	nptLagIfGroupTotalRxPkts127	OBJECT-TYPE	
		SYNTAX			Counter64
		MAX-ACCESS		read-only
		STATUS			current
		DESCRIPTION		"Description"
		::=  {  nptLagIfGroupTotalEntry  11  }


	nptLagIfGroupTotalRxPkts255	OBJECT-TYPE	
		SYNTAX			Counter64
		MAX-ACCESS		read-only
		STATUS			current
		DESCRIPTION		"Description"
		::=  {  nptLagIfGroupTotalEntry  12  }


	nptLagIfGroupTotalRxPkts511	OBJECT-TYPE	
		SYNTAX			Counter64
		MAX-ACCESS		read-only
		STATUS			current
		DESCRIPTION		"Description"
		::=  {  nptLagIfGroupTotalEntry  13  }


	nptLagIfGroupTotalRxPkts1023	OBJECT-TYPE	
		SYNTAX			Counter64
		MAX-ACCESS		read-only
		STATUS			current
		DESCRIPTION		"Description"
		::=  {  nptLagIfGroupTotalEntry  14  }


	nptLagIfGroupTotalRxPktsMtu	OBJECT-TYPE	
		SYNTAX			Counter64
		MAX-ACCESS		read-only
		STATUS			current
		DESCRIPTION		"Description"
		::=  {  nptLagIfGroupTotalEntry  15  }


	nptLagIfGroupTotalRxUndersizePkts	OBJECT-TYPE	
		SYNTAX			Counter64
		MAX-ACCESS		read-only
		STATUS			current
		DESCRIPTION		"Description"
		::=  {  nptLagIfGroupTotalEntry  16  }


	nptLagIfGroupTotalRxOversizePkts	OBJECT-TYPE	
		SYNTAX			Counter64
		MAX-ACCESS		read-only
		STATUS			current
		DESCRIPTION		"Description"
		::=  {  nptLagIfGroupTotalEntry  17  }


	nptLagIfGroupTotalRxPausePkts	OBJECT-TYPE	
		SYNTAX			Counter64
		MAX-ACCESS		read-only
		STATUS			current
		DESCRIPTION		"Description"
		::=  {  nptLagIfGroupTotalEntry  18  }

		
	nptStmCurrentTable	OBJECT-TYPE
		SYNTAX		SEQUENCE  OF  NptStmCurrentEntry
		MAX-ACCESS	not-accessible
		STATUS		current
		DESCRIPTION	"The STM current table contains various statistics
            being collected for the current 15 minute
            interval."
		::=  { nptStmIfGroup  1 }

	nptStmCurrentEntry	OBJECT-TYPE
		SYNTAX		NptStmCurrentEntry
		MAX-ACCESS	not-accessible
		STATUS		current
		DESCRIPTION	"An entry in the STM Current table."
		INDEX		{  nptStmCurrentIndex  }
		::=  { nptStmCurrentTable 1 }

	NptStmCurrentEntry  ::=  SEQUENCE {
		nptStmCurrentIndex  Integer32,
		nptStmCurrentMoDescription  DisplayString,
		nptStmCurrentRSES  Counter64,
		nptStmCurrentRSSES  Counter64,
		nptStmCurrentRSBBE  Counter64,
		nptStmCurrentRSUAS  Counter64,
		nptStmCurrentRSOFS  Counter64,
		nptStmCurrentMSES  Counter64,
		nptStmCurrentMSSES  Counter64,
		nptStmCurrentMSBBE  Counter64,
		nptStmCurrentMSUAS  Counter64,
		nptStmCurrentMSFEES  Counter64,
		nptStmCurrentMSFESES  Counter64,
		nptStmCurrentMSFEBBE  Counter64,
		nptStmCurrentMSFEUAS  Counter64,
		nptStmCurrentMaxRxPower  DisplayString,
		nptStmCurrentMinRxPower  DisplayString,
        	nptStmCurrentTxPower  DisplayString
		}


	nptStmCurrentIndex	OBJECT-TYPE	
		SYNTAX			Integer32  ( -2147483648 .. 2147483647  ) 
		MAX-ACCESS		read-only
		STATUS			current
		DESCRIPTION		"The index value which uniquely identifies  the
            STM interface to which this entry is applicable."
		::=  {  nptStmCurrentEntry  1  }
		
	nptStmCurrentMoDescription	OBJECT-TYPE	
		SYNTAX			DisplayString 
		MAX-ACCESS		read-only
		STATUS			current
		DESCRIPTION		"Mo Description"
		::=  {  nptStmCurrentEntry  2  }


	nptStmCurrentRSES	OBJECT-TYPE	
		SYNTAX			Counter64
		MAX-ACCESS		read-only
		STATUS			current
		DESCRIPTION		"The number of Errored Seconds.errored seconds. If errors occur within a certain second, this second is called an errored second."
		::=  {  nptStmCurrentEntry  3  }


	nptStmCurrentRSSES	OBJECT-TYPE	
		SYNTAX			Counter64
		MAX-ACCESS		read-only
		STATUS			current
		DESCRIPTION		"severely errored seconds. If there are errors in 30% of the frames, 
		the errors exceed the threshold, or the signal fails within a certain second, 
		this second is called a severely errored second. Errored seconds (ESs) are not counted when severely errored seconds occur."
		::=  {  nptStmCurrentEntry  4  }


	nptStmCurrentRSBBE	OBJECT-TYPE	
		SYNTAX			Counter64
		MAX-ACCESS		read-only
		STATUS			current
		DESCRIPTION		"background block errors. If there are errors in a frame of data, 
		this frame is counted as a block error. The background block error is the block error 
		with the number of severely errored seconds deducted from the counting interval."
		::=  {  nptStmCurrentEntry  5  }


	nptStmCurrentRSUAS	OBJECT-TYPE	
		SYNTAX			Counter64
		MAX-ACCESS		read-only
		STATUS			current
		DESCRIPTION		"unavailable seconds. When an SES lasts for 10 seconds, it becomes a UAS. 
		When there are no severely errored seconds within 10 seconds, it is no longer counted as a UAS. The UAS is not calculated in SES calculations."
		::=  {  nptStmCurrentEntry  6  }


	nptStmCurrentRSOFS	OBJECT-TYPE	
		SYNTAX			Counter64
		MAX-ACCESS		read-only
		STATUS			current
		DESCRIPTION		"out-of-frame seconds."
		::=  {  nptStmCurrentEntry  7  }


	nptStmCurrentMSES	OBJECT-TYPE	
		SYNTAX			Counter64
		MAX-ACCESS		read-only
		STATUS			current
		DESCRIPTION		"errored seconds. If errors occur within a certain second, this second is called an errored second."
		::=  {  nptStmCurrentEntry  8  }


	nptStmCurrentMSSES	OBJECT-TYPE	
		SYNTAX			Counter64
		MAX-ACCESS		read-only
		STATUS			current
		DESCRIPTION		"severely errored seconds. If there are errors in 30% of the frames, the 
		errors exceed the threshold, or the signal fails within a certain second, this second is 
		called a severely errored second. Errored seconds (ESs) are not counted when severely errored seconds occur."
		::=  {  nptStmCurrentEntry  9  }


	nptStmCurrentMSBBE	OBJECT-TYPE	
		SYNTAX			Counter64
		MAX-ACCESS		read-only
		STATUS			current
		DESCRIPTION		"background block errors. If there are errors in a frame of data, this frame
		is counted as a block error. The background block error is the block error with the number
		of severely errored seconds deducted from the counting interval."
		::=  {  nptStmCurrentEntry  10  }


	nptStmCurrentMSUAS	OBJECT-TYPE	
		SYNTAX			Counter64
		MAX-ACCESS		read-only
		STATUS			current
		DESCRIPTION		"unavailable seconds. When an SES lasts for 10 seconds, it becomes a 
		UAS. When there are no severely errored seconds within 10 seconds, it is no longer 
		counted as a UAS. The UAS is not calculated in SES calculations."
		::=  {  nptStmCurrentEntry  11  }


	nptStmCurrentMSFEES	OBJECT-TYPE	
		SYNTAX			Counter64
		MAX-ACCESS		read-only
		STATUS			current
		DESCRIPTION		"far-end errored seconds."
		::=  {  nptStmCurrentEntry  12  }


	nptStmCurrentMSFESES	OBJECT-TYPE	
		SYNTAX			Counter64
		MAX-ACCESS		read-only
		STATUS			current
		DESCRIPTION		"far-end severely errored seconds."
		::=  {  nptStmCurrentEntry  13  }
		
	nptStmCurrentMSFEBBE	OBJECT-TYPE	
		SYNTAX			Counter64
		MAX-ACCESS		read-only
		STATUS			current
		DESCRIPTION		"far-end background block errors."
		::=  {  nptStmCurrentEntry  14  }
		
	nptStmCurrentMSFEUAS	OBJECT-TYPE	
		SYNTAX			Counter64
		MAX-ACCESS		read-only
		STATUS			current
		DESCRIPTION		"far-end unavailable seconds."
		::=  {  nptStmCurrentEntry  15  }
		
	nptStmCurrentMaxRxPower	OBJECT-TYPE	
		SYNTAX			DisplayString
		MAX-ACCESS		read-only
		STATUS			current
		DESCRIPTION		"The maximal receive optical power in monitored duration."
		::=  {  nptStmCurrentEntry  16  }
		
	nptStmCurrentMinRxPower	OBJECT-TYPE	
		SYNTAX			DisplayString
		MAX-ACCESS		read-only
		STATUS			current
		DESCRIPTION		"The minimal receive optical power in monitored duration."
		::=  {  nptStmCurrentEntry  17  }
        
	nptStmCurrentTxPower	OBJECT-TYPE	
		SYNTAX			DisplayString
		MAX-ACCESS		read-only
		STATUS			current
		DESCRIPTION		"."
		::=  {  nptStmCurrentEntry  18  }
        
	nptStmTotalTable	OBJECT-TYPE
		SYNTAX		SEQUENCE  OF  NptStmTotalEntry
		MAX-ACCESS	not-accessible
		STATUS		current
		DESCRIPTION	"The STM current table contains various statistics
            being collected for the current 15 minute
            interval."
		::=  { nptStmIfGroup  2 }

	nptStmTotalEntry	OBJECT-TYPE
		SYNTAX		NptStmTotalEntry
		MAX-ACCESS	not-accessible
		STATUS		current
		DESCRIPTION	"An entry in the STM Total table."
		INDEX		{  nptStmTotalIndex  }
		::=  { nptStmTotalTable 1 }

	NptStmTotalEntry  ::=  SEQUENCE {
		nptStmTotalIndex  Integer32,
		nptStmTotalMoDescription  DisplayString,
		nptStmTotalRSES  Counter64,
		nptStmTotalRSSES  Counter64,
		nptStmTotalRSBBE  Counter64,
		nptStmTotalRSUAS  Counter64,
		nptStmTotalRSOFS  Counter64,
		nptStmTotalMSES  Counter64,
		nptStmTotalMSSES  Counter64,
		nptStmTotalMSBBE  Counter64,
		nptStmTotalMSUAS  Counter64,
		nptStmTotalMSFEES  Counter64,
		nptStmTotalMSFESES  Counter64,
		nptStmTotalMSFEBBE  Counter64,
		nptStmTotalMSFEUAS  Counter64,
		nptStmTotalMaxRxPower  DisplayString,
		nptStmTotalMinRxPower  DisplayString,
     		nptStmTotalTxPower  DisplayString
		}


	nptStmTotalIndex	OBJECT-TYPE	
		SYNTAX			Integer32  ( -2147483648 .. 2147483647  ) 
		MAX-ACCESS		read-only
		STATUS			current
		DESCRIPTION		"The index value which uniquely identifies  the
            STM interface to which this entry is applicable."
		::=  {  nptStmTotalEntry  1  }
		
		
	nptStmTotalMoDescription	OBJECT-TYPE	
		SYNTAX			DisplayString 
		MAX-ACCESS		read-only
		STATUS			current
		DESCRIPTION		"Mo Description"
		::=  {  nptStmTotalEntry  2  }


	nptStmTotalRSES	OBJECT-TYPE	
		SYNTAX			Counter64
		MAX-ACCESS		read-only
		STATUS			current
		DESCRIPTION		"The number of Errored Seconds.errored seconds. If errors occur within a certain second, this second is called an errored second."
		::=  {  nptStmTotalEntry  3  }


	nptStmTotalRSSES	OBJECT-TYPE	
		SYNTAX			Counter64
		MAX-ACCESS		read-only
		STATUS			current
		DESCRIPTION		"severely errored seconds. If there are errors in 30% of the frames, 
		the errors exceed the threshold, or the signal fails within a certain second, 
		this second is called a severely errored second. Errored seconds (ESs) are not counted when severely errored seconds occur."
		::=  {  nptStmTotalEntry  4  }


	nptStmTotalRSBBE	OBJECT-TYPE	
		SYNTAX			Counter64
		MAX-ACCESS		read-only
		STATUS			current
		DESCRIPTION		"background block errors. If there are errors in a frame of data, 
		this frame is counted as a block error. The background block error is the block error 
		with the number of severely errored seconds deducted from the counting interval."
		::=  {  nptStmTotalEntry  5  }


	nptStmTotalRSUAS	OBJECT-TYPE	
		SYNTAX			Counter64
		MAX-ACCESS		read-only
		STATUS			current
		DESCRIPTION		"unavailable seconds. When an SES lasts for 10 seconds, it becomes a UAS. 
		When there are no severely errored seconds within 10 seconds, it is no longer counted as a UAS. The UAS is not calculated in SES calculations."
		::=  {  nptStmTotalEntry  6  }


	nptStmTotalRSOFS	OBJECT-TYPE	
		SYNTAX			Counter64
		MAX-ACCESS		read-only
		STATUS			current
		DESCRIPTION		"out-of-frame seconds."
		::=  {  nptStmTotalEntry  7  }


	nptStmTotalMSES	OBJECT-TYPE	
		SYNTAX			Counter64
		MAX-ACCESS		read-only
		STATUS			current
		DESCRIPTION		"errored seconds. If errors occur within a certain second, this second is called an errored second."
		::=  {  nptStmTotalEntry  8  }


	nptStmTotalMSSES	OBJECT-TYPE	
		SYNTAX			Counter64
		MAX-ACCESS		read-only
		STATUS			current
		DESCRIPTION		"severely errored seconds. If there are errors in 30% of the frames, the 
		errors exceed the threshold, or the signal fails within a certain second, this second is 
		called a severely errored second. Errored seconds (ESs) are not counted when severely errored seconds occur."
		::=  {  nptStmTotalEntry  9  }


	nptStmTotalMSBBE	OBJECT-TYPE	
		SYNTAX			Counter64
		MAX-ACCESS		read-only
		STATUS			current
		DESCRIPTION		"background block errors. If there are errors in a frame of data, this frame
		is counted as a block error. The background block error is the block error with the number
		of severely errored seconds deducted from the counting interval."
		::=  {  nptStmTotalEntry  10  }


	nptStmTotalMSUAS	OBJECT-TYPE	
		SYNTAX			Counter64
		MAX-ACCESS		read-only
		STATUS			current
		DESCRIPTION		"unavailable seconds. When an SES lasts for 10 seconds, it becomes a 
		UAS. When there are no severely errored seconds within 10 seconds, it is no longer 
		counted as a UAS. The UAS is not calculated in SES calculations."
		::=  {  nptStmTotalEntry  11  }


	nptStmTotalMSFEES	OBJECT-TYPE	
		SYNTAX			Counter64
		MAX-ACCESS		read-only
		STATUS			current
		DESCRIPTION		"far-end errored seconds."
		::=  {  nptStmTotalEntry  12  }


	nptStmTotalMSFESES	OBJECT-TYPE	
		SYNTAX			Counter64
		MAX-ACCESS		read-only
		STATUS			current
		DESCRIPTION		"far-end severely errored seconds."
		::=  {  nptStmTotalEntry  13  }
		
	nptStmTotalMSFEBBE	OBJECT-TYPE	
		SYNTAX			Counter64
		MAX-ACCESS		read-only
		STATUS			current
		DESCRIPTION		"far-end background block errors."
		::=  {  nptStmTotalEntry  14  }
		
	nptStmTotalMSFEUAS	OBJECT-TYPE	
		SYNTAX			Counter64
		MAX-ACCESS		read-only
		STATUS			current
		DESCRIPTION		"far-end unavailable seconds."
		::=  {  nptStmTotalEntry  15  }
		
	nptStmTotalMaxRxPower	OBJECT-TYPE	
		SYNTAX			DisplayString
		MAX-ACCESS		read-only
		STATUS			current
		DESCRIPTION		"The maximal receive optical power in monitored duration."
		::=  {  nptStmTotalEntry  16  }
		
	nptStmTotalMinRxPower	OBJECT-TYPE	
		SYNTAX			DisplayString
		MAX-ACCESS		read-only
		STATUS			current
		DESCRIPTION		"The minimal receive optical power in monitored duration."
		::=  {  nptStmTotalEntry  17  }
		
	nptStmTotalTxPower	OBJECT-TYPE	
		SYNTAX			DisplayString
		MAX-ACCESS		read-only
		STATUS			current
		DESCRIPTION		"."
		::=  {  nptStmTotalEntry  18  }
        
	nptVc4CurrentTable	OBJECT-TYPE
		SYNTAX		SEQUENCE  OF  NptVc4CurrentEntry
		MAX-ACCESS	not-accessible
		STATUS		current
		DESCRIPTION	"The VC4 current table contains various statistics
            being collected for the current 15 minute
            interval."
		::=  { nptVc4IfGroup  1 }

	nptVc4CurrentEntry	OBJECT-TYPE
		SYNTAX		NptVc4CurrentEntry
		MAX-ACCESS	not-accessible
		STATUS		current
		DESCRIPTION	"An entry in the VC4 Current table."
		INDEX		{  nptVc4CurrentIndex  }
		::=  { nptVc4CurrentTable 1 }

	NptVc4CurrentEntry  ::=  SEQUENCE {
		nptVc4CurrentIndex  Integer32,
		nptVc4CurrentMoDescription  DisplayString,
		nptVc4CurrentAU4PPJC  Counter64,
		nptVc4CurrentAU4NPJC  Counter64,
		nptVc4CurrentES  Counter64,
		nptVc4CurrentSES  Counter64,
		nptVc4CurrentBBE  Counter64,
		nptVc4CurrentUAS  Counter64,
		nptVc4CurrentFEES  Counter64,
		nptVc4CurrentFESES  Counter64,
		nptVc4CurrentFEBBE  Counter64,
		nptVc4CurrentFEUAS  Counter64
		}


	nptVc4CurrentIndex	OBJECT-TYPE	
		SYNTAX			Integer32  ( -2147483648 .. 2147483647  ) 
		MAX-ACCESS		read-only
		STATUS			current
		DESCRIPTION		"The index value which uniquely identifies  the
            VC4 interface to which this entry is applicable."
		::=  {  nptVc4CurrentEntry  1  }
		
		
	nptVc4CurrentMoDescription	OBJECT-TYPE	
		SYNTAX			DisplayString 
		MAX-ACCESS		read-only
		STATUS			current
		DESCRIPTION		"Mo Description"
		::=  {  nptVc4CurrentEntry  2  }


	nptVc4CurrentAU4PPJC	OBJECT-TYPE	
		SYNTAX			Counter64
		MAX-ACCESS		read-only
		STATUS			current
		DESCRIPTION		"positive pointer justification events."
		::=  {  nptVc4CurrentEntry  3  }


	nptVc4CurrentAU4NPJC	OBJECT-TYPE	
		SYNTAX			Counter64
		MAX-ACCESS		read-only
		STATUS			current
		DESCRIPTION		"negative pointer justification events."
		::=  {  nptVc4CurrentEntry  4  }


	nptVc4CurrentES	OBJECT-TYPE	
		SYNTAX			Counter64
		MAX-ACCESS		read-only
		STATUS			current
		DESCRIPTION		"errored seconds. If errors occur within a certain second, this second is called an errored second."
		::=  {  nptVc4CurrentEntry  5  }


	nptVc4CurrentSES	OBJECT-TYPE	
		SYNTAX			Counter64
		MAX-ACCESS		read-only
		STATUS			current
		DESCRIPTION		"severely errored seconds. If there are errors in 30% of the frames, 
		the errors exceed the threshold, or the signal fails within a certain second, 
		this second is called a severely errored second. Errored seconds (ESs) are not counted when severely errored seconds occur."
		::=  {  nptVc4CurrentEntry  6  }


	nptVc4CurrentBBE	OBJECT-TYPE	
		SYNTAX			Counter64
		MAX-ACCESS		read-only
		STATUS			current
		DESCRIPTION		"background block errors. If there are errors in a frame of data, this frame is counted as a block error.
		The background block error is the block error with the number of severely errored seconds deducted from the counting interval."
		::=  {  nptVc4CurrentEntry  7  }


	nptVc4CurrentUAS	OBJECT-TYPE	
		SYNTAX			Counter64
		MAX-ACCESS		read-only
		STATUS			current
		DESCRIPTION		"unavailable seconds. When an SES lasts for 10 seconds, 
		it becomes a UAS. When there are no severely errored seconds within 10 seconds, 
		it is no longer counted as a UAS. The UAS is not calculated in SES calculations."
		::=  {  nptVc4CurrentEntry  8  }


	nptVc4CurrentFEES	OBJECT-TYPE	
		SYNTAX			Counter64
		MAX-ACCESS		read-only
		STATUS			current
		DESCRIPTION		"far-end errored seconds."
		::=  {  nptVc4CurrentEntry  9  }


	nptVc4CurrentFESES	OBJECT-TYPE	
		SYNTAX			Counter64
		MAX-ACCESS		read-only
		STATUS			current
		DESCRIPTION		"far-end severely errored seconds."
		::=  {  nptVc4CurrentEntry  10  }


	nptVc4CurrentFEBBE	OBJECT-TYPE	
		SYNTAX			Counter64
		MAX-ACCESS		read-only
		STATUS			current
		DESCRIPTION		"far-end background block errors."
		::=  {  nptVc4CurrentEntry  11  }


	nptVc4CurrentFEUAS	OBJECT-TYPE	
		SYNTAX			Counter64
		MAX-ACCESS		read-only
		STATUS			current
		DESCRIPTION		"far-end unavailable seconds."
		::=  {  nptVc4CurrentEntry  12  }
		
		nptVc4TotalTable	OBJECT-TYPE
		SYNTAX		SEQUENCE  OF  NptVc4TotalEntry
		MAX-ACCESS	not-accessible
		STATUS		current
		DESCRIPTION	"The VC4 current table contains various statistics
            being collected for the current 15 minute
            interval."
		::=  { nptVc4IfGroup  2 }

	nptVc4TotalEntry	OBJECT-TYPE
		SYNTAX		NptVc4TotalEntry
		MAX-ACCESS	not-accessible
		STATUS		current
		DESCRIPTION	"An entry in the VC4 Total table."
		INDEX		{  nptVc4TotalIndex  }
		::=  { nptVc4TotalTable 1 }

	NptVc4TotalEntry  ::=  SEQUENCE {
		nptVc4TotalIndex  Integer32,
		nptVc4TotalMoDescription  DisplayString,
		nptVc4TotalAU4PPJC  Counter64,
		nptVc4TotalAU4NPJC  Counter64,
		nptVc4TotalES  Counter64,
		nptVc4TotalSES  Counter64,
		nptVc4TotalBBE  Counter64,
		nptVc4TotalUAS  Counter64,
		nptVc4TotalFEES  Counter64,
		nptVc4TotalFESES  Counter64,
		nptVc4TotalFEBBE  Counter64,
		nptVc4TotalFEUAS  Counter64
		}


	nptVc4TotalIndex	OBJECT-TYPE	
		SYNTAX			Integer32  ( -2147483648 .. 2147483647  ) 
		MAX-ACCESS		read-only
		STATUS			current
		DESCRIPTION		"The index value which uniquely identifies  the
            VC4 interface to which this entry is applicable."
		::=  {  nptVc4TotalEntry  1  }
		
		
		
	nptVc4TotalMoDescription	OBJECT-TYPE	
		SYNTAX			DisplayString 
		MAX-ACCESS		read-only
		STATUS			current
		DESCRIPTION		"Mo Description"
		::=  {  nptVc4TotalEntry  2  }


	nptVc4TotalAU4PPJC	OBJECT-TYPE	
		SYNTAX			Counter64
		MAX-ACCESS		read-only
		STATUS			current
		DESCRIPTION		"positive pointer justification events."
		::=  {  nptVc4TotalEntry  3  }


	nptVc4TotalAU4NPJC	OBJECT-TYPE	
		SYNTAX			Counter64
		MAX-ACCESS		read-only
		STATUS			current
		DESCRIPTION		"negative pointer justification events."
		::=  {  nptVc4TotalEntry  4  }


	nptVc4TotalES	OBJECT-TYPE	
		SYNTAX			Counter64
		MAX-ACCESS		read-only
		STATUS			current
		DESCRIPTION		"errored seconds. If errors occur within a certain second, this second is called an errored second."
		::=  {  nptVc4TotalEntry  5  }


	nptVc4TotalSES	OBJECT-TYPE	
		SYNTAX			Counter64
		MAX-ACCESS		read-only
		STATUS			current
		DESCRIPTION		"severely errored seconds. If there are errors in 30% of the frames, 
		the errors exceed the threshold, or the signal fails within a certain second, 
		this second is called a severely errored second. Errored seconds (ESs) are not counted when severely errored seconds occur."
		::=  {  nptVc4TotalEntry  6  }


	nptVc4TotalBBE	OBJECT-TYPE	
		SYNTAX			Counter64
		MAX-ACCESS		read-only
		STATUS			current
		DESCRIPTION		"background block errors. If there are errors in a frame of data, this frame is counted as a block error.
		The background block error is the block error with the number of severely errored seconds deducted from the counting interval."
		::=  {  nptVc4TotalEntry  7  }


	nptVc4TotalUAS	OBJECT-TYPE	
		SYNTAX			Counter64
		MAX-ACCESS		read-only
		STATUS			current
		DESCRIPTION		"unavailable seconds. When an SES lasts for 10 seconds, 
		it becomes a UAS. When there are no severely errored seconds within 10 seconds, 
		it is no longer counted as a UAS. The UAS is not calculated in SES calculations."
		::=  {  nptVc4TotalEntry  8  }


	nptVc4TotalFEES	OBJECT-TYPE	
		SYNTAX			Counter64
		MAX-ACCESS		read-only
		STATUS			current
		DESCRIPTION		"far-end errored seconds."
		::=  {  nptVc4TotalEntry  9  }


	nptVc4TotalFESES	OBJECT-TYPE	
		SYNTAX			Counter64
		MAX-ACCESS		read-only
		STATUS			current
		DESCRIPTION		"far-end severely errored seconds."
		::=  {  nptVc4TotalEntry  10  }


	nptVc4TotalFEBBE	OBJECT-TYPE	
		SYNTAX			Counter64
		MAX-ACCESS		read-only
		STATUS			current
		DESCRIPTION		"far-end background block errors."
		::=  {  nptVc4TotalEntry  11  }


	nptVc4TotalFEUAS	OBJECT-TYPE	
		SYNTAX			Counter64
		MAX-ACCESS		read-only
		STATUS			current
		DESCRIPTION		"far-end unavailable seconds."
		::=  {  nptVc4TotalEntry  12  }
		
		nptVc12CurrentTable	OBJECT-TYPE
		SYNTAX		SEQUENCE  OF  NptVc12CurrentEntry
		MAX-ACCESS	not-accessible
		STATUS		current
		DESCRIPTION	"The VC12 current table contains various statistics
            being collected for the current 15 minute
            interval."
		::=  { nptVc12IfGroup  1 }

	nptVc12CurrentEntry	OBJECT-TYPE
		SYNTAX		NptVc12CurrentEntry
		MAX-ACCESS	not-accessible
		STATUS		current
		DESCRIPTION	"An entry in the VC12 Current table."
		INDEX		{  nptVc12CurrentIndex  }
		::=  { nptVc12CurrentTable 1 }

	NptVc12CurrentEntry  ::=  SEQUENCE {
		nptVc12CurrentIndex  Integer32,
		nptVc12CurrentMoDescription  DisplayString,
		nptVc12CurrentTU12PPJC  Counter64,
		nptVc12CurrentTU12NPJC  Counter64,
		nptVc12CurrentES  Counter64,
		nptVc12CurrentSES  Counter64,
		nptVc12CurrentBBE  Counter64,
		nptVc12CurrentUAS  Counter64,
		nptVc12CurrentFEES  Counter64,
		nptVc12CurrentFESES  Counter64,
		nptVc12CurrentFEBBE  Counter64,
		nptVc12CurrentFEUAS  Counter64
		}


	nptVc12CurrentIndex	OBJECT-TYPE	
		SYNTAX			Integer32  ( -2147483648 .. 2147483647  ) 
		MAX-ACCESS		read-only
		STATUS			current
		DESCRIPTION		"The index value which uniquely identifies  the
            VC12 interface to which this entry is applicable."
		::=  {  nptVc12CurrentEntry  1  }
		
		
	nptVc12CurrentMoDescription	OBJECT-TYPE	
		SYNTAX			DisplayString 
		MAX-ACCESS		read-only
		STATUS			current
		DESCRIPTION		"Mo Description"
		::=  {  nptVc12CurrentEntry  2  }


	nptVc12CurrentTU12PPJC	OBJECT-TYPE	
		SYNTAX			Counter64
		MAX-ACCESS		read-only
		STATUS			current
		DESCRIPTION		"positive pointer justification events."
		::=  {  nptVc12CurrentEntry  3  }


	nptVc12CurrentTU12NPJC	OBJECT-TYPE	
		SYNTAX			Counter64
		MAX-ACCESS		read-only
		STATUS			current
		DESCRIPTION		"negative pointer justification events."
		::=  {  nptVc12CurrentEntry  4  }


	nptVc12CurrentES	OBJECT-TYPE	
		SYNTAX			Counter64
		MAX-ACCESS		read-only
		STATUS			current
		DESCRIPTION		"errored seconds. If errors occur within a certain second, this second is called an errored second."
		::=  {  nptVc12CurrentEntry  5  }


	nptVc12CurrentSES	OBJECT-TYPE	
		SYNTAX			Counter64
		MAX-ACCESS		read-only
		STATUS			current
		DESCRIPTION		"severely errored seconds. If there are errors in 30% of the frames, 
		the errors exceed the threshold, or the signal fails within a certain second, 
		this second is called a severely errored second. Errored seconds (ESs) are not counted when severely errored seconds occur."
		::=  {  nptVc12CurrentEntry  6  }


	nptVc12CurrentBBE	OBJECT-TYPE	
		SYNTAX			Counter64
		MAX-ACCESS		read-only
		STATUS			current
		DESCRIPTION		"background block errors. If there are errors in a frame of data, this frame is counted as a block error.
		The background block error is the block error with the number of severely errored seconds deducted from the counting interval."
		::=  {  nptVc12CurrentEntry  7  }


	nptVc12CurrentUAS	OBJECT-TYPE	
		SYNTAX			Counter64
		MAX-ACCESS		read-only
		STATUS			current
		DESCRIPTION		"unavailable seconds. When an SES lasts for 10 seconds, 
		it becomes a UAS. When there are no severely errored seconds within 10 seconds, 
		it is no longer counted as a UAS. The UAS is not calculated in SES calculations."
		::=  {  nptVc12CurrentEntry  8  }


	nptVc12CurrentFEES	OBJECT-TYPE	
		SYNTAX			Counter64
		MAX-ACCESS		read-only
		STATUS			current
		DESCRIPTION		"far-end errored seconds."
		::=  {  nptVc12CurrentEntry  9  }


	nptVc12CurrentFESES	OBJECT-TYPE	
		SYNTAX			Counter64
		MAX-ACCESS		read-only
		STATUS			current
		DESCRIPTION		"far-end severely errored seconds."
		::=  {  nptVc12CurrentEntry  10  }


	nptVc12CurrentFEBBE	OBJECT-TYPE	
		SYNTAX			Counter64
		MAX-ACCESS		read-only
		STATUS			current
		DESCRIPTION		"far-end background block errors."
		::=  {  nptVc12CurrentEntry  11  }


	nptVc12CurrentFEUAS	OBJECT-TYPE	
		SYNTAX			Counter64
		MAX-ACCESS		read-only
		STATUS			current
		DESCRIPTION		"far-end unavailable seconds."
		::=  {  nptVc12CurrentEntry  12  }
		
		nptVc12TotalTable	OBJECT-TYPE
		SYNTAX		SEQUENCE  OF  NptVc12TotalEntry
		MAX-ACCESS	not-accessible
		STATUS		current
		DESCRIPTION	"The VC12 current table contains various statistics
            being collected for the current 15 minute
            interval."
		::=  { nptVc12IfGroup  2 }

	nptVc12TotalEntry	OBJECT-TYPE
		SYNTAX		NptVc12TotalEntry
		MAX-ACCESS	not-accessible
		STATUS		current
		DESCRIPTION	"An entry in the VC12 Total table."
		INDEX		{  nptVc12TotalIndex  }
		::=  { nptVc12TotalTable 1 }

	NptVc12TotalEntry  ::=  SEQUENCE {
		nptVc12TotalIndex  Integer32,
		nptVc12TotalMoDescription  DisplayString,
		nptVc12TotalTU12PPJC  Counter64,
		nptVc12TotalTU12NPJC  Counter64,
		nptVc12TotalES  Counter64,
		nptVc12TotalSES  Counter64,
		nptVc12TotalBBE  Counter64,
		nptVc12TotalUAS  Counter64,
		nptVc12TotalFEES  Counter64,
		nptVc12TotalFESES  Counter64,
		nptVc12TotalFEBBE  Counter64,
		nptVc12TotalFEUAS  Counter64
		}


	nptVc12TotalIndex	OBJECT-TYPE	
		SYNTAX			Integer32  ( -2147483648 .. 2147483647  ) 
		MAX-ACCESS		read-only
		STATUS			current
		DESCRIPTION		"The index value which uniquely identifies  the
            VC12 interface to which this entry is applicable."
		::=  {  nptVc12TotalEntry  1  }
		
		
	nptVc12TotalMoDescription	OBJECT-TYPE	
		SYNTAX			DisplayString 
		MAX-ACCESS		read-only
		STATUS			current
		DESCRIPTION		"Mo Description"
		::=  {  nptVc12TotalEntry  2  }


	nptVc12TotalTU12PPJC	OBJECT-TYPE	
		SYNTAX			Counter64
		MAX-ACCESS		read-only
		STATUS			current
		DESCRIPTION		"positive pointer justification events."
		::=  {  nptVc12TotalEntry  3  }


	nptVc12TotalTU12NPJC	OBJECT-TYPE	
		SYNTAX			Counter64
		MAX-ACCESS		read-only
		STATUS			current
		DESCRIPTION		"negative pointer justification events."
		::=  {  nptVc12TotalEntry  4  }


	nptVc12TotalES	OBJECT-TYPE	
		SYNTAX			Counter64
		MAX-ACCESS		read-only
		STATUS			current
		DESCRIPTION		"errored seconds. If errors occur within a certain second, this second is called an errored second."
		::=  {  nptVc12TotalEntry  5  }


	nptVc12TotalSES	OBJECT-TYPE	
		SYNTAX			Counter64
		MAX-ACCESS		read-only
		STATUS			current
		DESCRIPTION		"severely errored seconds. If there are errors in 30% of the frames, 
		the errors exceed the threshold, or the signal fails within a certain second, 
		this second is called a severely errored second. Errored seconds (ESs) are not counted when severely errored seconds occur."
		::=  {  nptVc12TotalEntry  6  }


	nptVc12TotalBBE	OBJECT-TYPE	
		SYNTAX			Counter64
		MAX-ACCESS		read-only
		STATUS			current
		DESCRIPTION		"background block errors. If there are errors in a frame of data, this frame is counted as a block error.
		The background block error is the block error with the number of severely errored seconds deducted from the counting interval."
		::=  {  nptVc12TotalEntry  7  }


	nptVc12TotalUAS	OBJECT-TYPE	
		SYNTAX			Counter64
		MAX-ACCESS		read-only
		STATUS			current
		DESCRIPTION		"unavailable seconds. When an SES lasts for 10 seconds, 
		it becomes a UAS. When there are no severely errored seconds within 10 seconds, 
		it is no longer counted as a UAS. The UAS is not calculated in SES calculations."
		::=  {  nptVc12TotalEntry  8  }


	nptVc12TotalFEES	OBJECT-TYPE	
		SYNTAX			Counter64
		MAX-ACCESS		read-only
		STATUS			current
		DESCRIPTION		"far-end errored seconds."
		::=  {  nptVc12TotalEntry  9  }


	nptVc12TotalFESES	OBJECT-TYPE	
		SYNTAX			Counter64
		MAX-ACCESS		read-only
		STATUS			current
		DESCRIPTION		"far-end severely errored seconds."
		::=  {  nptVc12TotalEntry  10  }


	nptVc12TotalFEBBE	OBJECT-TYPE	
		SYNTAX			Counter64
		MAX-ACCESS		read-only
		STATUS			current
		DESCRIPTION		"far-end background block errors."
		::=  {  nptVc12TotalEntry  11  }


	nptVc12TotalFEUAS	OBJECT-TYPE	
		SYNTAX			Counter64
		MAX-ACCESS		read-only
		STATUS			current
		DESCRIPTION		"far-end unavailable seconds."
		::=  {  nptVc12TotalEntry  12  }
		
		nptE1ppiCurrentTable	OBJECT-TYPE
		SYNTAX		SEQUENCE  OF  NptE1ppiCurrentEntry
		MAX-ACCESS	not-accessible
		STATUS		current
		DESCRIPTION	"The E1ppi current table contains various statistics
            being collected for the current 15 minute
            interval."
		::=  { nptE1ppiIfGroup  1 }

	nptE1ppiCurrentEntry	OBJECT-TYPE
		SYNTAX		NptE1ppiCurrentEntry
		MAX-ACCESS	not-accessible
		STATUS		current
		DESCRIPTION	"An entry in the E1ppi Current table."
		INDEX		{  nptE1ppiCurrentIndex  }
		::=  { nptE1ppiCurrentTable 1 }

	NptE1ppiCurrentEntry  ::=  SEQUENCE {
		nptE1ppiCurrentIndex  Integer32,
		nptE1ppiCurrentMoDescription  DisplayString,
		nptE1ppiCurrentCV  Counter64,
		nptE1ppiCurrentES  Counter64,
		nptE1ppiCurrentSES  Counter64,
		nptE1ppiCurrentLOSS  Counter64,
		nptE1ppiCurrentUAS  Counter64
		}


	nptE1ppiCurrentIndex	OBJECT-TYPE	
		SYNTAX			Integer32  ( -2147483648 .. 2147483647  ) 
		MAX-ACCESS		read-only
		STATUS			current
		DESCRIPTION		"The index value which uniquely identifies  the
            E1ppi interface to which this entry is applicable."
		::=  {  nptE1ppiCurrentEntry  1  }
		
	nptE1ppiCurrentMoDescription	OBJECT-TYPE	
		SYNTAX			DisplayString 
		MAX-ACCESS		read-only
		STATUS			current
		DESCRIPTION		"Mo Description"
		::=  {  nptE1ppiCurrentEntry  2  }

	nptE1ppiCurrentCV	OBJECT-TYPE	
		SYNTAX			Counter64
		MAX-ACCESS		read-only
		STATUS			current
		DESCRIPTION		"Coding Violations."
		::=  {  nptE1ppiCurrentEntry  3  }


	nptE1ppiCurrentES	OBJECT-TYPE	
		SYNTAX			Counter64
		MAX-ACCESS		read-only
		STATUS			current
		DESCRIPTION		"errored seconds. a count of seconds during which one or more of the following has occurred: CVs, LOSs."
		::=  {  nptE1ppiCurrentEntry  4  }


	nptE1ppiCurrentSES	OBJECT-TYPE	
		SYNTAX			Counter64
		MAX-ACCESS		read-only
		STATUS			current
		DESCRIPTION		"severely errored seconds. If there are errors in 30% of the frames, 
		the errors exceed the threshold, or the signal fails within a certain second, 
		this second is called a severely errored second. Errored seconds (ESs) are not counted when severely errored seconds occur."
		::=  {  nptE1ppiCurrentEntry  5  }


	nptE1ppiCurrentLOSS	OBJECT-TYPE	
		SYNTAX			Counter64
		MAX-ACCESS		read-only
		STATUS			current
		DESCRIPTION		"A count of 1-second intervals containing one or more LOS defects."
		::=  {  nptE1ppiCurrentEntry  6  }


	nptE1ppiCurrentUAS	OBJECT-TYPE	
		SYNTAX			Counter64
		MAX-ACCESS		read-only
		STATUS			current
		DESCRIPTION		"Description"
		::=  {  nptE1ppiCurrentEntry  7  }
		
		nptE1ppiTotalTable	OBJECT-TYPE
		SYNTAX		SEQUENCE  OF  NptE1ppiTotalEntry
		MAX-ACCESS	not-accessible
		STATUS		current
		DESCRIPTION	"The E1ppi current table contains various statistics
            being collected for the current 15 minute
            interval."
		::=  { nptE1ppiIfGroup  2 }

	nptE1ppiTotalEntry	OBJECT-TYPE
		SYNTAX		NptE1ppiTotalEntry
		MAX-ACCESS	not-accessible
		STATUS		current
		DESCRIPTION	"An entry in the E1ppi Total table."
		INDEX		{  nptE1ppiTotalIndex  }
		::=  { nptE1ppiTotalTable 1 }

	NptE1ppiTotalEntry  ::=  SEQUENCE {
		nptE1ppiTotalIndex  Integer32,
		nptE1ppiTotalMoDescription  DisplayString,
		nptE1ppiTotalCV  Counter64,
		nptE1ppiTotalES  Counter64,
		nptE1ppiTotalSES  Counter64,
		nptE1ppiTotalLOSS  Counter64,
		nptE1ppiTotalUAS  Counter64
		}


	nptE1ppiTotalIndex	OBJECT-TYPE	
		SYNTAX			Integer32  ( -2147483648 .. 2147483647  ) 
		MAX-ACCESS		read-only
		STATUS			current
		DESCRIPTION		"The index value which uniquely identifies  the
            E1ppi interface to which this entry is applicable."
		::=  {  nptE1ppiTotalEntry  1  }
		
		
	nptE1ppiTotalMoDescription	OBJECT-TYPE	
		SYNTAX			DisplayString 
		MAX-ACCESS		read-only
		STATUS			current
		DESCRIPTION		"Mo Description"
		::=  {  nptE1ppiTotalEntry  2  }

	nptE1ppiTotalCV	OBJECT-TYPE	
		SYNTAX			Counter64
		MAX-ACCESS		read-only
		STATUS			current
		DESCRIPTION		"Coding Violations."
		::=  {  nptE1ppiTotalEntry  3  }


	nptE1ppiTotalES	OBJECT-TYPE	
		SYNTAX			Counter64
		MAX-ACCESS		read-only
		STATUS			current
		DESCRIPTION		"errored seconds. a count of seconds during which one or more of the following has occurred: CVs, LOSs."
		::=  {  nptE1ppiTotalEntry  4  }


	nptE1ppiTotalSES	OBJECT-TYPE	
		SYNTAX			Counter64
		MAX-ACCESS		read-only
		STATUS			current
		DESCRIPTION		"severely errored seconds. If there are errors in 30% of the frames, 
		the errors exceed the threshold, or the signal fails within a certain second, 
		this second is called a severely errored second. Errored seconds (ESs) are not counted when severely errored seconds occur."
		::=  {  nptE1ppiTotalEntry  5  }


	nptE1ppiTotalLOSS	OBJECT-TYPE	
		SYNTAX			Counter64
		MAX-ACCESS		read-only
		STATUS			current
		DESCRIPTION		"A count of 1-second intervals containing one or more LOS defects."
		::=  {  nptE1ppiTotalEntry  6  }


	nptE1ppiTotalUAS	OBJECT-TYPE	
		SYNTAX			Counter64
		MAX-ACCESS		read-only
		STATUS			current
		DESCRIPTION		"Description"
		::=  {  nptE1ppiTotalEntry  7  }
		
	nptE1CurrentTable	OBJECT-TYPE
		SYNTAX		SEQUENCE  OF  NptE1CurrentEntry
		MAX-ACCESS	not-accessible
		STATUS		current
		DESCRIPTION	"The E1 current table contains various statistics
            being collected for the current 15 minute
            interval."
		::=  { nptE1IfGroup  1 }

	nptE1CurrentEntry	OBJECT-TYPE
		SYNTAX		NptE1CurrentEntry
		MAX-ACCESS	not-accessible
		STATUS		current
		DESCRIPTION	"An entry in the E1 Current table."
		INDEX		{  nptE1CurrentIndex  }
		::=  { nptE1CurrentTable 1 }

	NptE1CurrentEntry  ::=  SEQUENCE {
		nptE1CurrentIndex  Integer32,
		nptE1CurrentMoDescription  DisplayString,
		nptE1CurrentES  Counter64,
		nptE1CurrentSES  Counter64,
		nptE1CurrentBBE  Counter64,
		nptE1CurrentUAS  Counter64,
		nptE1CurrentFEES  Counter64,
		nptE1CurrentFESES  Counter64,
		nptE1CurrentFEBBE  Counter64,
		nptE1CurrentFEUAS  Counter64
		}


	nptE1CurrentIndex	OBJECT-TYPE	
		SYNTAX			Integer32  ( -2147483648 .. 2147483647  ) 
		MAX-ACCESS		read-only
		STATUS			current
		DESCRIPTION		"The index value which uniquely identifies  the
            E1 interface to which this entry is applicable."
		::=  {  nptE1CurrentEntry  1  }
		
		
	nptE1CurrentMoDescription	OBJECT-TYPE	
		SYNTAX			DisplayString 
		MAX-ACCESS		read-only
		STATUS			current
		DESCRIPTION		"Mo Description"
		::=  {  nptE1CurrentEntry  2  }
		

	nptE1CurrentES	OBJECT-TYPE	
		SYNTAX			Counter64
		MAX-ACCESS		read-only
		STATUS			current
		DESCRIPTION		"errored seconds. If errors occur within a certain second, this second is called an errored second."
		::=  {  nptE1CurrentEntry  3  }


	nptE1CurrentSES	OBJECT-TYPE	
		SYNTAX			Counter64
		MAX-ACCESS		read-only
		STATUS			current
		DESCRIPTION		"severely errored seconds. If there are errors in 30% of the frames, 
		the errors exceed the threshold, or the signal fails within a certain second, 
		this second is called a severely errored second. Errored seconds (ESs) are not counted when severely errored seconds occur."
		::=  {  nptE1CurrentEntry  4  }


	nptE1CurrentBBE	OBJECT-TYPE	
		SYNTAX			Counter64
		MAX-ACCESS		read-only
		STATUS			current
		DESCRIPTION		"background block errors. If there are errors in a frame of data, this frame is counted as a block error.
		The background block error is the block error with the number of severely errored seconds deducted from the counting interval."
		::=  {  nptE1CurrentEntry  5  }


	nptE1CurrentUAS	OBJECT-TYPE	
		SYNTAX			Counter64
		MAX-ACCESS		read-only
		STATUS			current
		DESCRIPTION		"unavailable seconds. When an SES lasts for 10 seconds, 
		it becomes a UAS. When there are no severely errored seconds within 10 seconds, 
		it is no longer counted as a UAS. The UAS is not calculated in SES calculations."
		::=  {  nptE1CurrentEntry  6  }


	nptE1CurrentFEES	OBJECT-TYPE	
		SYNTAX			Counter64
		MAX-ACCESS		read-only
		STATUS			current
		DESCRIPTION		"far-end errored seconds."
		::=  {  nptE1CurrentEntry  7  }


	nptE1CurrentFESES	OBJECT-TYPE	
		SYNTAX			Counter64
		MAX-ACCESS		read-only
		STATUS			current
		DESCRIPTION		"far-end severely errored seconds."
		::=  {  nptE1CurrentEntry  8  }


	nptE1CurrentFEBBE	OBJECT-TYPE	
		SYNTAX			Counter64
		MAX-ACCESS		read-only
		STATUS			current
		DESCRIPTION		"far-end background block errors."
		::=  {  nptE1CurrentEntry  9  }


	nptE1CurrentFEUAS	OBJECT-TYPE	
		SYNTAX			Counter64
		MAX-ACCESS		read-only
		STATUS			current
		DESCRIPTION		"far-end unavailable seconds."
		::=  {  nptE1CurrentEntry  10  }
		
		nptE1TotalTable	OBJECT-TYPE
		SYNTAX		SEQUENCE  OF  NptE1TotalEntry
		MAX-ACCESS	not-accessible
		STATUS		current
		DESCRIPTION	"The E1 current table contains various statistics
            being collected for the current 15 minute
            interval."
		::=  { nptE1IfGroup  2 }

	nptE1TotalEntry	OBJECT-TYPE
		SYNTAX		NptE1TotalEntry
		MAX-ACCESS	not-accessible
		STATUS		current
		DESCRIPTION	"An entry in the E1 Total table."
		INDEX		{  nptE1TotalIndex  }
		::=  { nptE1TotalTable 1 }

	NptE1TotalEntry  ::=  SEQUENCE {
		nptE1TotalIndex  Integer32,
		nptE1TotalMoDescription  DisplayString,
		nptE1TotalES  Counter64,
		nptE1TotalSES  Counter64,
		nptE1TotalBBE  Counter64,
		nptE1TotalUAS  Counter64,
		nptE1TotalFEES  Counter64,
		nptE1TotalFESES  Counter64,
		nptE1TotalFEBBE  Counter64,
		nptE1TotalFEUAS  Counter64
		}


	nptE1TotalIndex	OBJECT-TYPE	
		SYNTAX			Integer32  ( -2147483648 .. 2147483647  ) 
		MAX-ACCESS		read-only
		STATUS			current
		DESCRIPTION		"The index value which uniquely identifies  the
            E1 interface to which this entry is applicable."
		::=  {  nptE1TotalEntry  1  }
		
		
	nptE1TotalMoDescription	OBJECT-TYPE	
		SYNTAX			DisplayString 
		MAX-ACCESS		read-only
		STATUS			current
		DESCRIPTION		"Mo Description"
		::=  {  nptE1TotalEntry  2  }
	

	nptE1TotalES	OBJECT-TYPE	
		SYNTAX			Counter64
		MAX-ACCESS		read-only
		STATUS			current
		DESCRIPTION		"errored seconds. If errors occur within a certain second, this second is called an errored second."
		::=  {  nptE1TotalEntry  3  }


	nptE1TotalSES	OBJECT-TYPE	
		SYNTAX			Counter64
		MAX-ACCESS		read-only
		STATUS			current
		DESCRIPTION		"severely errored seconds. If there are errors in 30% of the frames, 
		the errors exceed the threshold, or the signal fails within a certain second, 
		this second is called a severely errored second. Errored seconds (ESs) are not counted when severely errored seconds occur."
		::=  {  nptE1TotalEntry  4  }


	nptE1TotalBBE	OBJECT-TYPE	
		SYNTAX			Counter64
		MAX-ACCESS		read-only
		STATUS			current
		DESCRIPTION		"background block errors. If there are errors in a frame of data, this frame is counted as a block error.
		The background block error is the block error with the number of severely errored seconds deducted from the counting interval."
		::=  {  nptE1TotalEntry  5  }


	nptE1TotalUAS	OBJECT-TYPE	
		SYNTAX			Counter64
		MAX-ACCESS		read-only
		STATUS			current
		DESCRIPTION		"unavailable seconds. When an SES lasts for 10 seconds, 
		it becomes a UAS. When there are no severely errored seconds within 10 seconds, 
		it is no longer counted as a UAS. The UAS is not calculated in SES calculations."
		::=  {  nptE1TotalEntry  6  }


	nptE1TotalFEES	OBJECT-TYPE	
		SYNTAX			Counter64
		MAX-ACCESS		read-only
		STATUS			current
		DESCRIPTION		"far-end errored seconds."
		::=  {  nptE1TotalEntry  7  }


	nptE1TotalFESES	OBJECT-TYPE	
		SYNTAX			Counter64
		MAX-ACCESS		read-only
		STATUS			current
		DESCRIPTION		"far-end severely errored seconds."
		::=  {  nptE1TotalEntry  8  }


	nptE1TotalFEBBE	OBJECT-TYPE	
		SYNTAX			Counter64
		MAX-ACCESS		read-only
		STATUS			current
		DESCRIPTION		"far-end background block errors."
		::=  {  nptE1TotalEntry  9  }


	nptE1TotalFEUAS	OBJECT-TYPE	
		SYNTAX			Counter64
		MAX-ACCESS		read-only
		STATUS			current
		DESCRIPTION		"far-end unavailable seconds."
		::=  {  nptE1TotalEntry  10  }
		
	nptOcCurrentTable	OBJECT-TYPE
		SYNTAX		SEQUENCE  OF  NptOcCurrentEntry
		MAX-ACCESS	not-accessible
		STATUS		current
		DESCRIPTION	"The OC current table contains various statistics
            being collected for the current 15 minute
            interval."
		::=  { nptOcIfGroup  1 }

	nptOcCurrentEntry	OBJECT-TYPE
		SYNTAX		NptOcCurrentEntry
		MAX-ACCESS	not-accessible
		STATUS		current
		DESCRIPTION	"An entry in the OC Current table."
		INDEX		{  nptOcCurrentIndex  }
		::=  { nptOcCurrentTable 1 }

	NptOcCurrentEntry  ::=  SEQUENCE {
		nptOcCurrentIndex  Integer32,
		nptOcCurrentMoDescription  DisplayString,
		nptOcCurrentESS  Counter64,
		nptOcCurrentSESS  Counter64,
		nptOcCurrentCVS  Counter64,
		nptOcCurrentSEFSS  Counter64,
		nptOcCurrentESL  Counter64,
		nptOcCurrentSESL  Counter64,
		nptOcCurrentCVL  Counter64,
		nptOcCurrentUASL  Counter64,
		nptOcCurrentFCL  Counter64,
		nptOcCurrentESLFE  Counter64,
		nptOcCurrentSESLFE  Counter64,
		nptOcCurrentCVLFE  Counter64,
		nptOcCurrentUASLFE  Counter64,
		nptOcCurrentFCLFE  Counter64,
		nptOcCurrentPSC  Counter64,
		nptOcCurrentPSD  Counter64,
		nptOcCurrentMaxRxPower  DisplayString,
		nptOcCurrentMinRxPower  DisplayString,
		nptOcCurrentTxPower  DisplayString
		}


	nptOcCurrentIndex	OBJECT-TYPE	
		SYNTAX			Integer32  ( -2147483648 .. 2147483647  ) 
		MAX-ACCESS		read-only
		STATUS			current
		DESCRIPTION		"The index value which uniquely identifies  the
            OC interface to which this entry is applicable."
		::=  {  nptOcCurrentEntry  1  }
		
		
	nptOcCurrentMoDescription	OBJECT-TYPE	
		SYNTAX			DisplayString 
		MAX-ACCESS		read-only
		STATUS			current
		DESCRIPTION		"Mo Description"
		::=  {  nptOcCurrentEntry  2  }


	nptOcCurrentESS	OBJECT-TYPE	
		SYNTAX			Counter64
		MAX-ACCESS		read-only
		STATUS			current
		DESCRIPTION		"errored seconds. If errors occur within a certain second, this second is called an errored second."
		::=  {  nptOcCurrentEntry  3  }


	nptOcCurrentSESS	OBJECT-TYPE	
		SYNTAX			Counter64
		MAX-ACCESS		read-only
		STATUS			current
		DESCRIPTION		"severely errored seconds. If there are errors in 30% of the frames, the errors exceed the threshold, 
		or the signal fails within a certain second, this second is called a severely errored second. 
		Errored seconds (ESs) are not counted when severely errored seconds occur."
		::=  {  nptOcCurrentEntry  4  }


	nptOcCurrentCVS 	OBJECT-TYPE	
		SYNTAX			Counter64
		MAX-ACCESS		read-only
		STATUS			current
		DESCRIPTION		"Section Coding Violations a count of BIP errors detected at the Section layer."
		::=  {  nptOcCurrentEntry  5  }


	nptOcCurrentSEFSS	OBJECT-TYPE	
		SYNTAX			Counter64
		MAX-ACCESS		read-only
		STATUS			current
		DESCRIPTION		"Section Severely Errored Framing Seconds."
		::=  {  nptOcCurrentEntry  6  }


	nptOcCurrentESL	OBJECT-TYPE	
		SYNTAX			Counter64
		MAX-ACCESS		read-only
		STATUS			current
		DESCRIPTION		"errored seconds. If errors occur within a certain second, this second is called an errored second."
		::=  {  nptOcCurrentEntry  7  }


	nptOcCurrentSESL	OBJECT-TYPE	
		SYNTAX			Counter64
		MAX-ACCESS		read-only
		STATUS			current
		DESCRIPTION		"severely errored seconds. If there are errors in 30% of the frames, the errors exceed the threshold, 
		or the signal fails within a certain second, this second is called a severely errored second. 
		Errored seconds (ESs) are not counted when severely errored seconds occur."
		::=  {  nptOcCurrentEntry  8  }


	nptOcCurrentCVL	OBJECT-TYPE	
		SYNTAX			Counter64
		MAX-ACCESS		read-only
		STATUS			current
		DESCRIPTION		"Near-end Line Coding Violations.a count of BIP errors detected at the Line layer"
		::=  {  nptOcCurrentEntry  9  }


	nptOcCurrentUASL	OBJECT-TYPE	
		SYNTAX			Counter64
		MAX-ACCESS		read-only
		STATUS			current
		DESCRIPTION		"unavailable seconds. When an SES lasts for 10 seconds, it becomes a UAS. 
		When there are no severely errored seconds within 10 seconds, it is no longer counted as a UAS. The UAS is not calculated in SES calculations."
		::=  {  nptOcCurrentEntry  10  }


	nptOcCurrentFCL	OBJECT-TYPE	
		SYNTAX			Counter64
		MAX-ACCESS		read-only
		STATUS			current
		DESCRIPTION		"Near-end Line Failure Counts. A failure event begins when the AIS-L failure is declared, and ends when the failure is cleared."
		::=  {  nptOcCurrentEntry  11  }


	nptOcCurrentESLFE	OBJECT-TYPE	
		SYNTAX			Counter64
		MAX-ACCESS		read-only
		STATUS			current
		DESCRIPTION		"far-end errored seconds."
		::=  {  nptOcCurrentEntry  12  }


	nptOcCurrentSESLFE	OBJECT-TYPE	
		SYNTAX			Counter64
		MAX-ACCESS		read-only
		STATUS			current
		DESCRIPTION		"far-end severely errored seconds."
		::=  {  nptOcCurrentEntry  13  }
		
	nptOcCurrentCVLFE	OBJECT-TYPE	
		SYNTAX			Counter64
		MAX-ACCESS		read-only
		STATUS			current
		DESCRIPTION		"Far-end Line Coding Violations."
		::=  {  nptOcCurrentEntry  14  }
		
	nptOcCurrentUASLFE	OBJECT-TYPE	
		SYNTAX			Counter64
		MAX-ACCESS		read-only
		STATUS			current
		DESCRIPTION		"far-end unavailable seconds."
		::=  {  nptOcCurrentEntry  15  }
		
	nptOcCurrentFCLFE	OBJECT-TYPE	
		SYNTAX			Counter64
		MAX-ACCESS		read-only
		STATUS			current
		DESCRIPTION		"Far-end Line Failure Counts."
		::=  {  nptOcCurrentEntry  16  }
		
	nptOcCurrentPSC	OBJECT-TYPE	
		SYNTAX			Counter64
		MAX-ACCESS		read-only
		STATUS			current
		DESCRIPTION		"Protection Switching Counts. a count of the number of times that service has been switched."
		::=  {  nptOcCurrentEntry  17  }
		
	nptOcCurrentPSD	OBJECT-TYPE	
		SYNTAX			Counter64
		MAX-ACCESS		read-only
		STATUS			current
		DESCRIPTION		"Protection Switching Duration. a count of the seconds that service was being carried on the protection line."
		::=  {  nptOcCurrentEntry  18  }
		
		
	nptOcCurrentMaxRxPower	OBJECT-TYPE	
		SYNTAX			DisplayString
		MAX-ACCESS		read-only
		STATUS			current
		DESCRIPTION		"The maximal receive optical power in monitored duration."
		::=  {  nptOcCurrentEntry  19  }
		
	nptOcCurrentMinRxPower	OBJECT-TYPE	
		SYNTAX			DisplayString
		MAX-ACCESS		read-only
		STATUS			current
		DESCRIPTION		"The minimal receive optical power in monitored duration."
		::=  {  nptOcCurrentEntry  20  }
        
        
	nptOcCurrentTxPower	OBJECT-TYPE	
		SYNTAX			DisplayString
		MAX-ACCESS		read-only
		STATUS			current
		DESCRIPTION		"."
		::=  {  nptOcCurrentEntry  21  }
	
	nptOcTotalTable	OBJECT-TYPE
		SYNTAX		SEQUENCE  OF  NptOcTotalEntry
		MAX-ACCESS	not-accessible
		STATUS		current
		DESCRIPTION	"The OC current table contains various statistics
            being collected for the current 15 minute
            interval."
		::=  { nptOcIfGroup  2 }

	nptOcTotalEntry	OBJECT-TYPE
		SYNTAX		NptOcTotalEntry
		MAX-ACCESS	not-accessible
		STATUS		current
		DESCRIPTION	"An entry in the OC Total table."
		INDEX		{  nptOcTotalIndex  }
		::=  { nptOcTotalTable 1 }

	NptOcTotalEntry  ::=  SEQUENCE {
		nptOcTotalIndex  Integer32,
		nptOcTotalMoDescription  DisplayString,
		nptOcTotalESS  Counter64,
		nptOcTotalSESS  Counter64,
		nptOcTotalCVS  Counter64,
		nptOcTotalSEFSS  Counter64,
		nptOcTotalESL  Counter64,
		nptOcTotalSESL  Counter64,
		nptOcTotalCVL  Counter64,
		nptOcTotalUASL  Counter64,
		nptOcTotalFCL  Counter64,
		nptOcTotalESLFE  Counter64,
		nptOcTotalSESLFE  Counter64,
		nptOcTotalCVLFE  Counter64,
		nptOcTotalUASLFE  Counter64,
		nptOcTotalFCLFE  Counter64,
		nptOcTotalPSC  Counter64,
		nptOcTotalPSD  Counter64,
		nptOcTotalMaxRxPower  DisplayString,
		nptOcTotalMinRxPower  DisplayString,
        nptOcTotalTxPower  DisplayString
		}


	nptOcTotalIndex	OBJECT-TYPE	
		SYNTAX			Integer32  ( -2147483648 .. 2147483647  ) 
		MAX-ACCESS		read-only
		STATUS			current
		DESCRIPTION		"The index value which uniquely identifies  the
            OC interface to which this entry is applicable."
		::=  {  nptOcTotalEntry  1  }
		
		
	nptOcTotalMoDescription	OBJECT-TYPE	
		SYNTAX			DisplayString 
		MAX-ACCESS		read-only
		STATUS			current
		DESCRIPTION		"Mo Description"
		::=  {  nptOcTotalEntry  2  }


	nptOcTotalESS	OBJECT-TYPE	
		SYNTAX			Counter64
		MAX-ACCESS		read-only
		STATUS			current
		DESCRIPTION		"errored seconds. If errors occur within a certain second, this second is called an errored second."
		::=  {  nptOcTotalEntry  3  }


	nptOcTotalSESS	OBJECT-TYPE	
		SYNTAX			Counter64
		MAX-ACCESS		read-only
		STATUS			current
		DESCRIPTION		"severely errored seconds. If there are errors in 30% of the frames, the errors exceed the threshold, 
		or the signal fails within a certain second, this second is called a severely errored second. 
		Errored seconds (ESs) are not counted when severely errored seconds occur."
		::=  {  nptOcTotalEntry  4  }


	nptOcTotalCVS 	OBJECT-TYPE	
		SYNTAX			Counter64
		MAX-ACCESS		read-only
		STATUS			current
		DESCRIPTION		"Section Coding Violations a count of BIP errors detected at the Section layer."
		::=  {  nptOcTotalEntry  5  }


	nptOcTotalSEFSS	OBJECT-TYPE	
		SYNTAX			Counter64
		MAX-ACCESS		read-only
		STATUS			current
		DESCRIPTION		"Section Severely Errored Framing Seconds."
		::=  {  nptOcTotalEntry  6  }


	nptOcTotalESL	OBJECT-TYPE	
		SYNTAX			Counter64
		MAX-ACCESS		read-only
		STATUS			current
		DESCRIPTION		"errored seconds. If errors occur within a certain second, this second is called an errored second."
		::=  {  nptOcTotalEntry  7  }


	nptOcTotalSESL	OBJECT-TYPE	
		SYNTAX			Counter64
		MAX-ACCESS		read-only
		STATUS			current
		DESCRIPTION		"severely errored seconds. If there are errors in 30% of the frames, the errors exceed the threshold, 
		or the signal fails within a certain second, this second is called a severely errored second. 
		Errored seconds (ESs) are not counted when severely errored seconds occur."
		::=  {  nptOcTotalEntry  8  }


	nptOcTotalCVL	OBJECT-TYPE	
		SYNTAX			Counter64
		MAX-ACCESS		read-only
		STATUS			current
		DESCRIPTION		"Near-end Line Coding Violations.a count of BIP errors detected at the Line layer"
		::=  {  nptOcTotalEntry  9  }


	nptOcTotalUASL	OBJECT-TYPE	
		SYNTAX			Counter64
		MAX-ACCESS		read-only
		STATUS			current
		DESCRIPTION		"unavailable seconds. When an SES lasts for 10 seconds, it becomes a UAS. 
		When there are no severely errored seconds within 10 seconds, it is no longer counted as a UAS. The UAS is not calculated in SES calculations."
		::=  {  nptOcTotalEntry  10  }


	nptOcTotalFCL	OBJECT-TYPE	
		SYNTAX			Counter64
		MAX-ACCESS		read-only
		STATUS			current
		DESCRIPTION		"Near-end Line Failure Counts. A failure event begins when the AIS-L failure is declared, and ends when the failure is cleared."
		::=  {  nptOcTotalEntry  11  }


	nptOcTotalESLFE	OBJECT-TYPE	
		SYNTAX			Counter64
		MAX-ACCESS		read-only
		STATUS			current
		DESCRIPTION		"far-end errored seconds."
		::=  {  nptOcTotalEntry  12  }


	nptOcTotalSESLFE	OBJECT-TYPE	
		SYNTAX			Counter64
		MAX-ACCESS		read-only
		STATUS			current
		DESCRIPTION		"far-end severely errored seconds."
		::=  {  nptOcTotalEntry  13  }
		
	nptOcTotalCVLFE	OBJECT-TYPE	
		SYNTAX			Counter64
		MAX-ACCESS		read-only
		STATUS			current
		DESCRIPTION		"Far-end Line Coding Violations."
		::=  {  nptOcTotalEntry  14  }
		
	nptOcTotalUASLFE	OBJECT-TYPE	
		SYNTAX			Counter64
		MAX-ACCESS		read-only
		STATUS			current
		DESCRIPTION		"far-end unavailable seconds."
		::=  {  nptOcTotalEntry  15  }
		
	nptOcTotalFCLFE	OBJECT-TYPE	
		SYNTAX			Counter64
		MAX-ACCESS		read-only
		STATUS			current
		DESCRIPTION		"Far-end Line Failure Counts."
		::=  {  nptOcTotalEntry  16  }
		
	nptOcTotalPSC	OBJECT-TYPE	
		SYNTAX			Counter64
		MAX-ACCESS		read-only
		STATUS			current
		DESCRIPTION		"Protection Switching Counts. a count of the number of times that service has been switched."
		::=  {  nptOcTotalEntry  17  }
		
	nptOcTotalPSD	OBJECT-TYPE	
		SYNTAX			Counter64
		MAX-ACCESS		read-only
		STATUS			current
		DESCRIPTION		"Protection Switching Duration. a count of the seconds that service was being carried on the protection line."
		::=  {  nptOcTotalEntry  18  }
		
		
	nptOcTotalMaxRxPower	OBJECT-TYPE	
		SYNTAX			DisplayString
		MAX-ACCESS		read-only
		STATUS			current
		DESCRIPTION		"The maximal receive optical power in monitored duration."
		::=  {  nptOcTotalEntry  19  }
		
	nptOcTotalMinRxPower	OBJECT-TYPE	
		SYNTAX			DisplayString
		MAX-ACCESS		read-only
		STATUS			current
		DESCRIPTION		"The minimal receive optical power in monitored duration."
		::=  {  nptOcTotalEntry  20  }
        
        
	nptOcTotalTxPower	OBJECT-TYPE	
		SYNTAX			DisplayString
		MAX-ACCESS		read-only
		STATUS			current
		DESCRIPTION		"The minimal receive optical power in monitored duration."
		::=  {  nptOcTotalEntry  21  }
		
	nptStsCurrentTable	OBJECT-TYPE
		SYNTAX		SEQUENCE  OF  NptStsCurrentEntry
		MAX-ACCESS	not-accessible
		STATUS		current
		DESCRIPTION	"The STS current table contains various statistics
            being collected for the current 15 minute
            interval."
		::=  { nptStsIfGroup  1 }

	nptStsCurrentEntry	OBJECT-TYPE
		SYNTAX		NptStsCurrentEntry
		MAX-ACCESS	not-accessible
		STATUS		current
		DESCRIPTION	"An entry in the STS Current table."
		INDEX		{  nptStsCurrentIndex  }
		::=  { nptStsCurrentTable 1 }

	NptStsCurrentEntry  ::=  SEQUENCE {
		nptStsCurrentIndex  Integer32,
		nptStsCurrentMoDescription  DisplayString,
		nptStsCurrentPPJCPDet  Counter64,
		nptStsCurrentNPJCPDet  Counter64,
		nptStsCurrentESP  Counter64,
		nptStsCurrentSESP  Counter64,
		nptStsCurrentCVP  Counter64,
		nptStsCurrentUASP  Counter64,
		nptStsCurrentFCP  Counter64,
		nptStsCurrentESPFE  Counter64,
		nptStsCurrentSESPFE  Counter64,
		nptStsCurrentCVPFE  Counter64,
		nptStsCurrentUASPFE  Counter64,
		nptStsCurrentFCPFE  Counter64,
		nptStsCurrentPPJCPGen  Counter64,
		nptStsCurrentNPJCPGen  Counter64,
		nptStsCurrentPJCDiffP  Counter64,
		nptStsCurrentPJCSPDet  Counter64,
		nptStsCurrentPJCSPGen  Counter64
		}


	nptStsCurrentIndex	OBJECT-TYPE	
		SYNTAX			Integer32  ( -2147483648 .. 2147483647  ) 
		MAX-ACCESS		read-only
		STATUS			current
		DESCRIPTION		"The index value which uniquely identifies  the
            STS interface to which this entry is applicable."
		::=  {  nptStsCurrentEntry  1  }
		
		
	nptStsCurrentMoDescription	OBJECT-TYPE	
		SYNTAX			DisplayString 
		MAX-ACCESS		read-only
		STATUS			current
		DESCRIPTION		"Mo Description"
		::=  {  nptStsCurrentEntry  2  }


	nptStsCurrentPPJCPDet	OBJECT-TYPE	
		SYNTAX			Counter64
		MAX-ACCESS		read-only
		STATUS			current
		DESCRIPTION		"errored seconds. If errors occur within a certain second, this second is called an errored second."
		::=  {  nptStsCurrentEntry  3  }


	nptStsCurrentNPJCPDet	OBJECT-TYPE	
		SYNTAX			Counter64
		MAX-ACCESS		read-only
		STATUS			current
		DESCRIPTION		"severely errored seconds. If there are errors in 30% of the frames, the errors exceed the threshold, 
		or the signal fails within a certain second, this second is called a severely errored second. 
		Errored seconds (ESs) are not counted when severely errored seconds occur."
		::=  {  nptStsCurrentEntry  4  }

		
	nptStsCurrentESP	OBJECT-TYPE	
		SYNTAX			Counter64
		MAX-ACCESS		read-only
		STATUS			current
		DESCRIPTION		"errored seconds. If errors occur within a certain second, this second is called an errored second."
		::=  {  nptStsCurrentEntry  5  }


	nptStsCurrentSESP	OBJECT-TYPE	
		SYNTAX			Counter64
		MAX-ACCESS		read-only
		STATUS			current
		DESCRIPTION		"severely errored seconds. If there are errors in 30% of the frames, the errors exceed the threshold, 
		or the signal fails within a certain second, this second is called a severely errored second. 
		Errored seconds (ESs) are not counted when severely errored seconds occur."
		::=  {  nptStsCurrentEntry  6  }


	nptStsCurrentCVP	OBJECT-TYPE	
		SYNTAX			Counter64
		MAX-ACCESS		read-only
		STATUS			current
		DESCRIPTION		"Near-end Line Coding Violations.a count of BIP errors detected at the Line layer"
		::=  {  nptStsCurrentEntry  7  }


	nptStsCurrentUASP	OBJECT-TYPE	
		SYNTAX			Counter64
		MAX-ACCESS		read-only
		STATUS			current
		DESCRIPTION		"unavailable seconds. When an SES lasts for 10 seconds, it becomes a UAS. 
		When there are no severely errored seconds within 10 seconds, it is no longer counted as a UAS. The UAS is not calculated in SES calculations."
		::=  {  nptStsCurrentEntry  8  }


	nptStsCurrentFCP	OBJECT-TYPE	
		SYNTAX			Counter64
		MAX-ACCESS		read-only
		STATUS			current
		DESCRIPTION		"Near-end Line Failure Counts. A failure event begins when the AIS-L failure is declared, and ends when the failure is cleared."
		::=  {  nptStsCurrentEntry  9  }


	nptStsCurrentESPFE	OBJECT-TYPE	
		SYNTAX			Counter64
		MAX-ACCESS		read-only
		STATUS			current
		DESCRIPTION		"far-end errored seconds."
		::=  {  nptStsCurrentEntry  10  }


	nptStsCurrentSESPFE	OBJECT-TYPE	
		SYNTAX			Counter64
		MAX-ACCESS		read-only
		STATUS			current
		DESCRIPTION		"far-end severely errored seconds."
		::=  {  nptStsCurrentEntry  11  }
		
	nptStsCurrentCVPFE	OBJECT-TYPE	
		SYNTAX			Counter64
		MAX-ACCESS		read-only
		STATUS			current
		DESCRIPTION		"Far-end Line Coding Violations."
		::=  {  nptStsCurrentEntry  12  }
		
	nptStsCurrentUASPFE	OBJECT-TYPE	
		SYNTAX			Counter64
		MAX-ACCESS		read-only
		STATUS			current
		DESCRIPTION		"far-end unavailable seconds."
		::=  {  nptStsCurrentEntry  13  }
		
	nptStsCurrentFCPFE	OBJECT-TYPE	
		SYNTAX			Counter64
		MAX-ACCESS		read-only
		STATUS			current
		DESCRIPTION		"Far-end Line Failure Counts."
		::=  {  nptStsCurrentEntry  14  }
		
	nptStsCurrentPPJCPGen	OBJECT-TYPE	
		SYNTAX			Counter64
		MAX-ACCESS		read-only
		STATUS			current
		DESCRIPTION		"Protection Switching Counts. a count of the number of times that service has been switched."
		::=  {  nptStsCurrentEntry  15  }
		
	nptStsCurrentNPJCPGen	OBJECT-TYPE	
		SYNTAX			Counter64
		MAX-ACCESS		read-only
		STATUS			current
		DESCRIPTION		"Protection Switching Duration. a count of the seconds that service was being carried on the protection line."
		::=  {  nptStsCurrentEntry  16  }
		
		
	nptStsCurrentPJCDiffP	OBJECT-TYPE	
		SYNTAX			Counter64
		MAX-ACCESS		read-only
		STATUS			current
		DESCRIPTION		"Protection Switching Counts. a count of the number of times that service has been switched."
		::=  {  nptStsCurrentEntry  17  }
		
	nptStsCurrentPJCSPDet	OBJECT-TYPE	
		SYNTAX			Counter64
		MAX-ACCESS		read-only
		STATUS			current
		DESCRIPTION		"Protection Switching Duration. a count of the seconds that service was being carried on the protection line."
		::=  {  nptStsCurrentEntry  18  }
		
	nptStsCurrentPJCSPGen	OBJECT-TYPE	
		SYNTAX			Counter64
		MAX-ACCESS		read-only
		STATUS			current
		DESCRIPTION		"Protection Switching Duration. a count of the seconds that service was being carried on the protection line."
		::=  {  nptStsCurrentEntry  19  }
		
	nptStsTotalTable	OBJECT-TYPE
		SYNTAX		SEQUENCE  OF  NptStsTotalEntry
		MAX-ACCESS	not-accessible
		STATUS		current
		DESCRIPTION	"The STS current table contains various statistics
            being collected for the current 15 minute
            interval."
		::=  { nptStsIfGroup  2 }

	nptStsTotalEntry	OBJECT-TYPE
		SYNTAX		NptStsTotalEntry
		MAX-ACCESS	not-accessible
		STATUS		current
		DESCRIPTION	"An entry in the STS Total table."
		INDEX		{  nptStsTotalIndex  }
		::=  { nptStsTotalTable 1 }

	NptStsTotalEntry  ::=  SEQUENCE {
		nptStsTotalIndex  Integer32,
		nptStsTotalMoDescription  DisplayString,
		nptStsTotalPPJCPDet  Counter64,
		nptStsTotalNPJCPDet  Counter64,
		nptStsTotalESP  Counter64,
		nptStsTotalSESP  Counter64,
		nptStsTotalCVP  Counter64,
		nptStsTotalUASP  Counter64,
		nptStsTotalFCP  Counter64,
		nptStsTotalESPFE  Counter64,
		nptStsTotalSESPFE  Counter64,
		nptStsTotalCVPFE  Counter64,
		nptStsTotalUASPFE  Counter64,
		nptStsTotalFCPFE  Counter64,
		nptStsTotalPPJCPGen  Counter64,
		nptStsTotalNPJCPGen  Counter64,
		nptStsTotalPJCDiffP  Counter64,
		nptStsTotalPJCSPDet  Counter64,
		nptStsTotalPJCSPGen  Counter64
		}


	nptStsTotalIndex	OBJECT-TYPE	
		SYNTAX			Integer32  ( -2147483648 .. 2147483647  ) 
		MAX-ACCESS		read-only
		STATUS			current
		DESCRIPTION		"The index value which uniquely identifies  the
            STS interface to which this entry is applicable."
		::=  {  nptStsTotalEntry  1  }
		
		
	nptStsTotalMoDescription	OBJECT-TYPE	
		SYNTAX			DisplayString 
		MAX-ACCESS		read-only
		STATUS			current
		DESCRIPTION		"Mo Description"
		::=  {  nptStsTotalEntry  2  }


	nptStsTotalPPJCPDet	OBJECT-TYPE	
		SYNTAX			Counter64
		MAX-ACCESS		read-only
		STATUS			current
		DESCRIPTION		"errored seconds. If errors occur within a certain second, this second is called an errored second."
		::=  {  nptStsTotalEntry  3  }


	nptStsTotalNPJCPDet	OBJECT-TYPE	
		SYNTAX			Counter64
		MAX-ACCESS		read-only
		STATUS			current
		DESCRIPTION		"severely errored seconds. If there are errors in 30% of the frames, the errors exceed the threshold, 
		or the signal fails within a certain second, this second is called a severely errored second. 
		Errored seconds (ESs) are not counted when severely errored seconds occur."
		::=  {  nptStsTotalEntry  4  }

		
	nptStsTotalESP	OBJECT-TYPE	
		SYNTAX			Counter64
		MAX-ACCESS		read-only
		STATUS			current
		DESCRIPTION		"errored seconds. If errors occur within a certain second, this second is called an errored second."
		::=  {  nptStsTotalEntry  5  }


	nptStsTotalSESP	OBJECT-TYPE	
		SYNTAX			Counter64
		MAX-ACCESS		read-only
		STATUS			current
		DESCRIPTION		"severely errored seconds. If there are errors in 30% of the frames, the errors exceed the threshold, 
		or the signal fails within a certain second, this second is called a severely errored second. 
		Errored seconds (ESs) are not counted when severely errored seconds occur."
		::=  {  nptStsTotalEntry  6  }


	nptStsTotalCVP	OBJECT-TYPE	
		SYNTAX			Counter64
		MAX-ACCESS		read-only
		STATUS			current
		DESCRIPTION		"Near-end Line Coding Violations.a count of BIP errors detected at the Line layer"
		::=  {  nptStsTotalEntry  7  }


	nptStsTotalUASP	OBJECT-TYPE	
		SYNTAX			Counter64
		MAX-ACCESS		read-only
		STATUS			current
		DESCRIPTION		"unavailable seconds. When an SES lasts for 10 seconds, it becomes a UAS. 
		When there are no severely errored seconds within 10 seconds, it is no longer counted as a UAS. The UAS is not calculated in SES calculations."
		::=  {  nptStsTotalEntry  8  }


	nptStsTotalFCP	OBJECT-TYPE	
		SYNTAX			Counter64
		MAX-ACCESS		read-only
		STATUS			current
		DESCRIPTION		"Near-end Line Failure Counts. A failure event begins when the AIS-L failure is declared, and ends when the failure is cleared."
		::=  {  nptStsTotalEntry  9  }


	nptStsTotalESPFE	OBJECT-TYPE	
		SYNTAX			Counter64
		MAX-ACCESS		read-only
		STATUS			current
		DESCRIPTION		"far-end errored seconds."
		::=  {  nptStsTotalEntry  10  }


	nptStsTotalSESPFE	OBJECT-TYPE	
		SYNTAX			Counter64
		MAX-ACCESS		read-only
		STATUS			current
		DESCRIPTION		"far-end severely errored seconds."
		::=  {  nptStsTotalEntry  11  }
		
	nptStsTotalCVPFE	OBJECT-TYPE	
		SYNTAX			Counter64
		MAX-ACCESS		read-only
		STATUS			current
		DESCRIPTION		"Far-end Line Coding Violations."
		::=  {  nptStsTotalEntry  12  }
		
	nptStsTotalUASPFE	OBJECT-TYPE	
		SYNTAX			Counter64
		MAX-ACCESS		read-only
		STATUS			current
		DESCRIPTION		"far-end unavailable seconds."
		::=  {  nptStsTotalEntry  13  }
		
	nptStsTotalFCPFE	OBJECT-TYPE	
		SYNTAX			Counter64
		MAX-ACCESS		read-only
		STATUS			current
		DESCRIPTION		"Far-end Line Failure Counts."
		::=  {  nptStsTotalEntry  14  }
		
	nptStsTotalPPJCPGen	OBJECT-TYPE	
		SYNTAX			Counter64
		MAX-ACCESS		read-only
		STATUS			current
		DESCRIPTION		"Protection Switching Counts. a count of the number of times that service has been switched."
		::=  {  nptStsTotalEntry  15  }
		
	nptStsTotalNPJCPGen	OBJECT-TYPE	
		SYNTAX			Counter64
		MAX-ACCESS		read-only
		STATUS			current
		DESCRIPTION		"Protection Switching Duration. a count of the seconds that service was being carried on the protection line."
		::=  {  nptStsTotalEntry  16  }
		
		
	nptStsTotalPJCDiffP	OBJECT-TYPE	
		SYNTAX			Counter64
		MAX-ACCESS		read-only
		STATUS			current
		DESCRIPTION		"Protection Switching Counts. a count of the number of times that service has been switched."
		::=  {  nptStsTotalEntry  17  }
		
	nptStsTotalPJCSPDet	OBJECT-TYPE	
		SYNTAX			Counter64
		MAX-ACCESS		read-only
		STATUS			current
		DESCRIPTION		"Protection Switching Duration. a count of the seconds that service was being carried on the protection line."
		::=  {  nptStsTotalEntry  18  }
		
	nptStsTotalPJCSPGen	OBJECT-TYPE	
		SYNTAX			Counter64
		MAX-ACCESS		read-only
		STATUS			current
		DESCRIPTION		"Protection Switching Duration. a count of the seconds that service was being carried on the protection line."
		::=  {  nptStsTotalEntry  19  }
		
	nptVt15CurrentTable	OBJECT-TYPE
		SYNTAX		SEQUENCE  OF  NptVt15CurrentEntry
		MAX-ACCESS	not-accessible
		STATUS		current
		DESCRIPTION	"The VT15 current table contains various statistics
            being collected for the current 15 minute
            interval."
		::=  { nptVt15IfGroup  1 }

	nptVt15CurrentEntry	OBJECT-TYPE
		SYNTAX		NptVt15CurrentEntry
		MAX-ACCESS	not-accessible
		STATUS		current
		DESCRIPTION	"An entry in the VT15 Current table."
		INDEX		{  nptVt15CurrentIndex  }
		::=  { nptVt15CurrentTable 1 }

	NptVt15CurrentEntry  ::=  SEQUENCE {
		nptVt15CurrentIndex  Integer32,
		nptVt15CurrentMoDescription  DisplayString,
		nptVt15CurrentPPJCVDet  Counter64,
		nptVt15CurrentNPJCVDet  Counter64,
		nptVt15CurrentESV  Counter64,
		nptVt15CurrentSESV  Counter64,
		nptVt15CurrentCVV  Counter64,
		nptVt15CurrentFCV  Counter64,
		nptVt15CurrentUASV  Counter64,
		nptVt15CurrentESVFE  Counter64,
		nptVt15CurrentSESVFE  Counter64,
		nptVt15CurrentCVVFE  Counter64,
		nptVt15CurrentUASVFE  Counter64,
		nptVt15CurrentFCVFE  Counter64,
		nptVt15CurrentPPJCVGen  Counter64,
		nptVt15CurrentNPJCVGen  Counter64,
		nptVt15CurrentPJCDiffV  Counter64,
		nptVt15CurrentPJCSVDet  Counter64,
		nptVt15CurrentPJCSVGen  Counter64
		}


	nptVt15CurrentIndex	OBJECT-TYPE	
		SYNTAX			Integer32  ( -2147483648 .. 2147483647  ) 
		MAX-ACCESS		read-only
		STATUS			current
		DESCRIPTION		"The index value which uniquely identifies  the
            VT15 interface to which this entry is applicable."
		::=  {  nptVt15CurrentEntry  1  }
		
		
	nptVt15CurrentMoDescription	OBJECT-TYPE	
		SYNTAX			DisplayString 
		MAX-ACCESS		read-only
		STATUS			current
		DESCRIPTION		"Mo Description"
		::=  {  nptVt15CurrentEntry  2  }


	nptVt15CurrentPPJCVDet	OBJECT-TYPE	
		SYNTAX			Counter64
		MAX-ACCESS		read-only
		STATUS			current
		DESCRIPTION		"errored seconds. If errors occur within a certain second, this second is called an errored second."
		::=  {  nptVt15CurrentEntry  3  }


	nptVt15CurrentNPJCVDet	OBJECT-TYPE	
		SYNTAX			Counter64
		MAX-ACCESS		read-only
		STATUS			current
		DESCRIPTION		"severely errored seconds. If there are errors in 30% of the frames, the errors exceed the threshold, 
		or the signal fails within a certain second, this second is called a severely errored second. 
		Errored seconds (ESs) are not counted when severely errored seconds occur."
		::=  {  nptVt15CurrentEntry  4  }

		
	nptVt15CurrentESV	OBJECT-TYPE	
		SYNTAX			Counter64
		MAX-ACCESS		read-only
		STATUS			current
		DESCRIPTION		"errored seconds. If errors occur within a certain second, this second is called an errored second."
		::=  {  nptVt15CurrentEntry  5  }


	nptVt15CurrentSESV	OBJECT-TYPE	
		SYNTAX			Counter64
		MAX-ACCESS		read-only
		STATUS			current
		DESCRIPTION		"severely errored seconds. If there are errors in 30% of the frames, the errors exceed the threshold, 
		or the signal fails within a certain second, this second is called a severely errored second. 
		Errored seconds (ESs) are not counted when severely errored seconds occur."
		::=  {  nptVt15CurrentEntry  6  }


	nptVt15CurrentCVV	OBJECT-TYPE	
		SYNTAX			Counter64
		MAX-ACCESS		read-only
		STATUS			current
		DESCRIPTION		"Near-end Line Coding Violations.a count of BIP errors detected at the Line layer"
		::=  {  nptVt15CurrentEntry  7  }

	nptVt15CurrentFCV	OBJECT-TYPE	
		SYNTAX			Counter64
		MAX-ACCESS		read-only
		STATUS			current
		DESCRIPTION		"Near-end Line Failure Counts. A failure event begins when the AIS-L failure is declared, and ends when the failure is cleared."
		::=  {  nptVt15CurrentEntry  8  }


	nptVt15CurrentUASV	OBJECT-TYPE	
		SYNTAX			Counter64
		MAX-ACCESS		read-only
		STATUS			current
		DESCRIPTION		"unavailable seconds. When an SES lasts for 10 seconds, it becomes a UAS. 
		When there are no severely errored seconds within 10 seconds, it is no longer counted as a UAS. The UAS is not calculated in SES calculations."
		::=  {  nptVt15CurrentEntry  9  }


	nptVt15CurrentESVFE	OBJECT-TYPE	
		SYNTAX			Counter64
		MAX-ACCESS		read-only
		STATUS			current
		DESCRIPTION		"far-end errored seconds."
		::=  {  nptVt15CurrentEntry  10  }


	nptVt15CurrentSESVFE	OBJECT-TYPE	
		SYNTAX			Counter64
		MAX-ACCESS		read-only
		STATUS			current
		DESCRIPTION		"far-end severely errored seconds."
		::=  {  nptVt15CurrentEntry  11  }
		
	nptVt15CurrentCVVFE	OBJECT-TYPE	
		SYNTAX			Counter64
		MAX-ACCESS		read-only
		STATUS			current
		DESCRIPTION		"Far-end Line Coding Violations."
		::=  {  nptVt15CurrentEntry  12  }
		
	nptVt15CurrentUASVFE	OBJECT-TYPE	
		SYNTAX			Counter64
		MAX-ACCESS		read-only
		STATUS			current
		DESCRIPTION		"far-end unavailable seconds."
		::=  {  nptVt15CurrentEntry  13  }
		
	nptVt15CurrentFCVFE	OBJECT-TYPE	
		SYNTAX			Counter64
		MAX-ACCESS		read-only
		STATUS			current
		DESCRIPTION		"Far-end Line Failure Counts."
		::=  {  nptVt15CurrentEntry  14  }
		
	nptVt15CurrentPPJCVGen	OBJECT-TYPE	
		SYNTAX			Counter64
		MAX-ACCESS		read-only
		STATUS			current
		DESCRIPTION		"Protection Switching Counts. a count of the number of times that service has been switched."
		::=  {  nptVt15CurrentEntry  15  }
		
	nptVt15CurrentNPJCVGen	OBJECT-TYPE	
		SYNTAX			Counter64
		MAX-ACCESS		read-only
		STATUS			current
		DESCRIPTION		"Protection Switching Duration. a count of the seconds that service was being carried on the protection line."
		::=  {  nptVt15CurrentEntry  16  }
		
		
	nptVt15CurrentPJCDiffV	OBJECT-TYPE	
		SYNTAX			Counter64
		MAX-ACCESS		read-only
		STATUS			current
		DESCRIPTION		"Protection Switching Counts. a count of the number of times that service has been switched."
		::=  {  nptVt15CurrentEntry  17  }
		
	nptVt15CurrentPJCSVDet	OBJECT-TYPE	
		SYNTAX			Counter64
		MAX-ACCESS		read-only
		STATUS			current
		DESCRIPTION		"Protection Switching Duration. a count of the seconds that service was being carried on the protection line."
		::=  {  nptVt15CurrentEntry  18  }
		
	nptVt15CurrentPJCSVGen	OBJECT-TYPE	
		SYNTAX			Counter64
		MAX-ACCESS		read-only
		STATUS			current
		DESCRIPTION		"Protection Switching Duration. a count of the seconds that service was being carried on the protection line."
		::=  {  nptVt15CurrentEntry  19  }
		
	nptVt15TotalTable	OBJECT-TYPE
		SYNTAX		SEQUENCE  OF  NptVt15TotalEntry
		MAX-ACCESS	not-accessible
		STATUS		current
		DESCRIPTION	"The VT15 current table contains various statistics
            being collected for the current 15 minute
            interval."
		::=  { nptVt15IfGroup  2 }

	nptVt15TotalEntry	OBJECT-TYPE
		SYNTAX		NptVt15TotalEntry
		MAX-ACCESS	not-accessible
		STATUS		current
		DESCRIPTION	"An entry in the VT15 Total table."
		INDEX		{  nptVt15TotalIndex  }
		::=  { nptVt15TotalTable 1 }

	NptVt15TotalEntry  ::=  SEQUENCE {
		nptVt15TotalIndex  Integer32,
		nptVt15TotalMoDescription  DisplayString,
		nptVt15TotalPPJCVDet  Counter64,
		nptVt15TotalNPJCVDet  Counter64,
		nptVt15TotalESV  Counter64,
		nptVt15TotalSESV  Counter64,
		nptVt15TotalCVV  Counter64,
		nptVt15TotalUASV  Counter64,
		nptVt15TotalFCV  Counter64,
		nptVt15TotalESVFE  Counter64,
		nptVt15TotalSESVFE  Counter64,
		nptVt15TotalCVVFE  Counter64,
		nptVt15TotalUASVFE  Counter64,
		nptVt15TotalFCVFE  Counter64,
		nptVt15TotalPPJCVGen  Counter64,
		nptVt15TotalNPJCVGen  Counter64,
		nptVt15TotalPJCDiffV  Counter64,
		nptVt15TotalPJCSVDet  Counter64,
		nptVt15TotalPJCSVGen  Counter64
		}


	nptVt15TotalIndex	OBJECT-TYPE	
		SYNTAX			Integer32  ( -2147483648 .. 2147483647  ) 
		MAX-ACCESS		read-only
		STATUS			current
		DESCRIPTION		"The index value which uniquely identifies  the
            VT15 interface to which this entry is applicable."
		::=  {  nptVt15TotalEntry  1  }
		
		
	nptVt15TotalMoDescription	OBJECT-TYPE	
		SYNTAX			DisplayString 
		MAX-ACCESS		read-only
		STATUS			current
		DESCRIPTION		"Mo Description"
		::=  {  nptVt15TotalEntry  2  }


	nptVt15TotalPPJCVDet	OBJECT-TYPE	
		SYNTAX			Counter64
		MAX-ACCESS		read-only
		STATUS			current
		DESCRIPTION		"errored seconds. If errors occur within a certain second, this second is called an errored second."
		::=  {  nptVt15TotalEntry  3  }


	nptVt15TotalNPJCVDet	OBJECT-TYPE	
		SYNTAX			Counter64
		MAX-ACCESS		read-only
		STATUS			current
		DESCRIPTION		"severely errored seconds. If there are errors in 30% of the frames, the errors exceed the threshold, 
		or the signal fails within a certain second, this second is called a severely errored second. 
		Errored seconds (ESs) are not counted when severely errored seconds occur."
		::=  {  nptVt15TotalEntry  4  }

		
	nptVt15TotalESV	OBJECT-TYPE	
		SYNTAX			Counter64
		MAX-ACCESS		read-only
		STATUS			current
		DESCRIPTION		"errored seconds. If errors occur within a certain second, this second is called an errored second."
		::=  {  nptVt15TotalEntry  5  }


	nptVt15TotalSESV	OBJECT-TYPE	
		SYNTAX			Counter64
		MAX-ACCESS		read-only
		STATUS			current
		DESCRIPTION		"severely errored seconds. If there are errors in 30% of the frames, the errors exceed the threshold, 
		or the signal fails within a certain second, this second is called a severely errored second. 
		Errored seconds (ESs) are not counted when severely errored seconds occur."
		::=  {  nptVt15TotalEntry  6  }


	nptVt15TotalCVV	OBJECT-TYPE	
		SYNTAX			Counter64
		MAX-ACCESS		read-only
		STATUS			current
		DESCRIPTION		"Near-end Line Coding Violations.a count of BIP errors detected at the Line layer"
		::=  {  nptVt15TotalEntry  7  }


	nptVt15TotalUASV	OBJECT-TYPE	
		SYNTAX			Counter64
		MAX-ACCESS		read-only
		STATUS			current
		DESCRIPTION		"unavailable seconds. When an SES lasts for 10 seconds, it becomes a UAS. 
		When there are no severely errored seconds within 10 seconds, it is no longer counted as a UAS. The UAS is not calculated in SES calculations."
		::=  {  nptVt15TotalEntry  8  }


	nptVt15TotalFCV	OBJECT-TYPE	
		SYNTAX			Counter64
		MAX-ACCESS		read-only
		STATUS			current
		DESCRIPTION		"Near-end Line Failure Counts. A failure event begins when the AIS-L failure is declared, and ends when the failure is cleared."
		::=  {  nptVt15TotalEntry  9  }


	nptVt15TotalESVFE	OBJECT-TYPE	
		SYNTAX			Counter64
		MAX-ACCESS		read-only
		STATUS			current
		DESCRIPTION		"far-end errored seconds."
		::=  {  nptVt15TotalEntry  10  }


	nptVt15TotalSESVFE	OBJECT-TYPE	
		SYNTAX			Counter64
		MAX-ACCESS		read-only
		STATUS			current
		DESCRIPTION		"far-end severely errored seconds."
		::=  {  nptVt15TotalEntry  11  }
		
	nptVt15TotalCVVFE	OBJECT-TYPE	
		SYNTAX			Counter64
		MAX-ACCESS		read-only
		STATUS			current
		DESCRIPTION		"Far-end Line Coding Violations."
		::=  {  nptVt15TotalEntry  12  }
		
	nptVt15TotalUASVFE	OBJECT-TYPE	
		SYNTAX			Counter64
		MAX-ACCESS		read-only
		STATUS			current
		DESCRIPTION		"far-end unavailable seconds."
		::=  {  nptVt15TotalEntry  13  }
		
	nptVt15TotalFCVFE	OBJECT-TYPE	
		SYNTAX			Counter64
		MAX-ACCESS		read-only
		STATUS			current
		DESCRIPTION		"Far-end Line Failure Counts."
		::=  {  nptVt15TotalEntry  14  }
		
	nptVt15TotalPPJCVGen	OBJECT-TYPE	
		SYNTAX			Counter64
		MAX-ACCESS		read-only
		STATUS			current
		DESCRIPTION		"Protection Switching Counts. a count of the number of times that service has been switched."
		::=  {  nptVt15TotalEntry  15  }
		
	nptVt15TotalNPJCVGen	OBJECT-TYPE	
		SYNTAX			Counter64
		MAX-ACCESS		read-only
		STATUS			current
		DESCRIPTION		"Protection Switching Duration. a count of the seconds that service was being carried on the protection line."
		::=  {  nptVt15TotalEntry  16  }
		
		
	nptVt15TotalPJCDiffV	OBJECT-TYPE	
		SYNTAX			Counter64
		MAX-ACCESS		read-only
		STATUS			current
		DESCRIPTION		"Protection Switching Counts. a count of the number of times that service has been switched."
		::=  {  nptVt15TotalEntry  17  }
		
	nptVt15TotalPJCSVDet	OBJECT-TYPE	
		SYNTAX			Counter64
		MAX-ACCESS		read-only
		STATUS			current
		DESCRIPTION		"Protection Switching Duration. a count of the seconds that service was being carried on the protection line."
		::=  {  nptVt15TotalEntry  18  }
		
	nptVt15TotalPJCSVGen	OBJECT-TYPE	
		SYNTAX			Counter64
		MAX-ACCESS		read-only
		STATUS			current
		DESCRIPTION		"Protection Switching Duration. a count of the seconds that service was being carried on the protection line."
		::=  {  nptVt15TotalEntry  19  }
		
	nptDs1LineCurrentTable	OBJECT-TYPE
		SYNTAX		SEQUENCE  OF  NptDs1LineCurrentEntry
		MAX-ACCESS	not-accessible
		STATUS		current
		DESCRIPTION	"The Ds1Line current table contains various statistics
            being collected for the current 15 minute
            interval."
		::=  { nptDs1LineIfGroup  1 }

	nptDs1LineCurrentEntry	OBJECT-TYPE
		SYNTAX		NptDs1LineCurrentEntry
		MAX-ACCESS	not-accessible
		STATUS		current
		DESCRIPTION	"An entry in the Ds1Line Current table."
		INDEX		{  nptDs1LineCurrentIndex  }
		::=  { nptDs1LineCurrentTable 1 }

	NptDs1LineCurrentEntry  ::=  SEQUENCE {
		nptDs1LineCurrentIndex  Integer32,
		nptDs1LineCurrentMoDescription  DisplayString,
		nptDs1LineCurrentES  Counter64,
		nptDs1LineCurrentSES  Counter64,
		nptDs1LineCurrentCV  Counter64,
		nptDs1LineCurrentFEES  Counter64,
		nptDs1LineCurrentLOSS  Counter64,
		nptDs1LineCurrentUAS  Counter64
		}


	nptDs1LineCurrentIndex	OBJECT-TYPE	
		SYNTAX			Integer32  ( -2147483648 .. 2147483647  ) 
		MAX-ACCESS		read-only
		STATUS			current
		DESCRIPTION		"The index value which uniquely identifies  the
            Ds1Line interface to which this entry is applicable."
		::=  {  nptDs1LineCurrentEntry  1  }
		
		
	nptDs1LineCurrentMoDescription	OBJECT-TYPE	
		SYNTAX			DisplayString 
		MAX-ACCESS		read-only
		STATUS			current
		DESCRIPTION		"Mo Description"
		::=  {  nptDs1LineCurrentEntry  2  }


	nptDs1LineCurrentES	OBJECT-TYPE	
		SYNTAX			Counter64
		MAX-ACCESS		read-only
		STATUS			current
		DESCRIPTION		"errored seconds. a count of seconds during which one or more of the following has occurred: BPVs, EXZs, and LOSs."
		::=  {  nptDs1LineCurrentEntry  3  }


	nptDs1LineCurrentSES	OBJECT-TYPE	
		SYNTAX			Counter64
		MAX-ACCESS		read-only
		STATUS			current
		DESCRIPTION		"severely errored seconds. If there are errors in 30% of the frames, the errors exceed the threshold, 
		or the signal fails within a certain second, this second is called a severely errored second. 
		Errored seconds (ESs) are not counted when severely errored seconds occur."
		::=  {  nptDs1LineCurrentEntry  4  }

		
	nptDs1LineCurrentCV	OBJECT-TYPE	
		SYNTAX			Counter64
		MAX-ACCESS		read-only
		STATUS			current
		DESCRIPTION		"Coding Violations. The  Coding Violations is the block error with the number of severely errored seconds deducted from the counting interval."
		::=  {  nptDs1LineCurrentEntry  5  }


	nptDs1LineCurrentFEES	OBJECT-TYPE	
		SYNTAX			Counter64
		MAX-ACCESS		read-only
		STATUS			current
		DESCRIPTION		"far-end errored seconds."
		::=  {  nptDs1LineCurrentEntry  6  }


	nptDs1LineCurrentLOSS	OBJECT-TYPE	
		SYNTAX			Counter64
		MAX-ACCESS		read-only
		STATUS			current
		DESCRIPTION		"A count of 1-second intervals containing one or more LOS defects."
		::=  {  nptDs1LineCurrentEntry  7  }


	nptDs1LineCurrentUAS	OBJECT-TYPE	
		SYNTAX			Counter64
		MAX-ACCESS		read-only
		STATUS			current
		DESCRIPTION		"Description"
		::=  {  nptDs1LineCurrentEntry  8  }


		nptDs1LineTotalTable	OBJECT-TYPE
		SYNTAX		SEQUENCE  OF  NptDs1LineTotalEntry
		MAX-ACCESS	not-accessible
		STATUS		current
		DESCRIPTION	"The Ds1Line current table contains various statistics
            being collected for the current 15 minute
            interval."
		::=  { nptDs1LineIfGroup  2 }

	nptDs1LineTotalEntry	OBJECT-TYPE
		SYNTAX		NptDs1LineTotalEntry
		MAX-ACCESS	not-accessible
		STATUS		current
		DESCRIPTION	"An entry in the Ds1Line Total table."
		INDEX		{  nptDs1LineTotalIndex  }
		::=  { nptDs1LineTotalTable 1 }

	NptDs1LineTotalEntry  ::=  SEQUENCE {
		nptDs1LineTotalIndex  Integer32,
		nptDs1LineTotalMoDescription  DisplayString,
		nptDs1LineTotalES  Counter64,
		nptDs1LineTotalSES  Counter64,
		nptDs1LineTotalCV  Counter64,
		nptDs1LineTotalFEES  Counter64,
		nptDs1LineTotalLOSS  Counter64,
		nptDs1LineTotalUAS  Counter64
		}


	nptDs1LineTotalIndex	OBJECT-TYPE	
		SYNTAX			Integer32  ( -2147483648 .. 2147483647  ) 
		MAX-ACCESS		read-only
		STATUS			current
		DESCRIPTION		"The index value which uniquely identifies  the
            Ds1Line interface to which this entry is applicable."
		::=  {  nptDs1LineTotalEntry  1  }
		
		
	nptDs1LineTotalMoDescription	OBJECT-TYPE	
		SYNTAX			DisplayString 
		MAX-ACCESS		read-only
		STATUS			current
		DESCRIPTION		"Mo Description"
		::=  {  nptDs1LineTotalEntry  2  }


	nptDs1LineTotalES	OBJECT-TYPE	
		SYNTAX			Counter64
		MAX-ACCESS		read-only
		STATUS			current
		DESCRIPTION		"errored seconds. a count of seconds during which one or more of the following has occurred: BPVs, EXZs, and LOSs."
		::=  {  nptDs1LineTotalEntry  3  }


	nptDs1LineTotalSES	OBJECT-TYPE	
		SYNTAX			Counter64
		MAX-ACCESS		read-only
		STATUS			current
		DESCRIPTION		"severely errored seconds. If there are errors in 30% of the frames, the errors exceed the threshold, 
		or the signal fails within a certain second, this second is called a severely errored second. 
		Errored seconds (ESs) are not counted when severely errored seconds occur."
		::=  {  nptDs1LineTotalEntry  4  }

		
	nptDs1LineTotalCV	OBJECT-TYPE	
		SYNTAX			Counter64
		MAX-ACCESS		read-only
		STATUS			current
		DESCRIPTION		"Coding Violations. The  Coding Violations is the block error with the number of severely errored seconds deducted from the counting interval."
		::=  {  nptDs1LineTotalEntry  5  }


	nptDs1LineTotalFEES	OBJECT-TYPE	
		SYNTAX			Counter64
		MAX-ACCESS		read-only
		STATUS			current
		DESCRIPTION		"far-end errored seconds."
		::=  {  nptDs1LineTotalEntry  6  }


	nptDs1LineTotalLOSS	OBJECT-TYPE	
		SYNTAX			Counter64
		MAX-ACCESS		read-only
		STATUS			current
		DESCRIPTION		"A count of 1-second intervals containing one or more LOS defects."
		::=  {  nptDs1LineTotalEntry  7  }


	nptDs1LineTotalUAS	OBJECT-TYPE	
		SYNTAX			Counter64
		MAX-ACCESS		read-only
		STATUS			current
		DESCRIPTION		"Description"
		::=  {  nptDs1LineTotalEntry  8  }


		nptDs1PathCurrentTable	OBJECT-TYPE
		SYNTAX		SEQUENCE  OF  NptDs1PathCurrentEntry
		MAX-ACCESS	not-accessible
		STATUS		current
		DESCRIPTION	"The Ds1Path current table contains various statistics
            being collected for the current 15 minute
            interval."
		::=  { nptDs1PathIfGroup  1 }

	nptDs1PathCurrentEntry	OBJECT-TYPE
		SYNTAX		NptDs1PathCurrentEntry
		MAX-ACCESS	not-accessible
		STATUS		current
		DESCRIPTION	"An entry in the Ds1Path Current table."
		INDEX		{  nptDs1PathCurrentIndex  }
		::=  { nptDs1PathCurrentTable 1 }

	NptDs1PathCurrentEntry  ::=  SEQUENCE {
		nptDs1PathCurrentIndex  Integer32,
		nptDs1PathCurrentMoDescription  DisplayString,
		nptDs1PathCurrentES  Counter64,
		nptDs1PathCurrentSES  Counter64,
		nptDs1PathCurrentCV  Counter64,
		nptDs1PathCurrentCSS  Counter64,
		nptDs1PathCurrentSAS  Counter64,
		nptDs1PathCurrentUAS  Counter64,
		nptDs1PathCurrentFEES  Counter64,
		nptDs1PathCurrentFESES  Counter64,
		nptDs1PathCurrentFECV  Counter64,
		nptDs1PathCurrentFEUAS  Counter64,
		nptDs1PathCurrentFECSS  Counter64
		}


	nptDs1PathCurrentIndex	OBJECT-TYPE	
		SYNTAX			Integer32  ( -2147483648 .. 2147483647  ) 
		MAX-ACCESS		read-only
		STATUS			current
		DESCRIPTION		"The index value which uniquely identifies  the
            Ds1Path interface to which this entry is applicable."
		::=  {  nptDs1PathCurrentEntry  1  }
		
		
	nptDs1PathCurrentMoDescription	OBJECT-TYPE	
		SYNTAX			DisplayString 
		MAX-ACCESS		read-only
		STATUS			current
		DESCRIPTION		"Mo Description"
		::=  {  nptDs1PathCurrentEntry  2  }


	nptDs1PathCurrentES	OBJECT-TYPE	
		SYNTAX			Counter64
		MAX-ACCESS		read-only
		STATUS			current
		DESCRIPTION		"errored seconds. If errors occur within a certain second, this second is called an errored second."
		::=  {  nptDs1PathCurrentEntry  3  }


	nptDs1PathCurrentSES	OBJECT-TYPE	
		SYNTAX			Counter64
		MAX-ACCESS		read-only
		STATUS			current
		DESCRIPTION		"severely errored seconds. If there are errors in 30% of the frames, the errors exceed the threshold, 
		or the signal fails within a certain second, this second is called a severely errored second. 
		Errored seconds (ESs) are not counted when severely errored seconds occur."
		::=  {  nptDs1PathCurrentEntry  4  }

		
	nptDs1PathCurrentCV	OBJECT-TYPE	
		SYNTAX			Counter64
		MAX-ACCESS		read-only
		STATUS			current
		DESCRIPTION		"errored seconds. If errors occur within a certain second, this second is called an errored second."
		::=  {  nptDs1PathCurrentEntry  5  }


	nptDs1PathCurrentCSS	OBJECT-TYPE	
		SYNTAX			Counter64
		MAX-ACCESS		read-only
		STATUS			current
		DESCRIPTION		"Controlled Slip Seconds. If exceeding the threshold ,relevant TCA will raise."
		::=  {  nptDs1PathCurrentEntry  6  }


	nptDs1PathCurrentSAS	OBJECT-TYPE	
		SYNTAX			Counter64
		MAX-ACCESS		read-only
		STATUS			current
		DESCRIPTION		"Threshold of SEF/AIS Seconds. If exceeding the threshold ,relevant TCA will raise"
		::=  {  nptDs1PathCurrentEntry  7  }


	nptDs1PathCurrentUAS	OBJECT-TYPE	
		SYNTAX			Counter64
		MAX-ACCESS		read-only
		STATUS			current
		DESCRIPTION		"unavailable seconds. When an SES lasts for 10 seconds, it becomes a UAS. 
		When there are no severely errored seconds within 10 seconds, it is no longer counted as a UAS. The UAS is not calculated in SES calculations."
		::=  {  nptDs1PathCurrentEntry  8  }


	nptDs1PathCurrentFEES	OBJECT-TYPE	
		SYNTAX			Counter64
		MAX-ACCESS		read-only
		STATUS			current
		DESCRIPTION		"far-end errored seconds."
		::=  {  nptDs1PathCurrentEntry  9  }


	nptDs1PathCurrentFESES	OBJECT-TYPE	
		SYNTAX			Counter64
		MAX-ACCESS		read-only
		STATUS			current
		DESCRIPTION		"far-end severely errored seconds"
		::=  {  nptDs1PathCurrentEntry  10  }


	nptDs1PathCurrentFECV	OBJECT-TYPE	
		SYNTAX			Counter64
		MAX-ACCESS		read-only
		STATUS			current
		DESCRIPTION		"far-end Coding Violations."
		::=  {  nptDs1PathCurrentEntry  11  }
		
	nptDs1PathCurrentFEUAS	OBJECT-TYPE	
		SYNTAX			Counter64
		MAX-ACCESS		read-only
		STATUS			current
		DESCRIPTION		"far-end unavailable seconds."
		::=  {  nptDs1PathCurrentEntry  12  }
		
	nptDs1PathCurrentFECSS	OBJECT-TYPE	
		SYNTAX			Counter64
		MAX-ACCESS		read-only
		STATUS			current
		DESCRIPTION		"Controlled Slip Seconds. If exceeding the threshold ,relevant TCA will raise"
		::=  {  nptDs1PathCurrentEntry  13  }
		
	nptDs1PathTotalTable	OBJECT-TYPE
		SYNTAX		SEQUENCE  OF  NptDs1PathTotalEntry
		MAX-ACCESS	not-accessible
		STATUS		current
		DESCRIPTION	"The Ds1Path current table contains various statistics
            being collected for the current 15 minute
            interval."
		::=  { nptDs1PathIfGroup  2 }

	nptDs1PathTotalEntry	OBJECT-TYPE
		SYNTAX		NptDs1PathTotalEntry
		MAX-ACCESS	not-accessible
		STATUS		current
		DESCRIPTION	"An entry in the Ds1Path Total table."
		INDEX		{  nptDs1PathTotalIndex  }
		::=  { nptDs1PathTotalTable 1 }

	NptDs1PathTotalEntry  ::=  SEQUENCE {
		nptDs1PathTotalIndex  Integer32,
		nptDs1PathTotalMoDescription  DisplayString,
		nptDs1PathTotalES  Counter64,
		nptDs1PathTotalSES  Counter64,
		nptDs1PathTotalCV  Counter64,
		nptDs1PathTotalCSS  Counter64,
		nptDs1PathTotalSAS  Counter64,
		nptDs1PathTotalUAS  Counter64,
		nptDs1PathTotalFEES  Counter64,
		nptDs1PathTotalFESES  Counter64,
		nptDs1PathTotalFECV  Counter64,
		nptDs1PathTotalFEUAS  Counter64,
		nptDs1PathTotalFECSS  Counter64
		}


	nptDs1PathTotalIndex	OBJECT-TYPE	
		SYNTAX			Integer32  ( -2147483648 .. 2147483647  ) 
		MAX-ACCESS		read-only
		STATUS			current
		DESCRIPTION		"The index value which uniquely identifies  the
            Ds1Path interface to which this entry is applicable."
		::=  {  nptDs1PathTotalEntry  1  }
		
		
	nptDs1PathTotalMoDescription	OBJECT-TYPE	
		SYNTAX			DisplayString 
		MAX-ACCESS		read-only
		STATUS			current
		DESCRIPTION		"Mo Description"
		::=  {  nptDs1PathTotalEntry  2  }


	nptDs1PathTotalES	OBJECT-TYPE	
		SYNTAX			Counter64
		MAX-ACCESS		read-only
		STATUS			current
		DESCRIPTION		"errored seconds. If errors occur within a certain second, this second is called an errored second."
		::=  {  nptDs1PathTotalEntry  3  }


	nptDs1PathTotalSES	OBJECT-TYPE	
		SYNTAX			Counter64
		MAX-ACCESS		read-only
		STATUS			current
		DESCRIPTION		"severely errored seconds. If there are errors in 30% of the frames, the errors exceed the threshold, 
		or the signal fails within a certain second, this second is called a severely errored second. 
		Errored seconds (ESs) are not counted when severely errored seconds occur."
		::=  {  nptDs1PathTotalEntry  4  }

		
	nptDs1PathTotalCV	OBJECT-TYPE	
		SYNTAX			Counter64
		MAX-ACCESS		read-only
		STATUS			current
		DESCRIPTION		"errored seconds. If errors occur within a certain second, this second is called an errored second."
		::=  {  nptDs1PathTotalEntry  5  }


	nptDs1PathTotalCSS	OBJECT-TYPE	
		SYNTAX			Counter64
		MAX-ACCESS		read-only
		STATUS			current
		DESCRIPTION		"Controlled Slip Seconds. If exceeding the threshold ,relevant TCA will raise."
		::=  {  nptDs1PathTotalEntry  6  }


	nptDs1PathTotalSAS	OBJECT-TYPE	
		SYNTAX			Counter64
		MAX-ACCESS		read-only
		STATUS			current
		DESCRIPTION		"Threshold of SEF/AIS Seconds. If exceeding the threshold ,relevant TCA will raise"
		::=  {  nptDs1PathTotalEntry  7  }


	nptDs1PathTotalUAS	OBJECT-TYPE	
		SYNTAX			Counter64
		MAX-ACCESS		read-only
		STATUS			current
		DESCRIPTION		"unavailable seconds. When an SES lasts for 10 seconds, it becomes a UAS. 
		When there are no severely errored seconds within 10 seconds, it is no longer counted as a UAS. The UAS is not calculated in SES calculations."
		::=  {  nptDs1PathTotalEntry  8  }


	nptDs1PathTotalFEES	OBJECT-TYPE	
		SYNTAX			Counter64
		MAX-ACCESS		read-only
		STATUS			current
		DESCRIPTION		"far-end errored seconds."
		::=  {  nptDs1PathTotalEntry  9  }


	nptDs1PathTotalFESES	OBJECT-TYPE	
		SYNTAX			Counter64
		MAX-ACCESS		read-only
		STATUS			current
		DESCRIPTION		"far-end severely errored seconds"
		::=  {  nptDs1PathTotalEntry  10  }


	nptDs1PathTotalFECV	OBJECT-TYPE	
		SYNTAX			Counter64
		MAX-ACCESS		read-only
		STATUS			current
		DESCRIPTION		"far-end Coding Violations."
		::=  {  nptDs1PathTotalEntry  11  }
		
	nptDs1PathTotalFEUAS	OBJECT-TYPE	
		SYNTAX			Counter64
		MAX-ACCESS		read-only
		STATUS			current
		DESCRIPTION		"far-end unavailable seconds."
		::=  {  nptDs1PathTotalEntry  12  }
		
	nptDs1PathTotalFECSS	OBJECT-TYPE	
		SYNTAX			Counter64
		MAX-ACCESS		read-only
		STATUS			current
		DESCRIPTION		"Controlled Slip Seconds. If exceeding the threshold ,relevant TCA will raise"
		::=  {  nptDs1PathTotalEntry  13  }
		
        
	nptDs3LineCurrentTable	OBJECT-TYPE
		SYNTAX		SEQUENCE  OF  NptDs3LineCurrentEntry
		MAX-ACCESS	not-accessible
		STATUS		current
		DESCRIPTION	"The Ds3Line current table contains various statistics
            being collected for the current 15 minute
            interval."
		::=  { nptDs3LineIfGroup  1 }

	nptDs3LineCurrentEntry	OBJECT-TYPE
		SYNTAX		NptDs3LineCurrentEntry
		MAX-ACCESS	not-accessible
		STATUS		current
		DESCRIPTION	"An entry in the Ds3Line Current table."
		INDEX		{  nptDs3LineCurrentIndex  }
		::=  { nptDs3LineCurrentTable 1 }

	NptDs3LineCurrentEntry  ::=  SEQUENCE {
		nptDs3LineCurrentIndex  Integer32,
		nptDs3LineCurrentMoDescription  DisplayString,
		nptDs3LineCurrentLOSSL  Counter64,
		nptDs3LineCurrentCVL  Counter64,
		nptDs3LineCurrentESL  Counter64,
		nptDs3LineCurrentSESL  Counter64,
		nptDs3LineCurrentUASL  Counter64
		}


	nptDs3LineCurrentIndex	OBJECT-TYPE	
		SYNTAX			Integer32  ( -2147483648 .. 2147483647  ) 
		MAX-ACCESS		read-only
		STATUS			current
		DESCRIPTION		"The index value which uniquely identifies  the
            Ds3Line interface to which this entry is applicable."
		::=  {  nptDs3LineCurrentEntry  1  }
		
		
	nptDs3LineCurrentMoDescription	OBJECT-TYPE	
		SYNTAX			DisplayString 
		MAX-ACCESS		read-only
		STATUS			current
		DESCRIPTION		"Mo Description"
		::=  {  nptDs3LineCurrentEntry  2  }

	nptDs3LineCurrentLOSSL	OBJECT-TYPE	
		SYNTAX			Counter64
		MAX-ACCESS		read-only
		STATUS			current
		DESCRIPTION		"Description"
		::=  {  nptDs3LineCurrentEntry  3  }

	nptDs3LineCurrentCVL	OBJECT-TYPE	
		SYNTAX			Counter64
		MAX-ACCESS		read-only
		STATUS			current
		DESCRIPTION		"Description"
		::=  {  nptDs3LineCurrentEntry  4  }

		
	nptDs3LineCurrentESL	OBJECT-TYPE	
		SYNTAX			Counter64
		MAX-ACCESS		read-only
		STATUS			current
		DESCRIPTION		"Description"
		::=  {  nptDs3LineCurrentEntry  5  }

	nptDs3LineCurrentSESL	OBJECT-TYPE	
		SYNTAX			Counter64
		MAX-ACCESS		read-only
		STATUS			current
		DESCRIPTION		"Description"
		::=  {  nptDs3LineCurrentEntry  6  }

	nptDs3LineCurrentUASL	OBJECT-TYPE	
		SYNTAX			Counter64
		MAX-ACCESS		read-only
		STATUS			current
		DESCRIPTION		"Description"
		::=  {  nptDs3LineCurrentEntry  7  }


		nptDs3LineTotalTable	OBJECT-TYPE
		SYNTAX		SEQUENCE  OF  NptDs3LineTotalEntry
		MAX-ACCESS	not-accessible
		STATUS		current
		DESCRIPTION	"The Ds3Line current table contains various statistics
            being collected for the current 15 minute
            interval."
		::=  { nptDs3LineIfGroup  2 }

	nptDs3LineTotalEntry	OBJECT-TYPE
		SYNTAX		NptDs3LineTotalEntry
		MAX-ACCESS	not-accessible
		STATUS		current
		DESCRIPTION	"An entry in the Ds3Line Total table."
		INDEX		{  nptDs3LineTotalIndex  }
		::=  { nptDs3LineTotalTable 1 }

	NptDs3LineTotalEntry  ::=  SEQUENCE {
		nptDs3LineTotalIndex  Integer32,
		nptDs3LineTotalMoDescription  DisplayString,
		nptDs3LineTotalLOSSL  Counter64,
		nptDs3LineTotalCVL  Counter64,
		nptDs3LineTotalESL  Counter64,
		nptDs3LineTotalSESL  Counter64,
        	nptDs3LineTotalUASL  Counter64
		}


	nptDs3LineTotalIndex	OBJECT-TYPE	
		SYNTAX			Integer32  ( -2147483648 .. 2147483647  ) 
		MAX-ACCESS		read-only
		STATUS			current
		DESCRIPTION		"The index value which uniquely identifies  the
            Ds3Line interface to which this entry is applicable."
		::=  {  nptDs3LineTotalEntry  1  }
		
		
	nptDs3LineTotalMoDescription	OBJECT-TYPE	
		SYNTAX			DisplayString 
		MAX-ACCESS		read-only
		STATUS			current
		DESCRIPTION		"Mo Description"
		::=  {  nptDs3LineTotalEntry  2  }

	nptDs3LineTotalLOSSL	OBJECT-TYPE	
		SYNTAX			Counter64
		MAX-ACCESS		read-only
		STATUS			current
		DESCRIPTION		"Description"
		::=  {  nptDs3LineTotalEntry  3  }

	nptDs3LineTotalCVL	OBJECT-TYPE	
		SYNTAX			Counter64
		MAX-ACCESS		read-only
		STATUS			current
		DESCRIPTION		"Description"
		::=  {  nptDs3LineTotalEntry  4  }

		
	nptDs3LineTotalESL	OBJECT-TYPE	
		SYNTAX			Counter64
		MAX-ACCESS		read-only
		STATUS			current
		DESCRIPTION		"Description"
		::=  {  nptDs3LineTotalEntry  5  }

	nptDs3LineTotalSESL	OBJECT-TYPE	
		SYNTAX			Counter64
		MAX-ACCESS		read-only
		STATUS			current
		DESCRIPTION		"Description"
		::=  {  nptDs3LineTotalEntry  6  }

	nptDs3LineTotalUASL	OBJECT-TYPE	
		SYNTAX			Counter64
		MAX-ACCESS		read-only
		STATUS			current
		DESCRIPTION		"Description"
		::=  {  nptDs3LineTotalEntry  7  }


		nptDs3PathCurrentTable	OBJECT-TYPE
		SYNTAX		SEQUENCE  OF  NptDs3PathCurrentEntry
		MAX-ACCESS	not-accessible
		STATUS		current
		DESCRIPTION	"The Ds3Path current table contains various statistics
            being collected for the current 15 minute
            interval."
		::=  { nptDs3PathIfGroup  1 }

	nptDs3PathCurrentEntry	OBJECT-TYPE
		SYNTAX		NptDs3PathCurrentEntry
		MAX-ACCESS	not-accessible
		STATUS		current
		DESCRIPTION	"An entry in the Ds3Path Current table."
		INDEX		{  nptDs3PathCurrentIndex  }
		::=  { nptDs3PathCurrentTable 1 }

	NptDs3PathCurrentEntry  ::=  SEQUENCE {
		nptDs3PathCurrentIndex  Integer32,
		nptDs3PathCurrentMoDescription  DisplayString,
        nptDs3PathCurrentCV  Counter64,
		nptDs3PathCurrentFERR  Counter64,
		nptDs3PathCurrentPERR  Counter64,
		nptDs3PathCurrentCPERR  Counter64,
		nptDs3PathCurrentFEBR  Counter64,
		nptDs3PathCurrentES  Counter64,
		nptDs3PathCurrentSES  Counter64,
		nptDs3PathCurrentUAS  Counter64,
		nptDs3PathCurrentFEES  Counter64,
		nptDs3PathCurrentFESES  Counter64,
		nptDs3PathCurrentFEUAS  Counter64
		}


	nptDs3PathCurrentIndex	OBJECT-TYPE	
		SYNTAX			Integer32  ( -2147483648 .. 2147483647  ) 
		MAX-ACCESS		read-only
		STATUS			current
		DESCRIPTION		"The index value which uniquely identifies  the
            Ds3Path interface to which this entry is applicable."
		::=  {  nptDs3PathCurrentEntry  1  }
		
		
	nptDs3PathCurrentMoDescription	OBJECT-TYPE	
		SYNTAX			DisplayString 
		MAX-ACCESS		read-only
		STATUS			current
		DESCRIPTION		"Mo Description"
		::=  {  nptDs3PathCurrentEntry  2  }

	nptDs3PathCurrentCV	OBJECT-TYPE	
		SYNTAX			Counter64
		MAX-ACCESS		read-only
		STATUS			current
		DESCRIPTION		"Description"
		::=  {  nptDs3PathCurrentEntry  3  }

	nptDs3PathCurrentFERR	OBJECT-TYPE	
		SYNTAX			Counter64
		MAX-ACCESS		read-only
		STATUS			current
		DESCRIPTION		"Description"
		::=  {  nptDs3PathCurrentEntry  4  }


	nptDs3PathCurrentPERR	OBJECT-TYPE	
		SYNTAX			Counter64
		MAX-ACCESS		read-only
		STATUS			current
		DESCRIPTION		"Description"
		::=  {  nptDs3PathCurrentEntry  5  }

		
	nptDs3PathCurrentCPERR	OBJECT-TYPE	
		SYNTAX			Counter64
		MAX-ACCESS		read-only
		STATUS			current
		DESCRIPTION		"Description"
		::=  {  nptDs3PathCurrentEntry 6  }


	nptDs3PathCurrentFEBR	OBJECT-TYPE	
		SYNTAX			Counter64
		MAX-ACCESS		read-only
		STATUS			current
		DESCRIPTION		"Description"
		::=  {  nptDs3PathCurrentEntry  7  }


	nptDs3PathCurrentES	OBJECT-TYPE	
		SYNTAX			Counter64
		MAX-ACCESS		read-only
		STATUS			current
		DESCRIPTION		"Description"
		::=  {  nptDs3PathCurrentEntry  8  }


	nptDs3PathCurrentSES	OBJECT-TYPE	
		SYNTAX			Counter64
		MAX-ACCESS		read-only
		STATUS			current
		DESCRIPTION		"Description"
		::=  {  nptDs3PathCurrentEntry  9  }


	nptDs3PathCurrentUAS	OBJECT-TYPE	
		SYNTAX			Counter64
		MAX-ACCESS		read-only
		STATUS			current
		DESCRIPTION		"Description"
		::=  {  nptDs3PathCurrentEntry  10  }


	nptDs3PathCurrentFEES	OBJECT-TYPE	
		SYNTAX			Counter64
		MAX-ACCESS		read-only
		STATUS			current
		DESCRIPTION		"Description"
		::=  {  nptDs3PathCurrentEntry  11  }


	nptDs3PathCurrentFESES	OBJECT-TYPE	
		SYNTAX			Counter64
		MAX-ACCESS		read-only
		STATUS			current
		DESCRIPTION		"Description."
		::=  {  nptDs3PathCurrentEntry  12  }
		
	nptDs3PathCurrentFEUAS	OBJECT-TYPE	
		SYNTAX			Counter64
		MAX-ACCESS		read-only
		STATUS			current
		DESCRIPTION		"Description."
		::=  {  nptDs3PathCurrentEntry  13  }
		
	nptDs3PathTotalTable	OBJECT-TYPE
		SYNTAX		SEQUENCE  OF  NptDs3PathTotalEntry
		MAX-ACCESS	not-accessible
		STATUS		current
		DESCRIPTION	"The Ds3Path current table contains various statistics
            being collected for the current 15 minute
            interval."
		::=  { nptDs3PathIfGroup  2 }

	nptDs3PathTotalEntry	OBJECT-TYPE
		SYNTAX		NptDs3PathTotalEntry
		MAX-ACCESS	not-accessible
		STATUS		current
		DESCRIPTION	"An entry in the Ds3Path Total table."
		INDEX		{  nptDs3PathTotalIndex  }
		::=  { nptDs3PathTotalTable 1 }

	NptDs3PathTotalEntry  ::=  SEQUENCE {
		nptDs3PathTotalIndex  Integer32,
		nptDs3PathTotalMoDescription  DisplayString,
        nptDs3PathTotalCV  Counter64,
		nptDs3PathTotalFERR  Counter64,
		nptDs3PathTotalPERR  Counter64,
		nptDs3PathTotalCPERR  Counter64,
		nptDs3PathTotalFEBR  Counter64,
		nptDs3PathTotalES  Counter64,
		nptDs3PathTotalSES  Counter64,
		nptDs3PathTotalUAS  Counter64,
		nptDs3PathTotalFEES  Counter64,
		nptDs3PathTotalFESES  Counter64,
		nptDs3PathTotalFEUAS  Counter64
		}


	nptDs3PathTotalIndex	OBJECT-TYPE	
		SYNTAX			Integer32  ( -2147483648 .. 2147483647  ) 
		MAX-ACCESS		read-only
		STATUS			current
		DESCRIPTION		"The index value which uniquely identifies  the
            Ds3Path interface to which this entry is applicable."
		::=  {  nptDs3PathTotalEntry  1  }
		
		
	nptDs3PathTotalMoDescription	OBJECT-TYPE	
		SYNTAX			DisplayString 
		MAX-ACCESS		read-only
		STATUS			current
		DESCRIPTION		"Mo Description"
		::=  {  nptDs3PathTotalEntry  2  }

	nptDs3PathTotalCV OBJECT-TYPE	
		SYNTAX			Counter64
		MAX-ACCESS		read-only
		STATUS			current
		DESCRIPTION		"Description"
		::=  {  nptDs3PathTotalEntry  3  }

	nptDs3PathTotalFERR	OBJECT-TYPE	
		SYNTAX			Counter64
		MAX-ACCESS		read-only
		STATUS			current
		DESCRIPTION		"Description"
		::=  {  nptDs3PathTotalEntry  4  }


	nptDs3PathTotalPERR	OBJECT-TYPE	
		SYNTAX			Counter64
		MAX-ACCESS		read-only
		STATUS			current
		DESCRIPTION		"Description"
		::=  {  nptDs3PathTotalEntry  5  }

		
	nptDs3PathTotalCPERR	OBJECT-TYPE	
		SYNTAX			Counter64
		MAX-ACCESS		read-only
		STATUS			current
		DESCRIPTION		"Description."
		::=  {  nptDs3PathTotalEntry 6  }


	nptDs3PathTotalFEBR	OBJECT-TYPE	
		SYNTAX			Counter64
		MAX-ACCESS		read-only
		STATUS			current
		DESCRIPTION		"Description"
		::=  {  nptDs3PathTotalEntry  7  }


	nptDs3PathTotalES	OBJECT-TYPE	
		SYNTAX			Counter64
		MAX-ACCESS		read-only
		STATUS			current
		DESCRIPTION		"Description"
		::=  {  nptDs3PathTotalEntry  8  }


	nptDs3PathTotalSES	OBJECT-TYPE	
		SYNTAX			Counter64
		MAX-ACCESS		read-only
		STATUS			current
		DESCRIPTION		"Description"
		::=  {  nptDs3PathTotalEntry  9  }


	nptDs3PathTotalUAS	OBJECT-TYPE	
		SYNTAX			Counter64
		MAX-ACCESS		read-only
		STATUS			current
		DESCRIPTION		"Description"
		::=  {  nptDs3PathTotalEntry  10  }


	nptDs3PathTotalFEES	OBJECT-TYPE	
		SYNTAX			Counter64
		MAX-ACCESS		read-only
		STATUS			current
		DESCRIPTION		"Description"
		::=  {  nptDs3PathTotalEntry  11  }


	nptDs3PathTotalFESES	OBJECT-TYPE	
		SYNTAX			Counter64
		MAX-ACCESS		read-only
		STATUS			current
		DESCRIPTION		"Description"
		::=  {  nptDs3PathTotalEntry  12  }
		
	nptDs3PathTotalFEUAS	OBJECT-TYPE	
		SYNTAX			Counter64
		MAX-ACCESS		read-only
		STATUS			current
		DESCRIPTION		"Description"
		::=  {  nptDs3PathTotalEntry  13  }
		
        
	nptCesServiceIfCurrentTable	OBJECT-TYPE
		SYNTAX		SEQUENCE  OF  NptCesServiceIfCurrentEntry
		MAX-ACCESS	not-accessible
		STATUS		current
		DESCRIPTION	"Description"
		::=  { nptCesServiceIfGroup  1 }

	nptCesServiceIfCurrentEntry	OBJECT-TYPE
		SYNTAX		NptCesServiceIfCurrentEntry
		MAX-ACCESS	not-accessible
		STATUS		current
		DESCRIPTION	"Row Description"
		INDEX		{  nptCesServiceIfCurrentIndex  }
		::=  { nptCesServiceIfCurrentTable 1 }

	NptCesServiceIfCurrentEntry  ::=  SEQUENCE {
		nptCesServiceIfCurrentIndex  Integer32,
		nptCesServiceIfCurrentDescription  DisplayString,
		nptCesServiceIfCurrentAdminDownSec  Counter64,
		nptCesServiceIfCurrentOperDownSec  Counter64,
		nptCesServiceIfCurrentTxPsnPkts  Counter64,
		nptCesServiceIfCurrentTxPsnOctets  Counter64,
		nptCesServiceIfCurrentTxPsnDiscardPkts  Counter64,
		nptCesServiceIfCurrentTxPsnDiscardOctets  Counter64,
		nptCesServiceIfCurrentRxPsnOverrunEvents  Counter64,
		nptCesServiceIfCurrentRxPsnUnderrunEvents  Counter64,
		nptCesServiceIfCurrentRxPsnLopsEvents  Counter64,
		nptCesServiceIfCurrentRxPsnSwitchoverEvents  Counter64,
		nptCesServiceIfCurrentRxPsnValidPkts  Counter64,
		nptCesServiceIfCurrentRxPsnValidOctets  Counter64,
		nptCesServiceIfCurrentRxPsnReorderPkts  Counter64,
		nptCesServiceIfCurrentRxPsnLbitDiscardPkts  Counter64,
		nptCesServiceIfCurrentRxPsnStrayDiscardPkts  Counter64,
		nptCesServiceIfCurrentRxPsnMalformDiscardPkts  Counter64,
		nptCesServiceIfCurrentRxPsnDuplicatDiscardPkts  Counter64,
		nptCesServiceIfCurrentRxPsnOowDiscardPkts  Counter64,
		nptCesServiceIfCurrentRxPsnOverrunDiscardPkts  Counter64,
		nptCesServiceIfCurrentRxPsnLostPkts  Counter64,
		nptCesServiceIfCurrentRxPsnLostOctets  Counter64,
		nptCesServiceIfCurrentRxPsnPatternPackets  Counter64,
		nptCesServiceIfCurrentRxPsnPatternOctets  Counter64,
		nptCesServiceIfCurrentRxPsnLbitSec  Counter64,
		nptCesServiceIfCurrentRxPsnRbitSec  Counter64,
		nptCesServiceIfCurrentRxPsnLMbitSec  Counter64,
		nptCesServiceIfCurrentRxPsnES  Counter64,
		nptCesServiceIfCurrentRxPsnSES  Counter64,
		nptCesServiceIfCurrentRxPsnUAS  Counter64,
		nptCesServiceIfCurrentRxPsnRecClkFreeRunEvents  Counter64,
		nptCesServiceIfCurrentRxPsnRecClkPMSMEvents  Counter64,
		nptCesServiceIfCurrentRxPsnRecClkHoldoverTime  Counter64,
		nptCesServiceIfCurrentLdpInNotificationStatus0x24  Counter64,
		nptCesServiceIfCurrentLdpInNotificationStatus0x26  Counter64,
		nptCesServiceIfCurrentLdpInNotificationStatus0x27  Counter64,
		nptCesServiceIfCurrentLdpInNotificationStatus0x2A  Counter64,
		nptCesServiceIfCurrentRxPsnDeniedPkts  Counter64,
		nptCesServiceIfCurrentRxPsnGapsPkts  Counter64,
        nptCesServiceIfCurrentRxPsnPkts  Counter64,
        nptCesServiceIfCurrentRxDroppedMisorderedPkts  Counter64,
        nptCesServiceIfCurrentRxPsnUnderrunDiscardPkts  Counter64
		}


	nptCesServiceIfCurrentIndex	OBJECT-TYPE	
		SYNTAX			Integer32  ( -2147483648 .. 2147483647  ) 
		MAX-ACCESS		read-only
		STATUS			current
		DESCRIPTION		"Column Description"
		::=  {  nptCesServiceIfCurrentEntry  1  }
		
		
	nptCesServiceIfCurrentDescription	OBJECT-TYPE	
		SYNTAX			DisplayString 
		MAX-ACCESS		read-only
		STATUS			current
		DESCRIPTION		"Mo Description"
		::=  {  nptCesServiceIfCurrentEntry  2  }


	nptCesServiceIfCurrentAdminDownSec	OBJECT-TYPE	
		SYNTAX			Counter64
		MAX-ACCESS		read-only
		STATUS			current
		DESCRIPTION		"Column Description"
		::=  {  nptCesServiceIfCurrentEntry  3  }


	nptCesServiceIfCurrentOperDownSec	OBJECT-TYPE	
		SYNTAX			Counter64
		MAX-ACCESS		read-only
		STATUS			current
		DESCRIPTION		"Column Description"
		::=  {  nptCesServiceIfCurrentEntry  4  }


	nptCesServiceIfCurrentTxPsnPkts	OBJECT-TYPE	
		SYNTAX			Counter64
		MAX-ACCESS		read-only
		STATUS			current
		DESCRIPTION		"Column Description"
		::=  {  nptCesServiceIfCurrentEntry  5  }


	nptCesServiceIfCurrentTxPsnOctets	OBJECT-TYPE	
		SYNTAX			Counter64
		MAX-ACCESS		read-only
		STATUS			current
		DESCRIPTION		"Column Description"
		::=  {  nptCesServiceIfCurrentEntry  6  }


	nptCesServiceIfCurrentTxPsnDiscardPkts	OBJECT-TYPE	
		SYNTAX			Counter64
		MAX-ACCESS		read-only
		STATUS			current
		DESCRIPTION		"Column Description"
		::=  {  nptCesServiceIfCurrentEntry  7  }


	nptCesServiceIfCurrentTxPsnDiscardOctets	OBJECT-TYPE	
		SYNTAX			Counter64
		MAX-ACCESS		read-only
		STATUS			current
		DESCRIPTION		"Column Description"
		::=  {  nptCesServiceIfCurrentEntry  8  }


	nptCesServiceIfCurrentRxPsnOverrunEvents	OBJECT-TYPE	
		SYNTAX			Counter64
		MAX-ACCESS		read-only
		STATUS			current
		DESCRIPTION		"Column Description"
		::=  {  nptCesServiceIfCurrentEntry  9  }


	nptCesServiceIfCurrentRxPsnUnderrunEvents	OBJECT-TYPE	
		SYNTAX			Counter64
		MAX-ACCESS		read-only
		STATUS			current
		DESCRIPTION		"Column Description"
		::=  {  nptCesServiceIfCurrentEntry  10  }


	nptCesServiceIfCurrentRxPsnLopsEvents	OBJECT-TYPE	
		SYNTAX			Counter64
		MAX-ACCESS		read-only
		STATUS			current
		DESCRIPTION		"Column Description"
		::=  {  nptCesServiceIfCurrentEntry  11  }


	nptCesServiceIfCurrentRxPsnSwitchoverEvents	OBJECT-TYPE	
		SYNTAX			Counter64
		MAX-ACCESS		read-only
		STATUS			current
		DESCRIPTION		"Column Description"
		::=  {  nptCesServiceIfCurrentEntry  12  }


	nptCesServiceIfCurrentRxPsnValidPkts	OBJECT-TYPE	
		SYNTAX			Counter64
		MAX-ACCESS		read-only
		STATUS			current
		DESCRIPTION		"Column Description"
		::=  {  nptCesServiceIfCurrentEntry  13  }


	nptCesServiceIfCurrentRxPsnValidOctets	OBJECT-TYPE	
		SYNTAX			Counter64
		MAX-ACCESS		read-only
		STATUS			current
		DESCRIPTION		"Column Description"
		::=  {  nptCesServiceIfCurrentEntry  14  }


	nptCesServiceIfCurrentRxPsnReorderPkts	OBJECT-TYPE	
		SYNTAX			Counter64
		MAX-ACCESS		read-only
		STATUS			current
		DESCRIPTION		"Column Description"
		::=  {  nptCesServiceIfCurrentEntry  15  }


	nptCesServiceIfCurrentRxPsnLbitDiscardPkts	OBJECT-TYPE	
		SYNTAX			Counter64
		MAX-ACCESS		read-only
		STATUS			current
		DESCRIPTION		"Column Description"
		::=  {  nptCesServiceIfCurrentEntry  16  }


	nptCesServiceIfCurrentRxPsnStrayDiscardPkts	OBJECT-TYPE	
		SYNTAX			Counter64
		MAX-ACCESS		read-only
		STATUS			current
		DESCRIPTION		"Column Description"
		::=  {  nptCesServiceIfCurrentEntry  17  }


	nptCesServiceIfCurrentRxPsnMalformDiscardPkts	OBJECT-TYPE	
		SYNTAX			Counter64
		MAX-ACCESS		read-only
		STATUS			current
		DESCRIPTION		"Column Description"
		::=  {  nptCesServiceIfCurrentEntry  18  }


	nptCesServiceIfCurrentRxPsnDuplicatDiscardPkts	OBJECT-TYPE	
		SYNTAX			Counter64
		MAX-ACCESS		read-only
		STATUS			current
		DESCRIPTION		"Column Description"
		::=  {  nptCesServiceIfCurrentEntry  19  }


	nptCesServiceIfCurrentRxPsnOowDiscardPkts	OBJECT-TYPE	
		SYNTAX			Counter64
		MAX-ACCESS		read-only
		STATUS			current
		DESCRIPTION		"Column Description"
		::=  {  nptCesServiceIfCurrentEntry  20  }


	nptCesServiceIfCurrentRxPsnOverrunDiscardPkts	OBJECT-TYPE	
		SYNTAX			Counter64
		MAX-ACCESS		read-only
		STATUS			current
		DESCRIPTION		"Column Description"
		::=  {  nptCesServiceIfCurrentEntry  21  }


	nptCesServiceIfCurrentRxPsnLostPkts	OBJECT-TYPE	
		SYNTAX			Counter64
		MAX-ACCESS		read-only
		STATUS			current
		DESCRIPTION		"Column Description"
		::=  {  nptCesServiceIfCurrentEntry  22  }


	nptCesServiceIfCurrentRxPsnLostOctets	OBJECT-TYPE	
		SYNTAX			Counter64
		MAX-ACCESS		read-only
		STATUS			current
		DESCRIPTION		"Description"
		::=  {  nptCesServiceIfCurrentEntry  23  }


	nptCesServiceIfCurrentRxPsnPatternPackets	OBJECT-TYPE	
		SYNTAX			Counter64
		MAX-ACCESS		read-only
		STATUS			current
		DESCRIPTION		"Column Description"
		::=  {  nptCesServiceIfCurrentEntry  24  }


	nptCesServiceIfCurrentRxPsnPatternOctets	OBJECT-TYPE	
		SYNTAX			Counter64
		MAX-ACCESS		read-only
		STATUS			current
		DESCRIPTION		"Column Description"
		::=  {  nptCesServiceIfCurrentEntry  25  }


	nptCesServiceIfCurrentRxPsnLbitSec	OBJECT-TYPE	
		SYNTAX			Counter64
		MAX-ACCESS		read-only
		STATUS			current
		DESCRIPTION		"Column Description"
		::=  {  nptCesServiceIfCurrentEntry  26  }


	nptCesServiceIfCurrentRxPsnRbitSec	OBJECT-TYPE	
		SYNTAX			Counter64
		MAX-ACCESS		read-only
		STATUS			current
		DESCRIPTION		"Column Description"
		::=  {  nptCesServiceIfCurrentEntry  27  }


	nptCesServiceIfCurrentRxPsnLMbitSec	OBJECT-TYPE	
		SYNTAX			Counter64
		MAX-ACCESS		read-only
		STATUS			current
		DESCRIPTION		"Column Description"
		::=  {  nptCesServiceIfCurrentEntry  28  }


	nptCesServiceIfCurrentRxPsnES	OBJECT-TYPE	
		SYNTAX			Counter64
		MAX-ACCESS		read-only
		STATUS			current
		DESCRIPTION		"Column Description"
		::=  {  nptCesServiceIfCurrentEntry  29  }


	nptCesServiceIfCurrentRxPsnSES	OBJECT-TYPE	
		SYNTAX			Counter64
		MAX-ACCESS		read-only
		STATUS			current
		DESCRIPTION		"Column Description"
		::=  {  nptCesServiceIfCurrentEntry  30  }


	nptCesServiceIfCurrentRxPsnUAS	OBJECT-TYPE	
		SYNTAX			Counter64
		MAX-ACCESS		read-only
		STATUS			current
		DESCRIPTION		"Column Description"
		::=  {  nptCesServiceIfCurrentEntry  31  }


	nptCesServiceIfCurrentRxPsnRecClkFreeRunEvents	OBJECT-TYPE	
		SYNTAX			Counter64
		MAX-ACCESS		read-only
		STATUS			current
		DESCRIPTION		"Column Description"
		::=  {  nptCesServiceIfCurrentEntry  32  }


	nptCesServiceIfCurrentRxPsnRecClkPMSMEvents	OBJECT-TYPE	
		SYNTAX			Counter64
		MAX-ACCESS		read-only
		STATUS			current
		DESCRIPTION		"Column Description"
		::=  {  nptCesServiceIfCurrentEntry  33  }


	nptCesServiceIfCurrentRxPsnRecClkHoldoverTime	OBJECT-TYPE	
		SYNTAX			Counter64
		MAX-ACCESS		read-only
		STATUS			current
		DESCRIPTION		"Column Description"
		::=  {  nptCesServiceIfCurrentEntry  34  }


	nptCesServiceIfCurrentLdpInNotificationStatus0x24	OBJECT-TYPE	
		SYNTAX			Counter64
		MAX-ACCESS		read-only
		STATUS			current
		DESCRIPTION		"Column Description"
		::=  {  nptCesServiceIfCurrentEntry  35  }


	nptCesServiceIfCurrentLdpInNotificationStatus0x26	OBJECT-TYPE	
		SYNTAX			Counter64
		MAX-ACCESS		read-only
		STATUS			current
		DESCRIPTION		"Column Description"
		::=  {  nptCesServiceIfCurrentEntry  36  }


	nptCesServiceIfCurrentLdpInNotificationStatus0x27	OBJECT-TYPE	
		SYNTAX			Counter64
		MAX-ACCESS		read-only
		STATUS			current
		DESCRIPTION		"Column Description"
		::=  {  nptCesServiceIfCurrentEntry  37  }


	nptCesServiceIfCurrentLdpInNotificationStatus0x2A	OBJECT-TYPE	
		SYNTAX			Counter64
		MAX-ACCESS		read-only
		STATUS			current
		DESCRIPTION		"Column Description"
		::=  {  nptCesServiceIfCurrentEntry  38  }


	nptCesServiceIfCurrentRxPsnDeniedPkts	OBJECT-TYPE	
		SYNTAX			Counter64
		MAX-ACCESS		read-only
		STATUS			current
		DESCRIPTION		"Column Description"
		::=  {  nptCesServiceIfCurrentEntry  39  }


	nptCesServiceIfCurrentRxPsnGapsPkts	OBJECT-TYPE	
		SYNTAX			Counter64
		MAX-ACCESS		read-only
		STATUS			current
		DESCRIPTION		"Column Description"
		::=  {  nptCesServiceIfCurrentEntry  40  }


	nptCesServiceIfCurrentRxPsnPkts	OBJECT-TYPE	
		SYNTAX			Counter64
		MAX-ACCESS		read-only
		STATUS			current
		DESCRIPTION		"Column Description"
		::=  {  nptCesServiceIfCurrentEntry  41  }


	nptCesServiceIfCurrentRxDroppedMisorderedPkts	OBJECT-TYPE	
		SYNTAX			Counter64
		MAX-ACCESS		read-only
		STATUS			current
		DESCRIPTION		"Column Description"
		::=  {  nptCesServiceIfCurrentEntry  42  }


	nptCesServiceIfCurrentRxPsnUnderrunDiscardPkts	OBJECT-TYPE	
		SYNTAX			Counter64
		MAX-ACCESS		read-only
		STATUS			current
		DESCRIPTION		"Column Description"
		::=  {  nptCesServiceIfCurrentEntry  43  }
		
		
	nptCesServiceIfTotalTable	OBJECT-TYPE
		SYNTAX		SEQUENCE  OF  NptCesServiceIfTotalEntry
		MAX-ACCESS	not-accessible
		STATUS		current
		DESCRIPTION	"Description"
		::=  { nptCesServiceIfGroup  2 }

	nptCesServiceIfTotalEntry	OBJECT-TYPE
		SYNTAX		NptCesServiceIfTotalEntry
		MAX-ACCESS	not-accessible
		STATUS		current
		DESCRIPTION	"Row Description"
		INDEX		{  nptCesServiceIfTotalIndex  }
		::=  { nptCesServiceIfTotalTable 1 }

	NptCesServiceIfTotalEntry  ::=  SEQUENCE {
		nptCesServiceIfTotalIndex  Integer32,
		nptCesServiceIfTotalDescription  DisplayString,
		nptCesServiceIfTotalAdminDownSec  Counter64,
		nptCesServiceIfTotalOperDownSec  Counter64,
		nptCesServiceIfTotalTxPsnPkts  Counter64,
		nptCesServiceIfTotalTxPsnOctets  Counter64,
		nptCesServiceIfTotalTxPsnDiscardPkts  Counter64,
		nptCesServiceIfTotalTxPsnDiscardOctets  Counter64,
		nptCesServiceIfTotalRxPsnOverrunEvents  Counter64,
		nptCesServiceIfTotalRxPsnUnderrunEvents  Counter64,
		nptCesServiceIfTotalRxPsnLopsEvents  Counter64,
		nptCesServiceIfTotalRxPsnSwitchoverEvents  Counter64,
		nptCesServiceIfTotalRxPsnValidPkts  Counter64,
		nptCesServiceIfTotalRxPsnValidOctets  Counter64,
		nptCesServiceIfTotalRxPsnReorderPkts  Counter64,
		nptCesServiceIfTotalRxPsnLbitDiscardPkts  Counter64,
		nptCesServiceIfTotalRxPsnStrayDiscardPkts  Counter64,
		nptCesServiceIfTotalRxPsnMalformDiscardPkts  Counter64,
		nptCesServiceIfTotalRxPsnDuplicatDiscardPkts  Counter64,
		nptCesServiceIfTotalRxPsnOowDiscardPkts  Counter64,
		nptCesServiceIfTotalRxPsnOverrunDiscardPkts  Counter64,
		nptCesServiceIfTotalRxPsnLostPkts  Counter64,
		nptCesServiceIfTotalRxPsnLostOctets  Counter64,
		nptCesServiceIfTotalRxPsnPatternPackets  Counter64,
		nptCesServiceIfTotalRxPsnPatternOctets  Counter64,
		nptCesServiceIfTotalRxPsnLbitSec  Counter64,
		nptCesServiceIfTotalRxPsnRbitSec  Counter64,
		nptCesServiceIfTotalRxPsnLMbitSec  Counter64,
		nptCesServiceIfTotalRxPsnES  Counter64,
		nptCesServiceIfTotalRxPsnSES  Counter64,
		nptCesServiceIfTotalRxPsnUAS  Counter64,
		nptCesServiceIfTotalRxPsnRecClkFreeRunEvents  Counter64,
		nptCesServiceIfTotalRxPsnRecClkPMSMEvents  Counter64,
		nptCesServiceIfTotalRxPsnRecClkHoldoverTime  Counter64,
		nptCesServiceIfTotalLdpInNotificationStatus0x24  Counter64,
		nptCesServiceIfTotalLdpInNotificationStatus0x26  Counter64,
		nptCesServiceIfTotalLdpInNotificationStatus0x27  Counter64,
		nptCesServiceIfTotalLdpInNotificationStatus0x2A  Counter64,
		nptCesServiceIfTotalRxPsnDeniedPkts  Counter64,
		nptCesServiceIfTotalRxPsnGapsPkts  Counter64,
        nptCesServiceIfTotalRxPsnPkts  Counter64,
        nptCesServiceIfTotalRxDroppedMisorderedPkts  Counter64,
        nptCesServiceIfTotalRxPsnUnderrunDiscardPkts  Counter64
		}


	nptCesServiceIfTotalIndex	OBJECT-TYPE	
		SYNTAX			Integer32  ( -2147483648 .. 2147483647  ) 
		MAX-ACCESS		read-only
		STATUS			current
		DESCRIPTION		"Column Description"
		::=  {  nptCesServiceIfTotalEntry  1  }
		
		
	nptCesServiceIfTotalDescription	OBJECT-TYPE	
		SYNTAX			DisplayString 
		MAX-ACCESS		read-only
		STATUS			current
		DESCRIPTION		"Mo Description"
		::=  {  nptCesServiceIfTotalEntry  2  }


	nptCesServiceIfTotalAdminDownSec	OBJECT-TYPE	
		SYNTAX			Counter64
		MAX-ACCESS		read-only
		STATUS			current
		DESCRIPTION		"Column Description"
		::=  {  nptCesServiceIfTotalEntry  3  }


	nptCesServiceIfTotalOperDownSec	OBJECT-TYPE	
		SYNTAX			Counter64
		MAX-ACCESS		read-only
		STATUS			current
		DESCRIPTION		"Column Description"
		::=  {  nptCesServiceIfTotalEntry  4  }


	nptCesServiceIfTotalTxPsnPkts	OBJECT-TYPE	
		SYNTAX			Counter64
		MAX-ACCESS		read-only
		STATUS			current
		DESCRIPTION		"Column Description"
		::=  {  nptCesServiceIfTotalEntry  5  }


	nptCesServiceIfTotalTxPsnOctets	OBJECT-TYPE	
		SYNTAX			Counter64
		MAX-ACCESS		read-only
		STATUS			current
		DESCRIPTION		"Column Description"
		::=  {  nptCesServiceIfTotalEntry  6  }


	nptCesServiceIfTotalTxPsnDiscardPkts	OBJECT-TYPE	
		SYNTAX			Counter64
		MAX-ACCESS		read-only
		STATUS			current
		DESCRIPTION		"Column Description"
		::=  {  nptCesServiceIfTotalEntry  7  }


	nptCesServiceIfTotalTxPsnDiscardOctets	OBJECT-TYPE	
		SYNTAX			Counter64
		MAX-ACCESS		read-only
		STATUS			current
		DESCRIPTION		"Column Description"
		::=  {  nptCesServiceIfTotalEntry  8  }


	nptCesServiceIfTotalRxPsnOverrunEvents	OBJECT-TYPE	
		SYNTAX			Counter64
		MAX-ACCESS		read-only
		STATUS			current
		DESCRIPTION		"Column Description"
		::=  {  nptCesServiceIfTotalEntry  9  }


	nptCesServiceIfTotalRxPsnUnderrunEvents	OBJECT-TYPE	
		SYNTAX			Counter64
		MAX-ACCESS		read-only
		STATUS			current
		DESCRIPTION		"Column Description"
		::=  {  nptCesServiceIfTotalEntry  10  }


	nptCesServiceIfTotalRxPsnLopsEvents	OBJECT-TYPE	
		SYNTAX			Counter64
		MAX-ACCESS		read-only
		STATUS			current
		DESCRIPTION		"Column Description"
		::=  {  nptCesServiceIfTotalEntry  11  }


	nptCesServiceIfTotalRxPsnSwitchoverEvents	OBJECT-TYPE	
		SYNTAX			Counter64
		MAX-ACCESS		read-only
		STATUS			current
		DESCRIPTION		"Column Description"
		::=  {  nptCesServiceIfTotalEntry  12  }


	nptCesServiceIfTotalRxPsnValidPkts	OBJECT-TYPE	
		SYNTAX			Counter64
		MAX-ACCESS		read-only
		STATUS			current
		DESCRIPTION		"Column Description"
		::=  {  nptCesServiceIfTotalEntry  13  }


	nptCesServiceIfTotalRxPsnValidOctets	OBJECT-TYPE	
		SYNTAX			Counter64
		MAX-ACCESS		read-only
		STATUS			current
		DESCRIPTION		"Column Description"
		::=  {  nptCesServiceIfTotalEntry  14  }


	nptCesServiceIfTotalRxPsnReorderPkts	OBJECT-TYPE	
		SYNTAX			Counter64
		MAX-ACCESS		read-only
		STATUS			current
		DESCRIPTION		"Column Description"
		::=  {  nptCesServiceIfTotalEntry  15  }


	nptCesServiceIfTotalRxPsnLbitDiscardPkts	OBJECT-TYPE	
		SYNTAX			Counter64
		MAX-ACCESS		read-only
		STATUS			current
		DESCRIPTION		"Column Description"
		::=  {  nptCesServiceIfTotalEntry  16  }


	nptCesServiceIfTotalRxPsnStrayDiscardPkts	OBJECT-TYPE	
		SYNTAX			Counter64
		MAX-ACCESS		read-only
		STATUS			current
		DESCRIPTION		"Column Description"
		::=  {  nptCesServiceIfTotalEntry  17  }


	nptCesServiceIfTotalRxPsnMalformDiscardPkts	OBJECT-TYPE	
		SYNTAX			Counter64
		MAX-ACCESS		read-only
		STATUS			current
		DESCRIPTION		"Column Description"
		::=  {  nptCesServiceIfTotalEntry  18  }


	nptCesServiceIfTotalRxPsnDuplicatDiscardPkts	OBJECT-TYPE	
		SYNTAX			Counter64
		MAX-ACCESS		read-only
		STATUS			current
		DESCRIPTION		"Column Description"
		::=  {  nptCesServiceIfTotalEntry  19  }


	nptCesServiceIfTotalRxPsnOowDiscardPkts	OBJECT-TYPE	
		SYNTAX			Counter64
		MAX-ACCESS		read-only
		STATUS			current
		DESCRIPTION		"Column Description"
		::=  {  nptCesServiceIfTotalEntry  20  }


	nptCesServiceIfTotalRxPsnOverrunDiscardPkts	OBJECT-TYPE	
		SYNTAX			Counter64
		MAX-ACCESS		read-only
		STATUS			current
		DESCRIPTION		"Column Description"
		::=  {  nptCesServiceIfTotalEntry  21  }


	nptCesServiceIfTotalRxPsnLostPkts	OBJECT-TYPE	
		SYNTAX			Counter64
		MAX-ACCESS		read-only
		STATUS			current
		DESCRIPTION		"Column Description"
		::=  {  nptCesServiceIfTotalEntry  22  }


	nptCesServiceIfTotalRxPsnLostOctets	OBJECT-TYPE	
		SYNTAX			Counter64
		MAX-ACCESS		read-only
		STATUS			current
		DESCRIPTION		"Description"
		::=  {  nptCesServiceIfTotalEntry  23  }


	nptCesServiceIfTotalRxPsnPatternPackets	OBJECT-TYPE	
		SYNTAX			Counter64
		MAX-ACCESS		read-only
		STATUS			current
		DESCRIPTION		"Column Description"
		::=  {  nptCesServiceIfTotalEntry  24  }


	nptCesServiceIfTotalRxPsnPatternOctets	OBJECT-TYPE	
		SYNTAX			Counter64
		MAX-ACCESS		read-only
		STATUS			current
		DESCRIPTION		"Column Description"
		::=  {  nptCesServiceIfTotalEntry  25  }


	nptCesServiceIfTotalRxPsnLbitSec	OBJECT-TYPE	
		SYNTAX			Counter64
		MAX-ACCESS		read-only
		STATUS			current
		DESCRIPTION		"Column Description"
		::=  {  nptCesServiceIfTotalEntry  26  }


	nptCesServiceIfTotalRxPsnRbitSec	OBJECT-TYPE	
		SYNTAX			Counter64
		MAX-ACCESS		read-only
		STATUS			current
		DESCRIPTION		"Column Description"
		::=  {  nptCesServiceIfTotalEntry  27  }


	nptCesServiceIfTotalRxPsnLMbitSec	OBJECT-TYPE	
		SYNTAX			Counter64
		MAX-ACCESS		read-only
		STATUS			current
		DESCRIPTION		"Column Description"
		::=  {  nptCesServiceIfTotalEntry  28  }


	nptCesServiceIfTotalRxPsnES	OBJECT-TYPE	
		SYNTAX			Counter64
		MAX-ACCESS		read-only
		STATUS			current
		DESCRIPTION		"Column Description"
		::=  {  nptCesServiceIfTotalEntry  29  }


	nptCesServiceIfTotalRxPsnSES	OBJECT-TYPE	
		SYNTAX			Counter64
		MAX-ACCESS		read-only
		STATUS			current
		DESCRIPTION		"Column Description"
		::=  {  nptCesServiceIfTotalEntry  30  }


	nptCesServiceIfTotalRxPsnUAS	OBJECT-TYPE	
		SYNTAX			Counter64
		MAX-ACCESS		read-only
		STATUS			current
		DESCRIPTION		"Column Description"
		::=  {  nptCesServiceIfTotalEntry  31  }


	nptCesServiceIfTotalRxPsnRecClkFreeRunEvents	OBJECT-TYPE	
		SYNTAX			Counter64
		MAX-ACCESS		read-only
		STATUS			current
		DESCRIPTION		"Column Description"
		::=  {  nptCesServiceIfTotalEntry  32  }


	nptCesServiceIfTotalRxPsnRecClkPMSMEvents	OBJECT-TYPE	
		SYNTAX			Counter64
		MAX-ACCESS		read-only
		STATUS			current
		DESCRIPTION		"Column Description"
		::=  {  nptCesServiceIfTotalEntry  33  }


	nptCesServiceIfTotalRxPsnRecClkHoldoverTime	OBJECT-TYPE	
		SYNTAX			Counter64
		MAX-ACCESS		read-only
		STATUS			current
		DESCRIPTION		"Column Description"
		::=  {  nptCesServiceIfTotalEntry  34  }


	nptCesServiceIfTotalLdpInNotificationStatus0x24	OBJECT-TYPE	
		SYNTAX			Counter64
		MAX-ACCESS		read-only
		STATUS			current
		DESCRIPTION		"Column Description"
		::=  {  nptCesServiceIfTotalEntry  35  }


	nptCesServiceIfTotalLdpInNotificationStatus0x26	OBJECT-TYPE	
		SYNTAX			Counter64
		MAX-ACCESS		read-only
		STATUS			current
		DESCRIPTION		"Column Description"
		::=  {  nptCesServiceIfTotalEntry  36  }


	nptCesServiceIfTotalLdpInNotificationStatus0x27	OBJECT-TYPE	
		SYNTAX			Counter64
		MAX-ACCESS		read-only
		STATUS			current
		DESCRIPTION		"Column Description"
		::=  {  nptCesServiceIfTotalEntry  37  }


	nptCesServiceIfTotalLdpInNotificationStatus0x2A	OBJECT-TYPE	
		SYNTAX			Counter64
		MAX-ACCESS		read-only
		STATUS			current
		DESCRIPTION		"Column Description"
		::=  {  nptCesServiceIfTotalEntry  38  }


	nptCesServiceIfTotalRxPsnDeniedPkts	OBJECT-TYPE	
		SYNTAX			Counter64
		MAX-ACCESS		read-only
		STATUS			current
		DESCRIPTION		"Column Description"
		::=  {  nptCesServiceIfTotalEntry  39  }


	nptCesServiceIfTotalRxPsnGapsPkts	OBJECT-TYPE	
		SYNTAX			Counter64
		MAX-ACCESS		read-only
		STATUS			current
		DESCRIPTION		"Column Description"
		::=  {  nptCesServiceIfTotalEntry  40  }
		
		
	nptCesServiceIfTotalRxPsnPkts	OBJECT-TYPE	
		SYNTAX			Counter64
		MAX-ACCESS		read-only
		STATUS			current
		DESCRIPTION		"Column Description"
		::=  {  nptCesServiceIfTotalEntry  41  }


	nptCesServiceIfTotalRxDroppedMisorderedPkts	OBJECT-TYPE	
		SYNTAX			Counter64
		MAX-ACCESS		read-only
		STATUS			current
		DESCRIPTION		"Column Description"
		::=  {  nptCesServiceIfTotalEntry  42  }


	nptCesServiceIfTotalRxPsnUnderrunDiscardPkts	OBJECT-TYPE	
		SYNTAX			Counter64
		MAX-ACCESS		read-only
		STATUS			current
		DESCRIPTION		"Column Description"
		::=  {  nptCesServiceIfTotalEntry  43  }
        
        
	nptPtpPortCurrentTable	OBJECT-TYPE
		SYNTAX		SEQUENCE  OF  NptPtpPortCurrentEntry
		MAX-ACCESS	not-accessible
		STATUS		current
		DESCRIPTION	"The PtpPort current table contains various statistics
            being collected for the current 15 minute
            interval."
		::=  { nptPtpPortIfGroup  1 }

	nptPtpPortCurrentEntry	OBJECT-TYPE
		SYNTAX		NptPtpPortCurrentEntry
		MAX-ACCESS	not-accessible
		STATUS		current
		DESCRIPTION	"An entry in the PtpPort Current table."
		INDEX		{  nptPtpPortCurrentIndex  }
		::=  { nptPtpPortCurrentTable 1 }

	NptPtpPortCurrentEntry  ::=  SEQUENCE {
		nptPtpPortCurrentIndex  Integer32,
		nptPtpPortCurrentMoDescription  DisplayString,
		nptPtpPortCurrentPktunirx  Counter64,
		nptPtpPortCurrentPktunimax  Counter64,
		nptPtpPortCurrentPktunimin  Counter64,
		nptPtpPortCurrentPktuniavg  Counter64,
		nptPtpPortCurrentPktmultirx  Counter64,
		nptPtpPortCurrentPktmultimax  Counter64,
		nptPtpPortCurrentPktmultimin  Counter64,
		nptPtpPortCurrentPktmultiavg  Counter64
		}


	nptPtpPortCurrentIndex	OBJECT-TYPE	
		SYNTAX			Integer32  ( -2147483648 .. 2147483647  ) 
		MAX-ACCESS		read-only
		STATUS			current
		DESCRIPTION		"The index value which uniquely identifies  the
            PtpPort interface to which this entry is applicable."
		::=  {  nptPtpPortCurrentEntry  1  }
		
	nptPtpPortCurrentMoDescription	OBJECT-TYPE	
		SYNTAX			DisplayString 
		MAX-ACCESS		read-only
		STATUS			current
		DESCRIPTION		"Mo Description"
		::=  {  nptPtpPortCurrentEntry  2  }


	nptPtpPortCurrentPktunirx	OBJECT-TYPE	
		SYNTAX			Counter64
		MAX-ACCESS		read-only
		STATUS			current
		DESCRIPTION		"# of Ucast pkt received in 1min."
		::=  {  nptPtpPortCurrentEntry  3  }


	nptPtpPortCurrentPktunimax	OBJECT-TYPE	
		SYNTAX			Counter64
		MAX-ACCESS		read-only
		STATUS			current
		DESCRIPTION		"Maximum # of Ucast received in 1min."
		::=  {  nptPtpPortCurrentEntry  4  }


	nptPtpPortCurrentPktunimin	OBJECT-TYPE	
		SYNTAX			Counter64
		MAX-ACCESS		read-only
		STATUS			current
		DESCRIPTION		"Minimum # of Ucast received in 1min."
		::=  {  nptPtpPortCurrentEntry  5  }


	nptPtpPortCurrentPktuniavg	OBJECT-TYPE	
		SYNTAX			Counter64
		MAX-ACCESS		read-only
		STATUS			current
		DESCRIPTION		"Average # of Ucast received in 1min."
		::=  {  nptPtpPortCurrentEntry  6  }


	nptPtpPortCurrentPktmultirx	OBJECT-TYPE	
		SYNTAX			Counter64
		MAX-ACCESS		read-only
		STATUS			current
		DESCRIPTION		"# of Mcast pkt received in 1min."
		::=  {  nptPtpPortCurrentEntry  7  }


	nptPtpPortCurrentPktmultimax	OBJECT-TYPE	
		SYNTAX			Counter64
		MAX-ACCESS		read-only
		STATUS			current
		DESCRIPTION		"Maximum # of Mcast received in 1min."
		::=  {  nptPtpPortCurrentEntry  8  }


	nptPtpPortCurrentPktmultimin	OBJECT-TYPE	
		SYNTAX			Counter64
		MAX-ACCESS		read-only
		STATUS			current
		DESCRIPTION		"Minimum # of Mcast received in 1min."
		::=  {  nptPtpPortCurrentEntry  9  }


	nptPtpPortCurrentPktmultiavg	OBJECT-TYPE	
		SYNTAX			Counter64
		MAX-ACCESS		read-only
		STATUS			current
		DESCRIPTION		"Average # of Mcast received in 1min."
		::=  {  nptPtpPortCurrentEntry  10  }
		
		
		
	nptPtpPortTotalTable	OBJECT-TYPE
		SYNTAX		SEQUENCE  OF  NptPtpPortTotalEntry
		MAX-ACCESS	not-accessible
		STATUS		current
		DESCRIPTION	"The PtpPort current table contains various statistics
            being collected for the current 15 minute
            interval."
		::=  { nptPtpPortIfGroup  2 }

	nptPtpPortTotalEntry	OBJECT-TYPE
		SYNTAX		NptPtpPortTotalEntry
		MAX-ACCESS	not-accessible
		STATUS		current
		DESCRIPTION	"An entry in the PtpPort Total table."
		INDEX		{  nptPtpPortTotalIndex  }
		::=  { nptPtpPortTotalTable 1 }

	NptPtpPortTotalEntry  ::=  SEQUENCE {
		nptPtpPortTotalIndex  Integer32,
		nptPtpPortTotalMoDescription  DisplayString,
		nptPtpPortTotalPktunirx  Counter64,
		nptPtpPortTotalPktunimax  Counter64,
		nptPtpPortTotalPktunimin  Counter64,
		nptPtpPortTotalPktuniavg  Counter64,
		nptPtpPortTotalPktmultirx  Counter64,
		nptPtpPortTotalPktmultimax  Counter64,
		nptPtpPortTotalPktmultimin  Counter64,
		nptPtpPortTotalPktmultiavg  Counter64
		}


	nptPtpPortTotalIndex	OBJECT-TYPE	
		SYNTAX			Integer32  ( -2147483648 .. 2147483647  ) 
		MAX-ACCESS		read-only
		STATUS			current
		DESCRIPTION		"The index value which uniquely identifies  the
            PtpPort interface to which this entry is applicable."
		::=  {  nptPtpPortTotalEntry  1  }
		
	nptPtpPortTotalMoDescription	OBJECT-TYPE	
		SYNTAX			DisplayString 
		MAX-ACCESS		read-only
		STATUS			current
		DESCRIPTION		"Mo Description"
		::=  {  nptPtpPortTotalEntry  2  }


	nptPtpPortTotalPktunirx	OBJECT-TYPE	
		SYNTAX			Counter64
		MAX-ACCESS		read-only
		STATUS			current
		DESCRIPTION		"# of Ucast pkt received in 1min."
		::=  {  nptPtpPortTotalEntry  3  }


	nptPtpPortTotalPktunimax	OBJECT-TYPE	
		SYNTAX			Counter64
		MAX-ACCESS		read-only
		STATUS			current
		DESCRIPTION		"Maximum # of Ucast received in 1min."
		::=  {  nptPtpPortTotalEntry  4  }


	nptPtpPortTotalPktunimin	OBJECT-TYPE	
		SYNTAX			Counter64
		MAX-ACCESS		read-only
		STATUS			current
		DESCRIPTION		"Minimum # of Ucast received in 1min."
		::=  {  nptPtpPortTotalEntry  5  }


	nptPtpPortTotalPktuniavg	OBJECT-TYPE	
		SYNTAX			Counter64
		MAX-ACCESS		read-only
		STATUS			current
		DESCRIPTION		"Average # of Ucast received in 1min."
		::=  {  nptPtpPortTotalEntry  6  }


	nptPtpPortTotalPktmultirx	OBJECT-TYPE	
		SYNTAX			Counter64
		MAX-ACCESS		read-only
		STATUS			current
		DESCRIPTION		"# of Mcast pkt received in 1min."
		::=  {  nptPtpPortTotalEntry  7  }


	nptPtpPortTotalPktmultimax	OBJECT-TYPE	
		SYNTAX			Counter64
		MAX-ACCESS		read-only
		STATUS			current
		DESCRIPTION		"Maximum # of Mcast received in 1min."
		::=  {  nptPtpPortTotalEntry  8  }


	nptPtpPortTotalPktmultimin	OBJECT-TYPE	
		SYNTAX			Counter64
		MAX-ACCESS		read-only
		STATUS			current
		DESCRIPTION		"Minimum # of Mcast received in 1min."
		::=  {  nptPtpPortTotalEntry  9  }


	nptPtpPortTotalPktmultiavg	OBJECT-TYPE	
		SYNTAX			Counter64
		MAX-ACCESS		read-only
		STATUS			current
		DESCRIPTION		"Average # of Mcast received in 1min."
		::=  {  nptPtpPortTotalEntry  10  }
		
		
		nptPtpSlaveCurrentTable	OBJECT-TYPE
		SYNTAX		SEQUENCE  OF  NptPtpSlaveCurrentEntry
		MAX-ACCESS	not-accessible
		STATUS		current
		DESCRIPTION	"The PtpSlave current table contains various statistics
            being collected for the current 15 minute
            interval."
		::=  { nptPtpSlaveIfGroup  1 }

	nptPtpSlaveCurrentEntry	OBJECT-TYPE
		SYNTAX		NptPtpSlaveCurrentEntry
		MAX-ACCESS	not-accessible
		STATUS		current
		DESCRIPTION	"An entry in the PtpSlave Current table."
		INDEX		{  nptPtpSlaveCurrentIndex  }
		::=  { nptPtpSlaveCurrentTable 1 }

	NptPtpSlaveCurrentEntry  ::=  SEQUENCE {
		nptPtpSlaveCurrentIndex  Integer32,
		nptPtpSlaveCurrentMoDescription  DisplayString,
		nptPtpSlaveCurrentpdvmin  Integer32,
		nptPtpSlaveCurrentpdvmax Integer32,
		nptPtpSlaveCurrentpdvavg  Integer32,
		nptPtpSlaveCurrenttdmin  Integer32,
		nptPtpSlaveCurrenttdmax  Integer32,
		nptPtpSlaveCurrenttdavg  Integer32,
		nptPtpSlaveCurrenttumin  Integer32,
		nptPtpSlaveCurrenttumax  Integer32,
		nptPtpSlaveCurrenttuavg  Integer32,
		nptPtpSlaveCurrentffoff1ppsmax  Integer32,
		nptPtpSlaveCurrentffoff10Mmax  Integer32
		}


	nptPtpSlaveCurrentIndex	OBJECT-TYPE	
		SYNTAX			Integer32  ( -2147483648 .. 2147483647  ) 
		MAX-ACCESS		read-only
		STATUS			current
		DESCRIPTION		"The index value which uniquely identifies  the
            PtpSlave interface to which this entry is applicable."
		::=  {  nptPtpSlaveCurrentEntry  1  }
		
	nptPtpSlaveCurrentMoDescription	OBJECT-TYPE	
		SYNTAX			DisplayString 
		MAX-ACCESS		read-only
		STATUS			current
		DESCRIPTION		"Mo Description"
		::=  {  nptPtpSlaveCurrentEntry  2  }


	nptPtpSlaveCurrentpdvmin	OBJECT-TYPE	
		SYNTAX			Integer32
		MAX-ACCESS		read-only
		STATUS			current
		DESCRIPTION		"Minimum PDV in usec."
		::=  {  nptPtpSlaveCurrentEntry  3  }


	nptPtpSlaveCurrentpdvmax	OBJECT-TYPE	
		SYNTAX			Integer32
		MAX-ACCESS		read-only
		STATUS			current
		DESCRIPTION		"Maximum PDV in usec."
		::=  {  nptPtpSlaveCurrentEntry  4  }


	nptPtpSlaveCurrentpdvavg	OBJECT-TYPE	
		SYNTAX			Integer32
		MAX-ACCESS		read-only
		STATUS			current
		DESCRIPTION		"Accumulation of all max PDV in each minute."
		::=  {  nptPtpSlaveCurrentEntry  5  }


	nptPtpSlaveCurrenttdmin	OBJECT-TYPE	
		SYNTAX			Integer32
		MAX-ACCESS		read-only
		STATUS			current
		DESCRIPTION		"Minimum measured round trip delay."
		::=  {  nptPtpSlaveCurrentEntry  6  }


	nptPtpSlaveCurrenttdmax	OBJECT-TYPE	
		SYNTAX			Integer32
		MAX-ACCESS		read-only
		STATUS			current
		DESCRIPTION		"Maximum measured round trip delay."
		::=  {  nptPtpSlaveCurrentEntry  7  }


	nptPtpSlaveCurrenttdavg	OBJECT-TYPE	
		SYNTAX			Integer32
		MAX-ACCESS		read-only
		STATUS			current
		DESCRIPTION		"Accumulation of all min RTD in each minute."
		::=  {  nptPtpSlaveCurrentEntry  8  }


	nptPtpSlaveCurrenttumin	OBJECT-TYPE	
		SYNTAX			Integer32
		MAX-ACCESS		read-only
		STATUS			current
		DESCRIPTION		"Minimum RTD uncertainty in nsec."
		::=  {  nptPtpSlaveCurrentEntry  9  }


	nptPtpSlaveCurrenttumax	OBJECT-TYPE	
		SYNTAX			Integer32
		MAX-ACCESS		read-only
		STATUS			current
		DESCRIPTION		"Maximum RTD uncertainty in nsec."
		::=  {  nptPtpSlaveCurrentEntry  10  }
		
		
	nptPtpSlaveCurrenttuavg	OBJECT-TYPE	
		SYNTAX			Integer32
		MAX-ACCESS		read-only
		STATUS			current
		DESCRIPTION		"Accumulation of all max RTDU in each minute."
		::=  {  nptPtpSlaveCurrentEntry  11  }
		
		
	nptPtpSlaveCurrentffoff1ppsmax	OBJECT-TYPE	
		SYNTAX			Integer32
		MAX-ACCESS		read-only
		STATUS			current
		DESCRIPTION		"Maximal measured FFOFF."
		::=  {  nptPtpSlaveCurrentEntry  12  }
		
		
		
	nptPtpSlaveCurrentffoff10Mmax	OBJECT-TYPE	
		SYNTAX			Integer32
		MAX-ACCESS		read-only
		STATUS			current
		DESCRIPTION		"Maximal measured FFOFF."
		::=  {  nptPtpSlaveCurrentEntry  13  }
		
		
		nptPtpSlaveTotalTable	OBJECT-TYPE
		SYNTAX		SEQUENCE  OF  NptPtpSlaveTotalEntry
		MAX-ACCESS	not-accessible
		STATUS		current
		DESCRIPTION	"The PtpSlave current table contains various statistics
            being collected for the current 15 minute
            interval."
		::=  { nptPtpSlaveIfGroup  2 }

	nptPtpSlaveTotalEntry	OBJECT-TYPE
		SYNTAX		NptPtpSlaveTotalEntry
		MAX-ACCESS	not-accessible
		STATUS		current
		DESCRIPTION	"An entry in the PtpSlave Total table."
		INDEX		{  nptPtpSlaveTotalIndex  }
		::=  { nptPtpSlaveTotalTable 1 }

	NptPtpSlaveTotalEntry  ::=  SEQUENCE {
		nptPtpSlaveTotalIndex  Integer32,
		nptPtpSlaveTotalMoDescription  DisplayString,
		nptPtpSlaveTotalpdvmin  Integer32,
		nptPtpSlaveTotalpdvmax Integer32,
		nptPtpSlaveTotalpdvavg  Integer32,
		nptPtpSlaveTotaltdmin  Integer32,
		nptPtpSlaveTotaltdmax  Integer32,
		nptPtpSlaveTotaltdavg  Integer32,
		nptPtpSlaveTotaltumin  Integer32,
		nptPtpSlaveTotaltumax  Integer32,
		nptPtpSlaveTotaltuavg  Integer32,
		nptPtpSlaveTotalffoff1ppsmax  Integer32,
		nptPtpSlaveTotalffoff10Mmax  Integer32
		}


	nptPtpSlaveTotalIndex	OBJECT-TYPE	
		SYNTAX			Integer32  ( -2147483648 .. 2147483647  ) 
		MAX-ACCESS		read-only
		STATUS			current
		DESCRIPTION		"The index value which uniquely identifies  the
            PtpSlave interface to which this entry is applicable."
		::=  {  nptPtpSlaveTotalEntry  1  }
		
	nptPtpSlaveTotalMoDescription	OBJECT-TYPE	
		SYNTAX			DisplayString 
		MAX-ACCESS		read-only
		STATUS			current
		DESCRIPTION		"Mo Description"
		::=  {  nptPtpSlaveTotalEntry  2  }


	nptPtpSlaveTotalpdvmin	OBJECT-TYPE	
		SYNTAX			Integer32
		MAX-ACCESS		read-only
		STATUS			current
		DESCRIPTION		"Minimum PDV in usec."
		::=  {  nptPtpSlaveTotalEntry  3  }


	nptPtpSlaveTotalpdvmax	OBJECT-TYPE	
		SYNTAX			Integer32
		MAX-ACCESS		read-only
		STATUS			current
		DESCRIPTION		"Maximum PDV in usec."
		::=  {  nptPtpSlaveTotalEntry  4  }


	nptPtpSlaveTotalpdvavg	OBJECT-TYPE	
		SYNTAX			Integer32
		MAX-ACCESS		read-only
		STATUS			current
		DESCRIPTION		"Accumulation of all max PDV in each minute."
		::=  {  nptPtpSlaveTotalEntry  5  }


	nptPtpSlaveTotaltdmin	OBJECT-TYPE	
		SYNTAX			Integer32
		MAX-ACCESS		read-only
		STATUS			current
		DESCRIPTION		"Minimum measured round trip delay."
		::=  {  nptPtpSlaveTotalEntry  6  }


	nptPtpSlaveTotaltdmax	OBJECT-TYPE	
		SYNTAX			Integer32
		MAX-ACCESS		read-only
		STATUS			current
		DESCRIPTION		"Maximum measured round trip delay."
		::=  {  nptPtpSlaveTotalEntry  7  }


	nptPtpSlaveTotaltdavg	OBJECT-TYPE	
		SYNTAX			Integer32
		MAX-ACCESS		read-only
		STATUS			current
		DESCRIPTION		"Accumulation of all min RTD in each minute."
		::=  {  nptPtpSlaveTotalEntry  8  }


	nptPtpSlaveTotaltumin	OBJECT-TYPE	
		SYNTAX			Integer32
		MAX-ACCESS		read-only
		STATUS			current
		DESCRIPTION		"Minimum RTD uncertainty in nsec."
		::=  {  nptPtpSlaveTotalEntry  9  }


	nptPtpSlaveTotaltumax	OBJECT-TYPE	
		SYNTAX			Integer32
		MAX-ACCESS		read-only
		STATUS			current
		DESCRIPTION		"Maximum RTD uncertainty in nsec."
		::=  {  nptPtpSlaveTotalEntry  10  }
		
		
	nptPtpSlaveTotaltuavg	OBJECT-TYPE	
		SYNTAX			Integer32
		MAX-ACCESS		read-only
		STATUS			current
		DESCRIPTION		"Accumulation of all max RTDU in each minute."
		::=  {  nptPtpSlaveTotalEntry  11  }
		
		
	nptPtpSlaveTotalffoff1ppsmax	OBJECT-TYPE	
		SYNTAX			Integer32
		MAX-ACCESS		read-only
		STATUS			current
		DESCRIPTION		"Maximal measured FFOFF."
		::=  {  nptPtpSlaveTotalEntry  12  }
		
		
		
	nptPtpSlaveTotalffoff10Mmax	OBJECT-TYPE	
		SYNTAX			Integer32
		MAX-ACCESS		read-only
		STATUS			current
		DESCRIPTION		"Maximal measured FFOFF."
		::=  {  nptPtpSlaveTotalEntry  13  }


		nptPtpSlavetimeCurrentTable	OBJECT-TYPE
		SYNTAX		SEQUENCE  OF  NptPtpSlavetimeCurrentEntry
		MAX-ACCESS	not-accessible
		STATUS		current
		DESCRIPTION	"The PtpSlavetime current table contains various statistics
            being collected for the current 15 minute
            interval."
		::=  { nptPtpSlavetimeIfGroup  1 }

	nptPtpSlavetimeCurrentEntry	OBJECT-TYPE
		SYNTAX		NptPtpSlavetimeCurrentEntry
		MAX-ACCESS	not-accessible
		STATUS		current
		DESCRIPTION	"An entry in the PtpSlavetime Current table."
		INDEX		{  nptPtpSlavetimeCurrentIndex  }
		::=  { nptPtpSlavetimeCurrentTable 1 }

	NptPtpSlavetimeCurrentEntry  ::=  SEQUENCE {
		nptPtpSlavetimeCurrentIndex  Integer32,
		nptPtpSlavetimeCurrentMoDescription  DisplayString,
		nptPtpSlavetimeCurrentMaxOffestFromMaster  DisplayString,
		nptPtpSlavetimeCurrentMinOffestFromMaster DisplayString,
		nptPtpSlavetimeCurrentAverageOffestFromMaster  DisplayString,
		nptPtpSlavetimeCurrentCUROffestFromMaster  DisplayString,
		nptPtpSlavetimeCurrentACCUMOffestFromMaster  DisplayString,
        nptPtpSlavetimeCurrentMaximumTimeOffset  DisplayString,
        nptPtpSlavetimeCurrentMinimumTimeOffset  DisplayString,
        nptPtpSlavetimeCurrentAverageTimeOffset  DisplayString,
        nptPtpSlavetimeCurrentCurrentTimeOffset  DisplayString,
		nptPtpSlavetimeCurrentMaxMastertoSlaveDelay  DisplayString,
		nptPtpSlavetimeCurrentMinMastertoSlaveDelay  DisplayString,
		nptPtpSlavetimeCurrentAverageMastertoSlaveDelay  DisplayString,
		nptPtpSlavetimeCurrentCURMastertoSlaveDelay  DisplayString,
		nptPtpSlavetimeCurrentMaxSlavetoMasterDelay  DisplayString,
		nptPtpSlavetimeCurrentMinSlavetoMasterDelay  DisplayString,
        nptPtpSlavetimeCurrentAverageSlavetoMasterDelay  DisplayString,
       	nptPtpSlavetimeCurrentCURSlavetoMasterDelay  DisplayString,
		nptPtpSlavetimeCurrentMaxMeanPathDelay  DisplayString,
		nptPtpSlavetimeCurrentMinMeanPathDelay  DisplayString,
        nptPtpSlavetimeCurrentAverageMeanPathDelay  DisplayString,
        nptPtpSlavetimeCurrentCURMeanPathDelay  DisplayString,
		nptPtpSlavetimeCurrentMaxPassiveTimeOffset  DisplayString,
		nptPtpSlavetimeCurrentMinPassiveTimeOffset  DisplayString,
        nptPtpSlavetimeCurrentAveragePassiveTimeOffset  DisplayString,
        nptPtpSlavetimeCurrentCURPassiveTimeOffset  DisplayString
		}


	nptPtpSlavetimeCurrentIndex	OBJECT-TYPE	
		SYNTAX			Integer32  ( -2147483648 .. 2147483647  ) 
		MAX-ACCESS		read-only
		STATUS			current
		DESCRIPTION		"The index value which uniquely identifies  the
            PtpSlavetime interface to which this entry is applicable."
		::=  {  nptPtpSlavetimeCurrentEntry  1  }
		
	nptPtpSlavetimeCurrentMoDescription	OBJECT-TYPE	
		SYNTAX			DisplayString 
		MAX-ACCESS		read-only
		STATUS			current
		DESCRIPTION		"Mo Description"
		::=  {  nptPtpSlavetimeCurrentEntry  2  }


	nptPtpSlavetimeCurrentMaxOffestFromMaster	OBJECT-TYPE	
		SYNTAX			DisplayString
		MAX-ACCESS		read-only
		STATUS			current
		DESCRIPTION		"Maximum Offset From Master"
		::=  {  nptPtpSlavetimeCurrentEntry  3  }


	nptPtpSlavetimeCurrentMinOffestFromMaster	OBJECT-TYPE	
		SYNTAX			DisplayString
		MAX-ACCESS		read-only
		STATUS			current
		DESCRIPTION		"Minimum Offset From Master"
		::=  {  nptPtpSlavetimeCurrentEntry  4  }


	nptPtpSlavetimeCurrentAverageOffestFromMaster	OBJECT-TYPE	
		SYNTAX			DisplayString
		MAX-ACCESS		read-only
		STATUS			current
		DESCRIPTION		"Average Offset From Master"
		::=  {  nptPtpSlavetimeCurrentEntry  5  }


	nptPtpSlavetimeCurrentCUROffestFromMaster	OBJECT-TYPE	
		SYNTAX			DisplayString
		MAX-ACCESS		read-only
		STATUS			current
		DESCRIPTION		"Current Offset From Master"
		::=  {  nptPtpSlavetimeCurrentEntry  6  }


	nptPtpSlavetimeCurrentACCUMOffestFromMaster	OBJECT-TYPE	
		SYNTAX			DisplayString
		MAX-ACCESS		read-only
		STATUS			current
		DESCRIPTION		"Accumulated Offset from Master"
		::=  {  nptPtpSlavetimeCurrentEntry  7  }


	nptPtpSlavetimeCurrentMaximumTimeOffset	OBJECT-TYPE	
		SYNTAX			DisplayString
		MAX-ACCESS		read-only
		STATUS			current
		DESCRIPTION		"Maximum Time Offset"
		::=  {  nptPtpSlavetimeCurrentEntry  8  }


	nptPtpSlavetimeCurrentMinimumTimeOffset	OBJECT-TYPE	
		SYNTAX			DisplayString
		MAX-ACCESS		read-only
		STATUS			current
		DESCRIPTION		"Minimum Time Offset"
		::=  {  nptPtpSlavetimeCurrentEntry  9  }


	nptPtpSlavetimeCurrentAverageTimeOffset	OBJECT-TYPE	
		SYNTAX			DisplayString
		MAX-ACCESS		read-only
		STATUS			current
		DESCRIPTION		"Average Time Offset"
		::=  {  nptPtpSlavetimeCurrentEntry  10  }


	nptPtpSlavetimeCurrentCurrentTimeOffset	OBJECT-TYPE	
		SYNTAX			DisplayString
		MAX-ACCESS		read-only
		STATUS			current
		DESCRIPTION		"Current Time Offset"
		::=  {  nptPtpSlavetimeCurrentEntry  11  }


	nptPtpSlavetimeCurrentMaxMastertoSlaveDelay	OBJECT-TYPE	
		SYNTAX			DisplayString
		MAX-ACCESS		read-only
		STATUS			current
		DESCRIPTION		"Maximum Master to Slave Delay"
		::=  {  nptPtpSlavetimeCurrentEntry  12  }


	nptPtpSlavetimeCurrentMinMastertoSlaveDelay	OBJECT-TYPE	
		SYNTAX			DisplayString
		MAX-ACCESS		read-only
		STATUS			current
		DESCRIPTION		"Minimum Master to Slave Delay"
		::=  {  nptPtpSlavetimeCurrentEntry  13  }


	nptPtpSlavetimeCurrentAverageMastertoSlaveDelay	OBJECT-TYPE	
		SYNTAX			DisplayString
		MAX-ACCESS		read-only
		STATUS			current
		DESCRIPTION		"Average Master to Slave Delay"
		::=  {  nptPtpSlavetimeCurrentEntry  14  }
		
		
	nptPtpSlavetimeCurrentCURMastertoSlaveDelay	OBJECT-TYPE	
		SYNTAX			DisplayString
		MAX-ACCESS		read-only
		STATUS			current
		DESCRIPTION		"Current Master to Slave Delay"
		::=  {  nptPtpSlavetimeCurrentEntry  15  }
		
		
	nptPtpSlavetimeCurrentMaxSlavetoMasterDelay	OBJECT-TYPE	
		SYNTAX			DisplayString
		MAX-ACCESS		read-only
		STATUS			current
		DESCRIPTION		"Maximum Slave to Master Delay"
		::=  {  nptPtpSlavetimeCurrentEntry  16  }
		
		
		
	nptPtpSlavetimeCurrentMinSlavetoMasterDelay	OBJECT-TYPE	
		SYNTAX			DisplayString
		MAX-ACCESS		read-only
		STATUS			current
		DESCRIPTION		"Minimum Slave to Master Delay"
		::=  {  nptPtpSlavetimeCurrentEntry  17  }
		
        
	nptPtpSlavetimeCurrentAverageSlavetoMasterDelay	OBJECT-TYPE	
		SYNTAX			DisplayString
		MAX-ACCESS		read-only
		STATUS			current
		DESCRIPTION		"Average Slave to Master Delay"
		::=  {  nptPtpSlavetimeCurrentEntry  18  }
		
		
	nptPtpSlavetimeCurrentCURSlavetoMasterDelay	OBJECT-TYPE	
		SYNTAX			DisplayString
		MAX-ACCESS		read-only
		STATUS			current
		DESCRIPTION		"Current Slave to Master Delay"
		::=  {  nptPtpSlavetimeCurrentEntry  19  }
		
		
	nptPtpSlavetimeCurrentMaxMeanPathDelay	OBJECT-TYPE	
		SYNTAX			DisplayString
		MAX-ACCESS		read-only
		STATUS			current
		DESCRIPTION		"Maximum Mean Path Delay"
		::=  {  nptPtpSlavetimeCurrentEntry  20  }
		
		
		
	nptPtpSlavetimeCurrentMinMeanPathDelay	OBJECT-TYPE	
		SYNTAX			DisplayString
		MAX-ACCESS		read-only
		STATUS			current
		DESCRIPTION		"Minimum Mean Path Delay"
		::=  {  nptPtpSlavetimeCurrentEntry  21  }
        
		
	nptPtpSlavetimeCurrentAverageMeanPathDelay	OBJECT-TYPE	
		SYNTAX			DisplayString
		MAX-ACCESS		read-only
		STATUS			current
		DESCRIPTION		"Average Mean Path Delay"
		::=  {  nptPtpSlavetimeCurrentEntry  22  }
		
		
	nptPtpSlavetimeCurrentCURMeanPathDelay	OBJECT-TYPE	
		SYNTAX			DisplayString
		MAX-ACCESS		read-only
		STATUS			current
		DESCRIPTION		"Current Mean Path Delay"
		::=  {  nptPtpSlavetimeCurrentEntry  23  }
		
		
	nptPtpSlavetimeCurrentMaxPassiveTimeOffset	OBJECT-TYPE	
		SYNTAX			DisplayString
		MAX-ACCESS		read-only
		STATUS			current
		DESCRIPTION		"Maximum Passive Time Offset"
		::=  {  nptPtpSlavetimeCurrentEntry  24  }
		
		
		
	nptPtpSlavetimeCurrentMinPassiveTimeOffset	OBJECT-TYPE	
		SYNTAX			DisplayString
		MAX-ACCESS		read-only
		STATUS			current
		DESCRIPTION		"Minimum Passive Time Offset"
		::=  {  nptPtpSlavetimeCurrentEntry  25  }
        
        
	nptPtpSlavetimeCurrentAveragePassiveTimeOffset	OBJECT-TYPE	
		SYNTAX			DisplayString
		MAX-ACCESS		read-only
		STATUS			current
		DESCRIPTION		"Average Passive Time Offset"
		::=  {  nptPtpSlavetimeCurrentEntry  26  }
		
		
	nptPtpSlavetimeCurrentCURPassiveTimeOffset	OBJECT-TYPE	
		SYNTAX			DisplayString
		MAX-ACCESS		read-only
		STATUS			current
		DESCRIPTION		"Current Passive Time Offset"
		::=  {  nptPtpSlavetimeCurrentEntry  27  }
		
        
        
		nptPtpSlavetimeTotalTable	OBJECT-TYPE
		SYNTAX		SEQUENCE  OF  NptPtpSlavetimeTotalEntry
		MAX-ACCESS	not-accessible
		STATUS		current
		DESCRIPTION	"The PtpSlavetime current table contains various statistics
            being collected for the current 15 minute
            interval."
		::=  { nptPtpSlavetimeIfGroup  2 }

	nptPtpSlavetimeTotalEntry	OBJECT-TYPE
		SYNTAX		NptPtpSlavetimeTotalEntry
		MAX-ACCESS	not-accessible
		STATUS		current
		DESCRIPTION	"An entry in the PtpSlavetime Total table."
		INDEX		{  nptPtpSlavetimeTotalIndex  }
		::=  { nptPtpSlavetimeTotalTable 1 }

	NptPtpSlavetimeTotalEntry  ::=  SEQUENCE {
		nptPtpSlavetimeTotalIndex  Integer32,
		nptPtpSlavetimeTotalMoDescription  DisplayString,
		nptPtpSlavetimeTotalMaxOffestFromMaster  DisplayString,
		nptPtpSlavetimeTotalMinOffestFromMaster DisplayString,
		nptPtpSlavetimeTotalAverageOffestFromMaster  DisplayString,
		nptPtpSlavetimeTotalCUROffestFromMaster  DisplayString,
		nptPtpSlavetimeTotalACCUMOffestFromMaster  DisplayString,
        nptPtpSlavetimeTotalMaximumTimeOffset  DisplayString,
        nptPtpSlavetimeTotalMinimumTimeOffset  DisplayString,
        nptPtpSlavetimeTotalAverageTimeOffset  DisplayString,
        nptPtpSlavetimeTotalCurrentTimeOffset  DisplayString,
		nptPtpSlavetimeTotalMaxMastertoSlaveDelay  DisplayString,
		nptPtpSlavetimeTotalMinMastertoSlaveDelay  DisplayString,
		nptPtpSlavetimeTotalAverageMastertoSlaveDelay  DisplayString,
		nptPtpSlavetimeTotalCURMastertoSlaveDelay  DisplayString,
		nptPtpSlavetimeTotalMaxSlavetoMasterDelay  DisplayString,
		nptPtpSlavetimeTotalMinSlavetoMasterDelay  DisplayString,
        nptPtpSlavetimeTotalAverageSlavetoMasterDelay  DisplayString,
        nptPtpSlavetimeTotalCURSlavetoMasterDelay  DisplayString,
		nptPtpSlavetimeTotalMaxMeanPathDelay  DisplayString,
		nptPtpSlavetimeTotalMinMeanPathDelay  DisplayString,
        nptPtpSlavetimeTotalAverageMeanPathDelay  DisplayString,
        nptPtpSlavetimeTotalCURMeanPathDelay  DisplayString,
		nptPtpSlavetimeTotalMaxPassiveTimeOffset  DisplayString,
		nptPtpSlavetimeTotalMinPassiveTimeOffset  DisplayString,
        nptPtpSlavetimeTotalAveragePassiveTimeOffset  DisplayString,
        nptPtpSlavetimeTotalCURPassiveTimeOffset  DisplayString
		}


	nptPtpSlavetimeTotalIndex	OBJECT-TYPE	
		SYNTAX			Integer32  ( -2147483648 .. 2147483647  ) 
		MAX-ACCESS		read-only
		STATUS			current
		DESCRIPTION		"The index value which uniquely identifies  the
            PtpSlavetime interface to which this entry is applicable."
		::=  {  nptPtpSlavetimeTotalEntry  1  }
		
	nptPtpSlavetimeTotalMoDescription	OBJECT-TYPE	
		SYNTAX			DisplayString 
		MAX-ACCESS		read-only
		STATUS			current
		DESCRIPTION		"Mo Description"
		::=  {  nptPtpSlavetimeTotalEntry  2  }


	nptPtpSlavetimeTotalMaxOffestFromMaster	OBJECT-TYPE	
		SYNTAX			DisplayString
		MAX-ACCESS		read-only
		STATUS			current
		DESCRIPTION		"Maximum Offset From Master"
		::=  {  nptPtpSlavetimeTotalEntry  3  }


	nptPtpSlavetimeTotalMinOffestFromMaster	OBJECT-TYPE	
		SYNTAX			DisplayString
		MAX-ACCESS		read-only
		STATUS			current
		DESCRIPTION		"Minimum Offset From Master"
		::=  {  nptPtpSlavetimeTotalEntry  4  }


	nptPtpSlavetimeTotalAverageOffestFromMaster	OBJECT-TYPE	
		SYNTAX			DisplayString
		MAX-ACCESS		read-only
		STATUS			current
		DESCRIPTION		"Average Offset From Master"
		::=  {  nptPtpSlavetimeTotalEntry  5  }


	nptPtpSlavetimeTotalCUROffestFromMaster	OBJECT-TYPE	
		SYNTAX			DisplayString
		MAX-ACCESS		read-only
		STATUS			current
		DESCRIPTION		"Current Offset From Master"
		::=  {  nptPtpSlavetimeTotalEntry  6  }


	nptPtpSlavetimeTotalACCUMOffestFromMaster	OBJECT-TYPE	
		SYNTAX			DisplayString
		MAX-ACCESS		read-only
		STATUS			current
		DESCRIPTION		"Accumulated Offset from Master"
		::=  {  nptPtpSlavetimeTotalEntry  7  }


	nptPtpSlavetimeTotalMaximumTimeOffset	OBJECT-TYPE	
		SYNTAX			DisplayString
		MAX-ACCESS		read-only
		STATUS			current
		DESCRIPTION		"Maximum Time Offset"
		::=  {  nptPtpSlavetimeTotalEntry  8  }


	nptPtpSlavetimeTotalMinimumTimeOffset	OBJECT-TYPE	
		SYNTAX			DisplayString
		MAX-ACCESS		read-only
		STATUS			current
		DESCRIPTION		"Minimum Time Offset"
		::=  {  nptPtpSlavetimeTotalEntry  9  }


	nptPtpSlavetimeTotalAverageTimeOffset	OBJECT-TYPE	
		SYNTAX			DisplayString
		MAX-ACCESS		read-only
		STATUS			current
		DESCRIPTION		"Average Time Offset"
		::=  {  nptPtpSlavetimeTotalEntry  10  }


	nptPtpSlavetimeTotalCurrentTimeOffset	OBJECT-TYPE	
		SYNTAX			DisplayString
		MAX-ACCESS		read-only
		STATUS			current
		DESCRIPTION		"Current Time Offset"
		::=  {  nptPtpSlavetimeTotalEntry  11  }


	nptPtpSlavetimeTotalMaxMastertoSlaveDelay	OBJECT-TYPE	
		SYNTAX			DisplayString
		MAX-ACCESS		read-only
		STATUS			current
		DESCRIPTION		"Maximum Master to Slave Delay"
		::=  {  nptPtpSlavetimeTotalEntry  12  }


	nptPtpSlavetimeTotalMinMastertoSlaveDelay	OBJECT-TYPE	
		SYNTAX			DisplayString
		MAX-ACCESS		read-only
		STATUS			current
		DESCRIPTION		"Minimum Master to Slave Delay"
		::=  {  nptPtpSlavetimeTotalEntry  13  }


	nptPtpSlavetimeTotalAverageMastertoSlaveDelay	OBJECT-TYPE	
		SYNTAX			DisplayString
		MAX-ACCESS		read-only
		STATUS			current
		DESCRIPTION		"Average Master to Slave Delay"
		::=  {  nptPtpSlavetimeTotalEntry  14  }
		
		
	nptPtpSlavetimeTotalCURMastertoSlaveDelay	OBJECT-TYPE	
		SYNTAX			DisplayString
		MAX-ACCESS		read-only
		STATUS			current
		DESCRIPTION		"Current Master to Slave Delay"
		::=  {  nptPtpSlavetimeTotalEntry  15  }
		
		
	nptPtpSlavetimeTotalMaxSlavetoMasterDelay	OBJECT-TYPE	
		SYNTAX			DisplayString
		MAX-ACCESS		read-only
		STATUS			current
		DESCRIPTION		"Maximum Slave to Master Delay"
		::=  {  nptPtpSlavetimeTotalEntry  16  }
		
		
		
	nptPtpSlavetimeTotalMinSlavetoMasterDelay	OBJECT-TYPE	
		SYNTAX			DisplayString
		MAX-ACCESS		read-only
		STATUS			current
		DESCRIPTION		"Minimum Slave to Master Delay"
		::=  {  nptPtpSlavetimeTotalEntry  17  }
		
	nptPtpSlavetimeTotalAverageSlavetoMasterDelay	OBJECT-TYPE	
		SYNTAX			DisplayString
		MAX-ACCESS		read-only
		STATUS			current
		DESCRIPTION		"Average Slave to Master Delay"
		::=  {  nptPtpSlavetimeTotalEntry  18  }
		
		
	nptPtpSlavetimeTotalCURSlavetoMasterDelay	OBJECT-TYPE	
		SYNTAX			DisplayString
		MAX-ACCESS		read-only
		STATUS			current
		DESCRIPTION		"Current Slave to Master Delay"
		::=  {  nptPtpSlavetimeTotalEntry  19  }
		
		
	nptPtpSlavetimeTotalMaxMeanPathDelay	OBJECT-TYPE	
		SYNTAX			DisplayString
		MAX-ACCESS		read-only
		STATUS			current
		DESCRIPTION		"Maximum Mean Path Delay"
		::=  {  nptPtpSlavetimeTotalEntry  20  }
		
		
		
	nptPtpSlavetimeTotalMinMeanPathDelay	OBJECT-TYPE	
		SYNTAX			DisplayString
		MAX-ACCESS		read-only
		STATUS			current
		DESCRIPTION		"Minimum Mean Path Delay"
		::=  {  nptPtpSlavetimeTotalEntry  21  }
        
		
	nptPtpSlavetimeTotalAverageMeanPathDelay	OBJECT-TYPE	
		SYNTAX			DisplayString
		MAX-ACCESS		read-only
		STATUS			current
		DESCRIPTION		"Average Mean Path Delay"
		::=  {  nptPtpSlavetimeTotalEntry  22  }
		
		
	nptPtpSlavetimeTotalCURMeanPathDelay	OBJECT-TYPE	
		SYNTAX			DisplayString
		MAX-ACCESS		read-only
		STATUS			current
		DESCRIPTION		"Current Mean Path Delay"
		::=  {  nptPtpSlavetimeTotalEntry  23  }
		
		
	nptPtpSlavetimeTotalMaxPassiveTimeOffset	OBJECT-TYPE	
		SYNTAX			DisplayString
		MAX-ACCESS		read-only
		STATUS			current
		DESCRIPTION		"Maximum Passive Time Offset"
		::=  {  nptPtpSlavetimeTotalEntry  24  }
		
		
		
	nptPtpSlavetimeTotalMinPassiveTimeOffset	OBJECT-TYPE	
		SYNTAX			DisplayString
		MAX-ACCESS		read-only
		STATUS			current
		DESCRIPTION		"Minimum Passive Time Offset"
		::=  {  nptPtpSlavetimeTotalEntry  25  }
        
        
	nptPtpSlavetimeTotalAveragePassiveTimeOffset	OBJECT-TYPE	
		SYNTAX			DisplayString
		MAX-ACCESS		read-only
		STATUS			current
		DESCRIPTION		"Average Passive Time Offset"
		::=  {  nptPtpSlavetimeTotalEntry  26  }
		
		
	nptPtpSlavetimeTotalCURPassiveTimeOffset	OBJECT-TYPE	
		SYNTAX			DisplayString
		MAX-ACCESS		read-only
		STATUS			current
		DESCRIPTION		"Current Passive Time Offset"
		::=  {  nptPtpSlavetimeTotalEntry  27  }


		nptPtp1588PortCurrentTable	OBJECT-TYPE
		SYNTAX		SEQUENCE  OF  NptPtp1588PortCurrentEntry
		MAX-ACCESS	not-accessible
		STATUS		current
		DESCRIPTION	"The Ptp1588Port current table contains various statistics
            being collected for the current 15 minute
            interval."
		::=  { nptPtp1588PortIfGroup  1 }

	nptPtp1588PortCurrentEntry	OBJECT-TYPE
		SYNTAX		NptPtp1588PortCurrentEntry
		MAX-ACCESS	not-accessible
		STATUS		current
		DESCRIPTION	"An entry in the Ptp1588Port Current table."
		INDEX		{  nptPtp1588PortCurrentIndex  }
		::=  { nptPtp1588PortCurrentTable 1 }

	NptPtp1588PortCurrentEntry  ::=  SEQUENCE {
		nptPtp1588PortCurrentIndex  Integer32,
		nptPtp1588PortCurrentMoDescription  DisplayString,
		nptPtp1588PortCurrentTxAnnouncePkts  Integer32,
		nptPtp1588PortCurrentRxAnnouncePkts Integer32,
		nptPtp1588PortCurrentDroppedAnnouncePkts  Integer32,
		nptPtp1588PortCurrentLostAnnouncePkts  Integer32,
		nptPtp1588PortCurrentTxSyncPkts  Integer32,
		nptPtp1588PortCurrentRxSyncPkts  Integer32,
		nptPtp1588PortCurrentDroppedSyncPkts  Integer32,
		nptPtp1588PortCurrentLostSyncPkts  Integer32,
		nptPtp1588PortCurrentTxFollowUpPkts  Integer32,
		nptPtp1588PortCurrentRxFollowUpPkts  Integer32,
		nptPtp1588PortCurrentDroppedFollowUpPkts  Integer32,
        nptPtp1588PortCurrentLostFollowUpPkts  Integer32,
        nptPtp1588PortCurrentTxDelayReqPkts  Integer32,
		nptPtp1588PortCurrentRxDelayReqPkts  Integer32,
		nptPtp1588PortCurrentDroppedDelayReqPkts  Integer32,
        nptPtp1588PortCurrentLostDelayReqPkts  Integer32,
        nptPtp1588PortCurrentTxDelayRespPkts  Integer32,
		nptPtp1588PortCurrentRxDelayRespPkts  Integer32,
		nptPtp1588PortCurrentDroppedDelayRespPkts  Integer32,
        nptPtp1588PortCurrentLostDelayRespPkts  Integer32,
        nptPtp1588PortCurrentTxSignalPkts  Integer32,
		nptPtp1588PortCurrentRxSignalPkts  Integer32,
		nptPtp1588PortCurrentDroppedSignalPkts  Integer32,
        nptPtp1588PortCurrentLostSignalPkts  Integer32,
        nptPtp1588PortCurrentTxManagementPkts  Integer32,
		nptPtp1588PortCurrentRxManagementPkts  Integer32,
		nptPtp1588PortCurrentDroppedManagementPkts  Integer32,
        nptPtp1588PortCurrentLostManagementPkts  Integer32
		}


	nptPtp1588PortCurrentIndex	OBJECT-TYPE	
		SYNTAX			Integer32  ( -2147483648 .. 2147483647  ) 
		MAX-ACCESS		read-only
		STATUS			current
		DESCRIPTION		"The index value which uniquely identifies  the
            Ptp1588Port interface to which this entry is applicable."
		::=  {  nptPtp1588PortCurrentEntry  1  }
		
	nptPtp1588PortCurrentMoDescription	OBJECT-TYPE	
		SYNTAX			DisplayString 
		MAX-ACCESS		read-only
		STATUS			current
		DESCRIPTION		"Mo Description"
		::=  {  nptPtp1588PortCurrentEntry  2  }


	nptPtp1588PortCurrentTxAnnouncePkts	OBJECT-TYPE	
		SYNTAX			Integer32
		MAX-ACCESS		read-only
		STATUS			current
		DESCRIPTION		"Maximum Offset From Master"
		::=  {  nptPtp1588PortCurrentEntry  3  }


	nptPtp1588PortCurrentRxAnnouncePkts	OBJECT-TYPE	
		SYNTAX			Integer32
		MAX-ACCESS		read-only
		STATUS			current
		DESCRIPTION		"Minimum Offset From Master"
		::=  {  nptPtp1588PortCurrentEntry  4  }


	nptPtp1588PortCurrentDroppedAnnouncePkts	OBJECT-TYPE	
		SYNTAX			Integer32
		MAX-ACCESS		read-only
		STATUS			current
		DESCRIPTION		"Average Offset From Master"
		::=  {  nptPtp1588PortCurrentEntry  5  }


	nptPtp1588PortCurrentLostAnnouncePkts	OBJECT-TYPE	
		SYNTAX			Integer32
		MAX-ACCESS		read-only
		STATUS			current
		DESCRIPTION		"Current Offset From Master"
		::=  {  nptPtp1588PortCurrentEntry  6  }


	nptPtp1588PortCurrentTxSyncPkts	OBJECT-TYPE	
		SYNTAX			Integer32
		MAX-ACCESS		read-only
		STATUS			current
		DESCRIPTION		"Accumulated Offset from Master"
		::=  {  nptPtp1588PortCurrentEntry  7  }


	nptPtp1588PortCurrentRxSyncPkts	OBJECT-TYPE	
		SYNTAX			Integer32
		MAX-ACCESS		read-only
		STATUS			current
		DESCRIPTION		"Maximum Master to Slave Delay"
		::=  {  nptPtp1588PortCurrentEntry  8  }


	nptPtp1588PortCurrentDroppedSyncPkts	OBJECT-TYPE	
		SYNTAX			Integer32
		MAX-ACCESS		read-only
		STATUS			current
		DESCRIPTION		"Minimum Master to Slave Delay"
		::=  {  nptPtp1588PortCurrentEntry  9  }


	nptPtp1588PortCurrentLostSyncPkts	OBJECT-TYPE	
		SYNTAX			Integer32
		MAX-ACCESS		read-only
		STATUS			current
		DESCRIPTION		"Average Master to Slave Delay"
		::=  {  nptPtp1588PortCurrentEntry  10  }
		
		
	nptPtp1588PortCurrentTxFollowUpPkts	OBJECT-TYPE	
		SYNTAX			Integer32
		MAX-ACCESS		read-only
		STATUS			current
		DESCRIPTION		"Current Master to Slave Delay"
		::=  {  nptPtp1588PortCurrentEntry  11  }
		
		
	nptPtp1588PortCurrentRxFollowUpPkts	OBJECT-TYPE	
		SYNTAX			Integer32
		MAX-ACCESS		read-only
		STATUS			current
		DESCRIPTION		"Maximum Slave to Master Delay"
		::=  {  nptPtp1588PortCurrentEntry  12  }
		
		
		
	nptPtp1588PortCurrentDroppedFollowUpPkts	OBJECT-TYPE	
		SYNTAX			Integer32
		MAX-ACCESS		read-only
		STATUS			current
		DESCRIPTION		"Minimum Slave to Master Delay"
		::=  {  nptPtp1588PortCurrentEntry  13  }
		
	nptPtp1588PortCurrentLostFollowUpPkts	OBJECT-TYPE	
		SYNTAX			Integer32
		MAX-ACCESS		read-only
		STATUS			current
		DESCRIPTION		"Average Slave to Master Delay"
		::=  {  nptPtp1588PortCurrentEntry  14  }
		
		
	nptPtp1588PortCurrentTxDelayReqPkts	OBJECT-TYPE	
		SYNTAX			Integer32
		MAX-ACCESS		read-only
		STATUS			current
		DESCRIPTION		"Current Slave to Master Delay"
		::=  {  nptPtp1588PortCurrentEntry  15  }
		
		
	nptPtp1588PortCurrentRxDelayReqPkts	OBJECT-TYPE	
		SYNTAX			Integer32
		MAX-ACCESS		read-only
		STATUS			current
		DESCRIPTION		"Maximum Mean Path Delay"
		::=  {  nptPtp1588PortCurrentEntry  16  }
		
		
		
	nptPtp1588PortCurrentDroppedDelayReqPkts	OBJECT-TYPE	
		SYNTAX			Integer32
		MAX-ACCESS		read-only
		STATUS			current
		DESCRIPTION		"Minimum Mean Path Delay"
		::=  {  nptPtp1588PortCurrentEntry  17  }
        
		
	nptPtp1588PortCurrentLostDelayReqPkts	OBJECT-TYPE	
		SYNTAX			Integer32
		MAX-ACCESS		read-only
		STATUS			current
		DESCRIPTION		"Average Mean Path Delay"
		::=  {  nptPtp1588PortCurrentEntry  18  }
		
		
	nptPtp1588PortCurrentTxDelayRespPkts	OBJECT-TYPE	
		SYNTAX			Integer32
		MAX-ACCESS		read-only
		STATUS			current
		DESCRIPTION		"Current Mean Path Delay"
		::=  {  nptPtp1588PortCurrentEntry  19  }
		
		
	nptPtp1588PortCurrentRxDelayRespPkts	OBJECT-TYPE	
		SYNTAX			Integer32
		MAX-ACCESS		read-only
		STATUS			current
		DESCRIPTION		"Maximum Passive Time Offset"
		::=  {  nptPtp1588PortCurrentEntry  20  }
		
		
		
	nptPtp1588PortCurrentDroppedDelayRespPkts	OBJECT-TYPE	
		SYNTAX			Integer32
		MAX-ACCESS		read-only
		STATUS			current
		DESCRIPTION		"Minimum Passive Time Offset"
		::=  {  nptPtp1588PortCurrentEntry  21  }
        
        
	nptPtp1588PortCurrentLostDelayRespPkts	OBJECT-TYPE	
		SYNTAX			Integer32
		MAX-ACCESS		read-only
		STATUS			current
		DESCRIPTION		"Average Passive Time Offset"
		::=  {  nptPtp1588PortCurrentEntry  22  }
		
		
	nptPtp1588PortCurrentTxSignalPkts	OBJECT-TYPE	
		SYNTAX			Integer32
		MAX-ACCESS		read-only
		STATUS			current
		DESCRIPTION		"Current Passive Time Offset"
		::=  {  nptPtp1588PortCurrentEntry  23  }
		
        
	nptPtp1588PortCurrentRxSignalPkts	OBJECT-TYPE	
		SYNTAX			Integer32
		MAX-ACCESS		read-only
		STATUS			current
		DESCRIPTION		"Current Mean Path Delay"
		::=  {  nptPtp1588PortCurrentEntry  24  }
		
		
	nptPtp1588PortCurrentDroppedSignalPkts	OBJECT-TYPE	
		SYNTAX			Integer32
		MAX-ACCESS		read-only
		STATUS			current
		DESCRIPTION		"Maximum Passive Time Offset"
		::=  {  nptPtp1588PortCurrentEntry  25  }
		
		
		
	nptPtp1588PortCurrentLostSignalPkts	OBJECT-TYPE	
		SYNTAX			Integer32
		MAX-ACCESS		read-only
		STATUS			current
		DESCRIPTION		"Minimum Passive Time Offset"
		::=  {  nptPtp1588PortCurrentEntry  26  }
        
        
	nptPtp1588PortCurrentTxManagementPkts	OBJECT-TYPE	
		SYNTAX			Integer32
		MAX-ACCESS		read-only
		STATUS			current
		DESCRIPTION		"Average Passive Time Offset"
		::=  {  nptPtp1588PortCurrentEntry  27  }
		
		
	nptPtp1588PortCurrentRxManagementPkts	OBJECT-TYPE	
		SYNTAX			Integer32
		MAX-ACCESS		read-only
		STATUS			current
		DESCRIPTION		"Current Passive Time Offset"
		::=  {  nptPtp1588PortCurrentEntry  28  }
        
        
	nptPtp1588PortCurrentDroppedManagementPkts	OBJECT-TYPE	
		SYNTAX			Integer32
		MAX-ACCESS		read-only
		STATUS			current
		DESCRIPTION		"Average Passive Time Offset"
		::=  {  nptPtp1588PortCurrentEntry  29  }
		
		
	nptPtp1588PortCurrentLostManagementPkts	OBJECT-TYPE	
		SYNTAX			Integer32
		MAX-ACCESS		read-only
		STATUS			current
		DESCRIPTION		"Current Passive Time Offset"
		::=  {  nptPtp1588PortCurrentEntry  30  }
        
        
        
		nptPtp1588PortTotalTable	OBJECT-TYPE
		SYNTAX		SEQUENCE  OF  NptPtp1588PortTotalEntry
		MAX-ACCESS	not-accessible
		STATUS		current
		DESCRIPTION	"The Ptp1588Port current table contains various statistics
            being collected for the current 15 minute
            interval."
		::=  { nptPtp1588PortIfGroup  2 }

	nptPtp1588PortTotalEntry	OBJECT-TYPE
		SYNTAX		NptPtp1588PortTotalEntry
		MAX-ACCESS	not-accessible
		STATUS		current
		DESCRIPTION	"An entry in the Ptp1588Port Total table."
		INDEX		{  nptPtp1588PortTotalIndex  }
		::=  { nptPtp1588PortTotalTable 1 }

	NptPtp1588PortTotalEntry  ::=  SEQUENCE {
		nptPtp1588PortTotalIndex  Integer32,
		nptPtp1588PortTotalMoDescription  DisplayString,
		nptPtp1588PortTotalTxAnnouncePkts  Integer32,
		nptPtp1588PortTotalRxAnnouncePkts Integer32,
		nptPtp1588PortTotalDroppedAnnouncePkts  Integer32,
		nptPtp1588PortTotalLostAnnouncePkts  Integer32,
		nptPtp1588PortTotalTxSyncPkts  Integer32,
		nptPtp1588PortTotalRxSyncPkts  Integer32,
		nptPtp1588PortTotalDroppedSyncPkts  Integer32,
		nptPtp1588PortTotalLostSyncPkts  Integer32,
		nptPtp1588PortTotalTxFollowUpPkts  Integer32,
		nptPtp1588PortTotalRxFollowUpPkts  Integer32,
		nptPtp1588PortTotalDroppedFollowUpPkts  Integer32,
        nptPtp1588PortTotalLostFollowUpPkts  Integer32,
        nptPtp1588PortTotalTxDelayReqPkts  Integer32,
		nptPtp1588PortTotalRxDelayReqPkts  Integer32,
		nptPtp1588PortTotalDroppedDelayReqPkts  Integer32,
        nptPtp1588PortTotalLostDelayReqPkts  Integer32,
        nptPtp1588PortTotalTxDelayRespPkts  Integer32,
		nptPtp1588PortTotalRxDelayRespPkts  Integer32,
		nptPtp1588PortTotalDroppedDelayRespPkts  Integer32,
        nptPtp1588PortTotalLostDelayRespPkts  Integer32,
        nptPtp1588PortTotalTxSignalPkts  Integer32,
		nptPtp1588PortTotalRxSignalPkts  Integer32,
		nptPtp1588PortTotalDroppedSignalPkts  Integer32,
        nptPtp1588PortTotalLostSignalPkts  Integer32,
        nptPtp1588PortTotalTxManagementPkts  Integer32,
		nptPtp1588PortTotalRxManagementPkts  Integer32,
		nptPtp1588PortTotalDroppedManagementPkts  Integer32,
        nptPtp1588PortTotalLostManagementPkts  Integer32
		}


	nptPtp1588PortTotalIndex	OBJECT-TYPE	
		SYNTAX			Integer32  ( -2147483648 .. 2147483647  ) 
		MAX-ACCESS		read-only
		STATUS			current
		DESCRIPTION		"The index value which uniquely identifies  the
            Ptp1588Port interface to which this entry is applicable."
		::=  {  nptPtp1588PortTotalEntry  1  }
		
	nptPtp1588PortTotalMoDescription	OBJECT-TYPE	
		SYNTAX			DisplayString 
		MAX-ACCESS		read-only
		STATUS			current
		DESCRIPTION		"Mo Description"
		::=  {  nptPtp1588PortTotalEntry  2  }


	nptPtp1588PortTotalTxAnnouncePkts	OBJECT-TYPE	
		SYNTAX			Integer32
		MAX-ACCESS		read-only
		STATUS			current
		DESCRIPTION		"Maximum Offset From Master"
		::=  {  nptPtp1588PortTotalEntry  3  }


	nptPtp1588PortTotalRxAnnouncePkts	OBJECT-TYPE	
		SYNTAX			Integer32
		MAX-ACCESS		read-only
		STATUS			current
		DESCRIPTION		"Minimum Offset From Master"
		::=  {  nptPtp1588PortTotalEntry  4  }


	nptPtp1588PortTotalDroppedAnnouncePkts	OBJECT-TYPE	
		SYNTAX			Integer32
		MAX-ACCESS		read-only
		STATUS			current
		DESCRIPTION		"Average Offset From Master"
		::=  {  nptPtp1588PortTotalEntry  5  }


	nptPtp1588PortTotalLostAnnouncePkts	OBJECT-TYPE	
		SYNTAX			Integer32
		MAX-ACCESS		read-only
		STATUS			current
		DESCRIPTION		"Current Offset From Master"
		::=  {  nptPtp1588PortTotalEntry  6  }


	nptPtp1588PortTotalTxSyncPkts	OBJECT-TYPE	
		SYNTAX			Integer32
		MAX-ACCESS		read-only
		STATUS			current
		DESCRIPTION		"Accumulated Offset from Master"
		::=  {  nptPtp1588PortTotalEntry  7  }


	nptPtp1588PortTotalRxSyncPkts	OBJECT-TYPE	
		SYNTAX			Integer32
		MAX-ACCESS		read-only
		STATUS			current
		DESCRIPTION		"Maximum Master to Slave Delay"
		::=  {  nptPtp1588PortTotalEntry  8  }


	nptPtp1588PortTotalDroppedSyncPkts	OBJECT-TYPE	
		SYNTAX			Integer32
		MAX-ACCESS		read-only
		STATUS			current
		DESCRIPTION		"Minimum Master to Slave Delay"
		::=  {  nptPtp1588PortTotalEntry  9  }


	nptPtp1588PortTotalLostSyncPkts	OBJECT-TYPE	
		SYNTAX			Integer32
		MAX-ACCESS		read-only
		STATUS			current
		DESCRIPTION		"Average Master to Slave Delay"
		::=  {  nptPtp1588PortTotalEntry  10  }
		
		
	nptPtp1588PortTotalTxFollowUpPkts	OBJECT-TYPE	
		SYNTAX			Integer32
		MAX-ACCESS		read-only
		STATUS			current
		DESCRIPTION		"Current Master to Slave Delay"
		::=  {  nptPtp1588PortTotalEntry  11  }
		
		
	nptPtp1588PortTotalRxFollowUpPkts	OBJECT-TYPE	
		SYNTAX			Integer32
		MAX-ACCESS		read-only
		STATUS			current
		DESCRIPTION		"Maximum Slave to Master Delay"
		::=  {  nptPtp1588PortTotalEntry  12  }
		
		
		
	nptPtp1588PortTotalDroppedFollowUpPkts	OBJECT-TYPE	
		SYNTAX			Integer32
		MAX-ACCESS		read-only
		STATUS			current
		DESCRIPTION		"Minimum Slave to Master Delay"
		::=  {  nptPtp1588PortTotalEntry  13  }
		
	nptPtp1588PortTotalLostFollowUpPkts	OBJECT-TYPE	
		SYNTAX			Integer32
		MAX-ACCESS		read-only
		STATUS			current
		DESCRIPTION		"Average Slave to Master Delay"
		::=  {  nptPtp1588PortTotalEntry  14  }
		
		
	nptPtp1588PortTotalTxDelayReqPkts	OBJECT-TYPE	
		SYNTAX			Integer32
		MAX-ACCESS		read-only
		STATUS			current
		DESCRIPTION		"Current Slave to Master Delay"
		::=  {  nptPtp1588PortTotalEntry  15  }
		
		
	nptPtp1588PortTotalRxDelayReqPkts	OBJECT-TYPE	
		SYNTAX			Integer32
		MAX-ACCESS		read-only
		STATUS			current
		DESCRIPTION		"Maximum Mean Path Delay"
		::=  {  nptPtp1588PortTotalEntry  16  }
		
		
		
	nptPtp1588PortTotalDroppedDelayReqPkts	OBJECT-TYPE	
		SYNTAX			Integer32
		MAX-ACCESS		read-only
		STATUS			current
		DESCRIPTION		"Minimum Mean Path Delay"
		::=  {  nptPtp1588PortTotalEntry  17  }
        
		
	nptPtp1588PortTotalLostDelayReqPkts	OBJECT-TYPE	
		SYNTAX			Integer32
		MAX-ACCESS		read-only
		STATUS			current
		DESCRIPTION		"Average Mean Path Delay"
		::=  {  nptPtp1588PortTotalEntry  18  }
		
		
	nptPtp1588PortTotalTxDelayRespPkts	OBJECT-TYPE	
		SYNTAX			Integer32
		MAX-ACCESS		read-only
		STATUS			current
		DESCRIPTION		"Current Mean Path Delay"
		::=  {  nptPtp1588PortTotalEntry  19  }
		
		
	nptPtp1588PortTotalRxDelayRespPkts	OBJECT-TYPE	
		SYNTAX			Integer32
		MAX-ACCESS		read-only
		STATUS			current
		DESCRIPTION		"Maximum Passive Time Offset"
		::=  {  nptPtp1588PortTotalEntry  20  }
		
		
		
	nptPtp1588PortTotalDroppedDelayRespPkts	OBJECT-TYPE	
		SYNTAX			Integer32
		MAX-ACCESS		read-only
		STATUS			current
		DESCRIPTION		"Minimum Passive Time Offset"
		::=  {  nptPtp1588PortTotalEntry  21  }
        
        
	nptPtp1588PortTotalLostDelayRespPkts	OBJECT-TYPE	
		SYNTAX			Integer32
		MAX-ACCESS		read-only
		STATUS			current
		DESCRIPTION		"Average Passive Time Offset"
		::=  {  nptPtp1588PortTotalEntry  22  }
		
		
	nptPtp1588PortTotalTxSignalPkts	OBJECT-TYPE	
		SYNTAX			Integer32
		MAX-ACCESS		read-only
		STATUS			current
		DESCRIPTION		"Current Passive Time Offset"
		::=  {  nptPtp1588PortTotalEntry  23  }
		
        
	nptPtp1588PortTotalRxSignalPkts	OBJECT-TYPE	
		SYNTAX			Integer32
		MAX-ACCESS		read-only
		STATUS			current
		DESCRIPTION		"Current Mean Path Delay"
		::=  {  nptPtp1588PortTotalEntry  24  }
		
		
	nptPtp1588PortTotalDroppedSignalPkts	OBJECT-TYPE	
		SYNTAX			Integer32
		MAX-ACCESS		read-only
		STATUS			current
		DESCRIPTION		"Maximum Passive Time Offset"
		::=  {  nptPtp1588PortTotalEntry  25  }
		
		
		
	nptPtp1588PortTotalLostSignalPkts	OBJECT-TYPE	
		SYNTAX			Integer32
		MAX-ACCESS		read-only
		STATUS			current
		DESCRIPTION		"Minimum Passive Time Offset"
		::=  {  nptPtp1588PortTotalEntry  26  }
        
        
	nptPtp1588PortTotalTxManagementPkts	OBJECT-TYPE	
		SYNTAX			Integer32
		MAX-ACCESS		read-only
		STATUS			current
		DESCRIPTION		"Average Passive Time Offset"
		::=  {  nptPtp1588PortTotalEntry  27  }
		
		
	nptPtp1588PortTotalRxManagementPkts	OBJECT-TYPE	
		SYNTAX			Integer32
		MAX-ACCESS		read-only
		STATUS			current
		DESCRIPTION		"Current Passive Time Offset"
		::=  {  nptPtp1588PortTotalEntry  28  }
        
        
	nptPtp1588PortTotalDroppedManagementPkts	OBJECT-TYPE	
		SYNTAX			Integer32
		MAX-ACCESS		read-only
		STATUS			current
		DESCRIPTION		"Average Passive Time Offset"
		::=  {  nptPtp1588PortTotalEntry  29  }
		
		
	nptPtp1588PortTotalLostManagementPkts	OBJECT-TYPE	
		SYNTAX			Integer32
		MAX-ACCESS		read-only
		STATUS			current
		DESCRIPTION		"Current Passive Time Offset"
		::=  {  nptPtp1588PortTotalEntry  30  }


    nptMaCurrentTable	OBJECT-TYPE
		SYNTAX		SEQUENCE  OF  NptMaCurrentEntry
		MAX-ACCESS	not-accessible
		STATUS		current
		DESCRIPTION	"The Ma current table contains various statistics
            being collected for the current 15 minute
            interval."
		::=  { nptMaIfGroup  1 }

	nptMaCurrentEntry	OBJECT-TYPE
		SYNTAX		NptMaCurrentEntry
		MAX-ACCESS	not-accessible
		STATUS		current
		DESCRIPTION	"An entry in the Ma Current table."
		INDEX		{  nptMaCurrentIndex  }
		::=  { nptMaCurrentTable 1 }

	NptMaCurrentEntry  ::=  SEQUENCE {
		nptMaCurrentIndex  Integer32,
		nptMaCurrentMoDescription  DisplayString,
		nptMaCurrentMADownSeconds  Counter64,
		nptMaCurrentMADownSecondsPPM Counter64
		}


	nptMaCurrentIndex	OBJECT-TYPE	
		SYNTAX			Integer32  ( -2147483648 .. 2147483647  ) 
		MAX-ACCESS		read-only
		STATUS			current
		DESCRIPTION		"The index value which uniquely identifies  the
            Ma interface to which this entry is applicable."
		::=  {  nptMaCurrentEntry  1  }
		
	nptMaCurrentMoDescription	OBJECT-TYPE	
		SYNTAX			DisplayString 
		MAX-ACCESS		read-only
		STATUS			current
		DESCRIPTION		"Mo Description"
		::=  {  nptMaCurrentEntry  2  }


	nptMaCurrentMADownSeconds	OBJECT-TYPE	
		SYNTAX			Counter64
		MAX-ACCESS		read-only
		STATUS			current
		DESCRIPTION		"Number of seconds during which the Operational state of MEG was down ."
		::=  {  nptMaCurrentEntry  3  }


	nptMaCurrentMADownSecondsPPM	OBJECT-TYPE	
		SYNTAX			Counter64
		MAX-ACCESS		read-only
		STATUS			current
		DESCRIPTION		"Ratio of time during which the the Operational state of MEG was down(0-1,000,000@1)."
		::=  {  nptMaCurrentEntry  4  }
		
		
	nptMaTotalTable	OBJECT-TYPE
		SYNTAX		SEQUENCE  OF  NptMaTotalEntry
		MAX-ACCESS	not-accessible
		STATUS		current
		DESCRIPTION	"The Ma current table contains various statistics
            being collected for the current 15 minute
            interval."
		::=  { nptMaIfGroup  2 }

	nptMaTotalEntry	OBJECT-TYPE
		SYNTAX		NptMaTotalEntry
		MAX-ACCESS	not-accessible
		STATUS		current
		DESCRIPTION	"An entry in the Ma Total table."
		INDEX		{  nptMaTotalIndex  }
		::=  { nptMaTotalTable 1 }

	NptMaTotalEntry  ::=  SEQUENCE {
		nptMaTotalIndex  Integer32,
		nptMaTotalMoDescription  DisplayString,
		nptMaTotalMADownSeconds  Counter64,
		nptMaTotalMADownSecondsPPM Counter64
		}


	nptMaTotalIndex	OBJECT-TYPE	
		SYNTAX			Integer32  ( -2147483648 .. 2147483647  ) 
		MAX-ACCESS		read-only
		STATUS			current
		DESCRIPTION		"The index value which uniquely identifies  the
            Ma interface to which this entry is applicable."
		::=  {  nptMaTotalEntry  1  }
		
	nptMaTotalMoDescription	OBJECT-TYPE	
		SYNTAX			DisplayString 
		MAX-ACCESS		read-only
		STATUS			current
		DESCRIPTION		"Mo Description"
		::=  {  nptMaTotalEntry  2  }


	nptMaTotalMADownSeconds	OBJECT-TYPE	
		SYNTAX			Counter64
		MAX-ACCESS		read-only
		STATUS			current
		DESCRIPTION		"Number of seconds during which the Operational state of MEG was down ."
		::=  {  nptMaTotalEntry  3  }


	nptMaTotalMADownSecondsPPM	OBJECT-TYPE	
		SYNTAX			Counter64
		MAX-ACCESS		read-only
		STATUS			current
		DESCRIPTION		"Ratio of time during which the the Operational state of MEG was down(0-1,000,000@1)."
		::=  {  nptMaTotalEntry  4  }
		

	nptLocalMepCurrentTable	OBJECT-TYPE
		SYNTAX		SEQUENCE  OF  NptLocalMepCurrentEntry
		MAX-ACCESS	not-accessible
		STATUS		current
		DESCRIPTION	"The LocalMep current table contains various statistics
            being collected for the current 15 minute
            interval."
		::=  { nptLocalMepIfGroup  1 }

	nptLocalMepCurrentEntry	OBJECT-TYPE
		SYNTAX		NptLocalMepCurrentEntry
		MAX-ACCESS	not-accessible
		STATUS		current
		DESCRIPTION	"An entry in the LocalMep Current table."
		INDEX		{  nptLocalMepCurrentIndex  }
		::=  { nptLocalMepCurrentTable 1 }

	NptLocalMepCurrentEntry  ::=  SEQUENCE {
		nptLocalMepCurrentIndex  Integer32,
		nptLocalMepCurrentMoDescription  DisplayString,
		nptLocalMepCurrentCCMFramesTx  Counter64,
		nptLocalMepCurrentCCMFramesRx Counter64,
		nptLocalMepCurrentLBMFramesTx  Counter64,
		nptLocalMepCurrentLBMFramesRx  Counter64,
		nptLocalMepCurrentLBRFramesTx  Counter64,
		nptLocalMepCurrentLBRFramesRx  Counter64,
		nptLocalMepCurrentLTMFramesTx  Counter64,
		nptLocalMepCurrentLTMFramesRx  Counter64,
		nptLocalMepCurrentLTRFramesTx  Counter64,
		nptLocalMepCurrentLTRFramesRx  Counter64
		}


	nptLocalMepCurrentIndex	OBJECT-TYPE	
		SYNTAX			Integer32  ( -2147483648 .. 2147483647  ) 
		MAX-ACCESS		read-only
		STATUS			current
		DESCRIPTION		"The index value which uniquely identifies  the
            LocalMep interface to which this entry is applicable."
		::=  {  nptLocalMepCurrentEntry  1  }
		
	nptLocalMepCurrentMoDescription	OBJECT-TYPE	
		SYNTAX			DisplayString 
		MAX-ACCESS		read-only
		STATUS			current
		DESCRIPTION		"Mo Description"
		::=  {  nptLocalMepCurrentEntry  2  }


	nptLocalMepCurrentCCMFramesTx	OBJECT-TYPE	
		SYNTAX			Counter64
		MAX-ACCESS		read-only
		STATUS			current
		DESCRIPTION		"Total number of transmitted CCM frames."
		::=  {  nptLocalMepCurrentEntry  3  }


	nptLocalMepCurrentCCMFramesRx	OBJECT-TYPE	
		SYNTAX			Counter64
		MAX-ACCESS		read-only
		STATUS			current
		DESCRIPTION		"Total number of valid CCM frames received."
		::=  {  nptLocalMepCurrentEntry  4  }


	nptLocalMepCurrentLBMFramesTx	OBJECT-TYPE	
		SYNTAX			Counter64
		MAX-ACCESS		read-only
		STATUS			current
		DESCRIPTION		"Total number of transmitted LBM frames ."
		::=  {  nptLocalMepCurrentEntry  5  }


	nptLocalMepCurrentLBMFramesRx	OBJECT-TYPE	
		SYNTAX			Counter64
		MAX-ACCESS		read-only
		STATUS			current
		DESCRIPTION		"Total number of valid LBM frames received."
		::=  {  nptLocalMepCurrentEntry  6  }


	nptLocalMepCurrentLBRFramesTx	OBJECT-TYPE	
		SYNTAX			Counter64
		MAX-ACCESS		read-only
		STATUS			current
		DESCRIPTION		"Total number of transmitted LBR frames."
		::=  {  nptLocalMepCurrentEntry  7  }


	nptLocalMepCurrentLBRFramesRx	OBJECT-TYPE	
		SYNTAX			Counter64
		MAX-ACCESS		read-only
		STATUS			current
		DESCRIPTION		"Total number of valid LBR frames received."
		::=  {  nptLocalMepCurrentEntry  8  }


	nptLocalMepCurrentLTMFramesTx	OBJECT-TYPE	
		SYNTAX			Counter64
		MAX-ACCESS		read-only
		STATUS			current
		DESCRIPTION		"Total number of transmitted LTM frames ."
		::=  {  nptLocalMepCurrentEntry  9  }


	nptLocalMepCurrentLTMFramesRx	OBJECT-TYPE	
		SYNTAX			Counter64
		MAX-ACCESS		read-only
		STATUS			current
		DESCRIPTION		"Total number of transmitted LTM frames ."
		::=  {  nptLocalMepCurrentEntry  10  }
		
		
	nptLocalMepCurrentLTRFramesTx	OBJECT-TYPE	
		SYNTAX			Counter64
		MAX-ACCESS		read-only
		STATUS			current
		DESCRIPTION		"Total number of transmitted LTR frames ."
		::=  {  nptLocalMepCurrentEntry  11  }
		
		
	nptLocalMepCurrentLTRFramesRx	OBJECT-TYPE	
		SYNTAX			Counter64
		MAX-ACCESS		read-only
		STATUS			current
		DESCRIPTION		"Total number of valid LTR frames received."
		::=  {  nptLocalMepCurrentEntry  12  }
		
		
	nptLocalMepTotalTable	OBJECT-TYPE
		SYNTAX		SEQUENCE  OF  NptLocalMepTotalEntry
		MAX-ACCESS	not-accessible
		STATUS		current
		DESCRIPTION	"The LocalMep current table contains various statistics
            being collected for the current 15 minute
            interval."
		::=  { nptLocalMepIfGroup  2 }

	nptLocalMepTotalEntry	OBJECT-TYPE
		SYNTAX		NptLocalMepTotalEntry
		MAX-ACCESS	not-accessible
		STATUS		current
		DESCRIPTION	"An entry in the LocalMep Total table."
		INDEX		{  nptLocalMepTotalIndex  }
		::=  { nptLocalMepTotalTable 1 }

	NptLocalMepTotalEntry  ::=  SEQUENCE {
		nptLocalMepTotalIndex  Integer32,
		nptLocalMepTotalMoDescription  DisplayString,
		nptLocalMepTotalCCMFramesTx  Counter64,
		nptLocalMepTotalCCMFramesRx Counter64,
		nptLocalMepTotalLBMFramesTx  Counter64,
		nptLocalMepTotalLBMFramesRx  Counter64,
		nptLocalMepTotalLBRFramesTx  Counter64,
		nptLocalMepTotalLBRFramesRx  Counter64,
		nptLocalMepTotalLTMFramesTx  Counter64,
		nptLocalMepTotalLTMFramesRx  Counter64,
		nptLocalMepTotalLTRFramesTx  Counter64,
		nptLocalMepTotalLTRFramesRx  Counter64
		}


	nptLocalMepTotalIndex	OBJECT-TYPE	
		SYNTAX			Integer32  ( -2147483648 .. 2147483647  ) 
		MAX-ACCESS		read-only
		STATUS			current
		DESCRIPTION		"The index value which uniquely identifies  the
            LocalMep interface to which this entry is applicable."
		::=  {  nptLocalMepTotalEntry  1  }
		
	nptLocalMepTotalMoDescription	OBJECT-TYPE	
		SYNTAX			DisplayString 
		MAX-ACCESS		read-only
		STATUS			current
		DESCRIPTION		"Mo Description"
		::=  {  nptLocalMepTotalEntry  2  }


	nptLocalMepTotalCCMFramesTx	OBJECT-TYPE	
		SYNTAX			Counter64
		MAX-ACCESS		read-only
		STATUS			current
		DESCRIPTION		"Total number of transmitted CCM frames."
		::=  {  nptLocalMepTotalEntry  3  }


	nptLocalMepTotalCCMFramesRx	OBJECT-TYPE	
		SYNTAX			Counter64
		MAX-ACCESS		read-only
		STATUS			current
		DESCRIPTION		"Total number of valid CCM frames received."
		::=  {  nptLocalMepTotalEntry  4  }


	nptLocalMepTotalLBMFramesTx	OBJECT-TYPE	
		SYNTAX			Counter64
		MAX-ACCESS		read-only
		STATUS			current
		DESCRIPTION		"Total number of transmitted LBM frames ."
		::=  {  nptLocalMepTotalEntry  5  }


	nptLocalMepTotalLBMFramesRx	OBJECT-TYPE	
		SYNTAX			Counter64
		MAX-ACCESS		read-only
		STATUS			current
		DESCRIPTION		"Total number of valid LBM frames received."
		::=  {  nptLocalMepTotalEntry  6  }


	nptLocalMepTotalLBRFramesTx	OBJECT-TYPE	
		SYNTAX			Counter64
		MAX-ACCESS		read-only
		STATUS			current
		DESCRIPTION		"Total number of transmitted LBR frames."
		::=  {  nptLocalMepTotalEntry  7  }


	nptLocalMepTotalLBRFramesRx	OBJECT-TYPE	
		SYNTAX			Counter64
		MAX-ACCESS		read-only
		STATUS			current
		DESCRIPTION		"Total number of valid LBR frames received."
		::=  {  nptLocalMepTotalEntry  8  }


	nptLocalMepTotalLTMFramesTx	OBJECT-TYPE	
		SYNTAX			Counter64
		MAX-ACCESS		read-only
		STATUS			current
		DESCRIPTION		"Total number of transmitted LTM frames ."
		::=  {  nptLocalMepTotalEntry  9  }


	nptLocalMepTotalLTMFramesRx	OBJECT-TYPE	
		SYNTAX			Counter64
		MAX-ACCESS		read-only
		STATUS			current
		DESCRIPTION		"Total number of transmitted LTM frames ."
		::=  {  nptLocalMepTotalEntry  10  }
		
		
	nptLocalMepTotalLTRFramesTx	OBJECT-TYPE	
		SYNTAX			Counter64
		MAX-ACCESS		read-only
		STATUS			current
		DESCRIPTION		"Total number of transmitted LTR frames ."
		::=  {  nptLocalMepTotalEntry  11  }
		
		
	nptLocalMepTotalLTRFramesRx	OBJECT-TYPE	
		SYNTAX			Counter64
		MAX-ACCESS		read-only
		STATUS			current
		DESCRIPTION		"Total number of valid LTR frames received."
		::=  {  nptLocalMepTotalEntry  12  }
		
		
	nptRemoteMepCurrentTable	OBJECT-TYPE
		SYNTAX		SEQUENCE  OF  NptRemoteMepCurrentEntry
		MAX-ACCESS	not-accessible
		STATUS		current
		DESCRIPTION	"The RemoteMep current table contains various statistics
            being collected for the current 15 minute
            interval."
		::=  { nptRemoteMepIfGroup  1 }

	nptRemoteMepCurrentEntry	OBJECT-TYPE
		SYNTAX		NptRemoteMepCurrentEntry
		MAX-ACCESS	not-accessible
		STATUS		current
		DESCRIPTION	"An entry in the RemoteMep Current table."
		INDEX		{  nptRemoteMepCurrentIndex  }
		::=  { nptRemoteMepCurrentTable 1 }

	NptRemoteMepCurrentEntry  ::=  SEQUENCE {
		nptRemoteMepCurrentIndex  Integer32,
		nptRemoteMepCurrentMoDescription  DisplayString,
		nptRemoteMepCurrentDownSeconds  Counter64,
		nptRemoteMepCurrentDownSecondsPPM Counter64
		}


	nptRemoteMepCurrentIndex	OBJECT-TYPE	
		SYNTAX			Integer32  ( -2147483648 .. 2147483647  ) 
		MAX-ACCESS		read-only
		STATUS			current
		DESCRIPTION		"The index value which uniquely identifies  the
            RemoteMep interface to which this entry is applicable."
		::=  {  nptRemoteMepCurrentEntry  1  }
		
	nptRemoteMepCurrentMoDescription	OBJECT-TYPE	
		SYNTAX			DisplayString 
		MAX-ACCESS		read-only
		STATUS			current
		DESCRIPTION		"Mo Description"
		::=  {  nptRemoteMepCurrentEntry  2  }


	nptRemoteMepCurrentDownSeconds	OBJECT-TYPE	
		SYNTAX			Counter64
		MAX-ACCESS		read-only
		STATUS			current
		DESCRIPTION		"Number of seconds during which the Operational state of remote MEP was down."
		::=  {  nptRemoteMepCurrentEntry  3  }


	nptRemoteMepCurrentDownSecondsPPM	OBJECT-TYPE	
		SYNTAX			Counter64
		MAX-ACCESS		read-only
		STATUS			current
		DESCRIPTION		"Ratio of time during which the Operational state of Remote MEP was down, calculated by: ."
		::=  {  nptRemoteMepCurrentEntry  4  }
		
		
	nptRemoteMepTotalTable	OBJECT-TYPE
		SYNTAX		SEQUENCE  OF  NptRemoteMepTotalEntry
		MAX-ACCESS	not-accessible
		STATUS		current
		DESCRIPTION	"The RemoteMep current table contains various statistics
            being collected for the current 15 minute
            interval."
		::=  { nptRemoteMepIfGroup  2 }

	nptRemoteMepTotalEntry	OBJECT-TYPE
		SYNTAX		NptRemoteMepTotalEntry
		MAX-ACCESS	not-accessible
		STATUS		current
		DESCRIPTION	"An entry in the RemoteMep Total table."
		INDEX		{  nptRemoteMepTotalIndex  }
		::=  { nptRemoteMepTotalTable 1 }

	NptRemoteMepTotalEntry  ::=  SEQUENCE {
		nptRemoteMepTotalIndex  Integer32,
		nptRemoteMepTotalMoDescription  DisplayString,
		nptRemoteMepTotalDownSeconds  Counter64,
		nptRemoteMepTotalDownSecondsPPM Counter64
		}


	nptRemoteMepTotalIndex	OBJECT-TYPE	
		SYNTAX			Integer32  ( -2147483648 .. 2147483647  ) 
		MAX-ACCESS		read-only
		STATUS			current
		DESCRIPTION		"The index value which uniquely identifies  the
            RemoteMep interface to which this entry is applicable."
		::=  {  nptRemoteMepTotalEntry  1  }
		
	nptRemoteMepTotalMoDescription	OBJECT-TYPE	
		SYNTAX			DisplayString 
		MAX-ACCESS		read-only
		STATUS			current
		DESCRIPTION		"Mo Description"
		::=  {  nptRemoteMepTotalEntry  2  }


	nptRemoteMepTotalDownSeconds	OBJECT-TYPE	
		SYNTAX			Counter64
		MAX-ACCESS		read-only
		STATUS			current
		DESCRIPTION		"Number of seconds during which the Operational state of remote MEP was down."
		::=  {  nptRemoteMepTotalEntry  3  }


	nptRemoteMepTotalDownSecondsPPM	OBJECT-TYPE	
		SYNTAX			Counter64
		MAX-ACCESS		read-only
		STATUS			current
		DESCRIPTION		"Ratio of time during which the Operational state of Remote MEP was down, calculated by: ."
		::=  {  nptRemoteMepTotalEntry  4  }


	nptRemoteMepdmCurrentTable	OBJECT-TYPE
		SYNTAX		SEQUENCE  OF  NptRemoteMepdmCurrentEntry
		MAX-ACCESS	not-accessible
		STATUS		current
		DESCRIPTION	"The RemoteMepdm current table contains various statistics
            being collected for the current 15 minute
            interval."
		::=  { nptRemoteMepdmIfGroup  1 }

	nptRemoteMepdmCurrentEntry	OBJECT-TYPE
		SYNTAX		NptRemoteMepdmCurrentEntry
		MAX-ACCESS	not-accessible
		STATUS		current
		DESCRIPTION	"An entry in the RemoteMepdm Current table."
		INDEX		{  nptRemoteMepdmCurrentIndex  }
		::=  { nptRemoteMepdmCurrentTable 1 }

	NptRemoteMepdmCurrentEntry  ::=  SEQUENCE {
		nptRemoteMepdmCurrentIndex  Integer32,
		nptRemoteMepdmCurrentMoDescription  DisplayString,
		nptRemoteMepdmCurrentDMMFramesTransmitted  Counter64,
		nptRemoteMepdmCurrentDMRFramesReceived Counter64,
		nptRemoteMepdmCurrentNotCompliantFDMeasurements  Counter64,
		nptRemoteMepdmCurrentNotCompliantFDVMeasurementsforward  Counter64,
		nptRemoteMepdmCurrentNotCompliantFDVMeasurementsbackward  Counter64,
		nptRemoteMepdmCurrentAverageFD  Counter64,
		nptRemoteMepdmCurrentMaximumFD  Counter64,
		nptRemoteMepdmCurrentMinmumFD  Counter64,
		nptRemoteMepdmCurrentAverageFDVforward  Counter64,
		nptRemoteMepdmCurrentAverageFDVbackward  Counter64,
		nptRemoteMepdmCurrentMinimumFDVforward  Counter64,
		nptRemoteMepdmCurrentMaximumFDVforward  Counter64,
		nptRemoteMepdmCurrentMinimumFDVbackward  Counter64,
		nptRemoteMepdmCurrentMaximumFDVbackward  Counter64
		}


	nptRemoteMepdmCurrentIndex	OBJECT-TYPE	
		SYNTAX			Integer32  ( -2147483648 .. 2147483647  ) 
		MAX-ACCESS		read-only
		STATUS			current
		DESCRIPTION		"The index value which uniquely identifies  the
            RemoteMepdm interface to which this entry is applicable."
		::=  {  nptRemoteMepdmCurrentEntry  1  }
		
	nptRemoteMepdmCurrentMoDescription	OBJECT-TYPE	
		SYNTAX			DisplayString 
		MAX-ACCESS		read-only
		STATUS			current
		DESCRIPTION		"Mo Description"
		::=  {  nptRemoteMepdmCurrentEntry  2  }


	nptRemoteMepdmCurrentDMMFramesTransmitted	OBJECT-TYPE	
		SYNTAX			Counter64
		MAX-ACCESS		read-only
		STATUS			current
		DESCRIPTION		"Number of transmitted DMM frames (i.e. number of initiated measurements )."
		::=  {  nptRemoteMepdmCurrentEntry  3  }


	nptRemoteMepdmCurrentDMRFramesReceived	OBJECT-TYPE	
		SYNTAX			Counter64
		MAX-ACCESS		read-only
		STATUS			current
		DESCRIPTION		"Number of received DMR frames (i.e. number of completed measurements )."
		::=  {  nptRemoteMepdmCurrentEntry  4  }


	nptRemoteMepdmCurrentNotCompliantFDMeasurements	OBJECT-TYPE	
		SYNTAX			Counter64
		MAX-ACCESS		read-only
		STATUS			current
		DESCRIPTION		"Number of FD measurements which fell above the threshold ."
		::=  {  nptRemoteMepdmCurrentEntry  5  }


	nptRemoteMepdmCurrentNotCompliantFDVMeasurementsforward	OBJECT-TYPE	
		SYNTAX			Counter64
		MAX-ACCESS		read-only
		STATUS			current
		DESCRIPTION		"Number of FDV measurements in forward direction which fell above the threshold."
		::=  {  nptRemoteMepdmCurrentEntry  6  }


	nptRemoteMepdmCurrentNotCompliantFDVMeasurementsbackward	OBJECT-TYPE	
		SYNTAX			Counter64
		MAX-ACCESS		read-only
		STATUS			current
		DESCRIPTION		"Number of FDV measurements in backward direction which fell above the threshold"
		::=  {  nptRemoteMepdmCurrentEntry  7  }


	nptRemoteMepdmCurrentAverageFD	OBJECT-TYPE	
		SYNTAX			Counter64
		MAX-ACCESS		read-only
		STATUS			current
		DESCRIPTION		"Average FD(usec) during the interval."
		::=  {  nptRemoteMepdmCurrentEntry  8  }


	nptRemoteMepdmCurrentMaximumFD	OBJECT-TYPE	
		SYNTAX			Counter64
		MAX-ACCESS		read-only
		STATUS			current
		DESCRIPTION		"Maximum FD(usec) during the interval."
		::=  {  nptRemoteMepdmCurrentEntry  9  }


	nptRemoteMepdmCurrentMinmumFD	OBJECT-TYPE	
		SYNTAX			Counter64
		MAX-ACCESS		read-only
		STATUS			current
		DESCRIPTION		"Minmum FD(usec) during the interval."
		::=  {  nptRemoteMepdmCurrentEntry  10  }
		
		
	nptRemoteMepdmCurrentAverageFDVforward	OBJECT-TYPE	
		SYNTAX			Counter64
		MAX-ACCESS		read-only
		STATUS			current
		DESCRIPTION		"Average FDV(usec) during the interval in forward direction."
		::=  {  nptRemoteMepdmCurrentEntry  11  }
		
		
	nptRemoteMepdmCurrentAverageFDVbackward	OBJECT-TYPE	
		SYNTAX			Counter64
		MAX-ACCESS		read-only
		STATUS			current
		DESCRIPTION		"Average FDV(usec) during the interval in backward direction."
		::=  {  nptRemoteMepdmCurrentEntry  12  }
		
		
	
	nptRemoteMepdmCurrentMinimumFDVforward	OBJECT-TYPE	
		SYNTAX			Counter64
		MAX-ACCESS		read-only
		STATUS			current
		DESCRIPTION		"Minimum FDV(usec) during the interval in forward direction."
		::=  {  nptRemoteMepdmCurrentEntry  13  }
		
		
	nptRemoteMepdmCurrentMaximumFDVforward	OBJECT-TYPE	
		SYNTAX			Counter64
		MAX-ACCESS		read-only
		STATUS			current
		DESCRIPTION		"Maximum FDV(usec) during the interval in forward direction."
		::=  {  nptRemoteMepdmCurrentEntry  14  }
		
		
	nptRemoteMepdmCurrentMinimumFDVbackward	OBJECT-TYPE	
		SYNTAX			Counter64
		MAX-ACCESS		read-only
		STATUS			current
		DESCRIPTION		"Minimum FDV(usec) during the interval in backward direction."
		::=  {  nptRemoteMepdmCurrentEntry  15  }
		
		
	nptRemoteMepdmCurrentMaximumFDVbackward	OBJECT-TYPE	
		SYNTAX			Counter64
		MAX-ACCESS		read-only
		STATUS			current
		DESCRIPTION		"Maximum FDV(usec) during the interval in backward direction."
		::=  {  nptRemoteMepdmCurrentEntry  16  }
		
		
	nptRemoteMepdmTotalTable	OBJECT-TYPE
		SYNTAX		SEQUENCE  OF  NptRemoteMepdmTotalEntry
		MAX-ACCESS	not-accessible
		STATUS		current
		DESCRIPTION	"The RemoteMepdm current table contains various statistics
            being collected for the current 15 minute
            interval."
		::=  { nptRemoteMepdmIfGroup  2 }

	nptRemoteMepdmTotalEntry	OBJECT-TYPE
		SYNTAX		NptRemoteMepdmTotalEntry
		MAX-ACCESS	not-accessible
		STATUS		current
		DESCRIPTION	"An entry in the RemoteMepdm Total table."
		INDEX		{  nptRemoteMepdmTotalIndex  }
		::=  { nptRemoteMepdmTotalTable 1 }

	NptRemoteMepdmTotalEntry  ::=  SEQUENCE {
		nptRemoteMepdmTotalIndex  Integer32,
		nptRemoteMepdmTotalMoDescription  DisplayString,
		nptRemoteMepdmTotalDMMFramesTransmitted  Counter64,
		nptRemoteMepdmTotalDMRFramesReceived Counter64,
		nptRemoteMepdmTotalNotCompliantFDMeasurements  Counter64,
		nptRemoteMepdmTotalNotCompliantFDVMeasurementsforward  Counter64,
		nptRemoteMepdmTotalNotCompliantFDVMeasurementsbackward  Counter64,
		nptRemoteMepdmTotalAverageFD  Counter64,
		nptRemoteMepdmTotalMaximumFD  Counter64,
		nptRemoteMepdmTotalMinmumFD  Counter64,
		nptRemoteMepdmTotalAverageFDVforward  Counter64,
		nptRemoteMepdmTotalAverageFDVbackward  Counter64,
		nptRemoteMepdmTotalMinimumFDVforward  Counter64,
		nptRemoteMepdmTotalMaximumFDVforward  Counter64,
		nptRemoteMepdmTotalMinimumFDVbackward  Counter64,
		nptRemoteMepdmTotalMaximumFDVbackward  Counter64
		}


	nptRemoteMepdmTotalIndex	OBJECT-TYPE	
		SYNTAX			Integer32  ( -2147483648 .. 2147483647  ) 
		MAX-ACCESS		read-only
		STATUS			current
		DESCRIPTION		"The index value which uniquely identifies  the
            RemoteMepdm interface to which this entry is applicable."
		::=  {  nptRemoteMepdmTotalEntry  1  }
		
	nptRemoteMepdmTotalMoDescription	OBJECT-TYPE	
		SYNTAX			DisplayString 
		MAX-ACCESS		read-only
		STATUS			current
		DESCRIPTION		"Mo Description"
		::=  {  nptRemoteMepdmTotalEntry  2  }


	nptRemoteMepdmTotalDMMFramesTransmitted	OBJECT-TYPE	
		SYNTAX			Counter64
		MAX-ACCESS		read-only
		STATUS			current
		DESCRIPTION		"Number of transmitted DMM frames (i.e. number of initiated measurements )."
		::=  {  nptRemoteMepdmTotalEntry  3  }


	nptRemoteMepdmTotalDMRFramesReceived	OBJECT-TYPE	
		SYNTAX			Counter64
		MAX-ACCESS		read-only
		STATUS			current
		DESCRIPTION		"Number of received DMR frames (i.e. number of completed measurements )."
		::=  {  nptRemoteMepdmTotalEntry  4  }


	nptRemoteMepdmTotalNotCompliantFDMeasurements	OBJECT-TYPE	
		SYNTAX			Counter64
		MAX-ACCESS		read-only
		STATUS			current
		DESCRIPTION		"Number of FD measurements which fell above the threshold ."
		::=  {  nptRemoteMepdmTotalEntry  5  }


	nptRemoteMepdmTotalNotCompliantFDVMeasurementsforward	OBJECT-TYPE	
		SYNTAX			Counter64
		MAX-ACCESS		read-only
		STATUS			current
		DESCRIPTION		"Number of FDV measurements in forward direction which fell above the threshold."
		::=  {  nptRemoteMepdmTotalEntry  6  }


	nptRemoteMepdmTotalNotCompliantFDVMeasurementsbackward	OBJECT-TYPE	
		SYNTAX			Counter64
		MAX-ACCESS		read-only
		STATUS			current
		DESCRIPTION		"Number of FDV measurements in backward direction which fell above the threshold"
		::=  {  nptRemoteMepdmTotalEntry  7  }


	nptRemoteMepdmTotalAverageFD	OBJECT-TYPE	
		SYNTAX			Counter64
		MAX-ACCESS		read-only
		STATUS			current
		DESCRIPTION		"Average FD(usec) during the interval."
		::=  {  nptRemoteMepdmTotalEntry  8  }


	nptRemoteMepdmTotalMaximumFD	OBJECT-TYPE	
		SYNTAX			Counter64
		MAX-ACCESS		read-only
		STATUS			current
		DESCRIPTION		"Maximum FD(usec) during the interval."
		::=  {  nptRemoteMepdmTotalEntry  9  }


	nptRemoteMepdmTotalMinmumFD	OBJECT-TYPE	
		SYNTAX			Counter64
		MAX-ACCESS		read-only
		STATUS			current
		DESCRIPTION		"Minmum FD(usec) during the interval."
		::=  {  nptRemoteMepdmTotalEntry  10  }
		
		
	nptRemoteMepdmTotalAverageFDVforward	OBJECT-TYPE	
		SYNTAX			Counter64
		MAX-ACCESS		read-only
		STATUS			current
		DESCRIPTION		"Average FDV(usec) during the interval in forward direction."
		::=  {  nptRemoteMepdmTotalEntry  11  }
		
		
	nptRemoteMepdmTotalAverageFDVbackward	OBJECT-TYPE	
		SYNTAX			Counter64
		MAX-ACCESS		read-only
		STATUS			current
		DESCRIPTION		"Average FDV(usec) during the interval in backward direction."
		::=  {  nptRemoteMepdmTotalEntry  12  }
		
		
	
	nptRemoteMepdmTotalMinimumFDVforward	OBJECT-TYPE	
		SYNTAX			Counter64
		MAX-ACCESS		read-only
		STATUS			current
		DESCRIPTION		"Minimum FDV(usec) during the interval in forward direction."
		::=  {  nptRemoteMepdmTotalEntry  13  }
		
		
	nptRemoteMepdmTotalMaximumFDVforward	OBJECT-TYPE	
		SYNTAX			Counter64
		MAX-ACCESS		read-only
		STATUS			current
		DESCRIPTION		"Maximum FDV(usec) during the interval in forward direction."
		::=  {  nptRemoteMepdmTotalEntry  14  }
		
		
	nptRemoteMepdmTotalMinimumFDVbackward	OBJECT-TYPE	
		SYNTAX			Counter64
		MAX-ACCESS		read-only
		STATUS			current
		DESCRIPTION		"Minimum FDV(usec) during the interval in backward direction."
		::=  {  nptRemoteMepdmTotalEntry  15  }
		
		
	nptRemoteMepdmTotalMaximumFDVbackward	OBJECT-TYPE	
		SYNTAX			Counter64
		MAX-ACCESS		read-only
		STATUS			current
		DESCRIPTION		"Maximum FDV(usec) during the interval in backward direction."
		::=  {  nptRemoteMepdmTotalEntry  16  }
		
		
	nptRemoteMepslmCurrentTable	OBJECT-TYPE
		SYNTAX		SEQUENCE  OF  NptRemoteMepslmCurrentEntry
		MAX-ACCESS	not-accessible
		STATUS		current
		DESCRIPTION	"The RemoteMepslm current table contains various statistics
            being collected for the current 15 minute
            interval."
		::=  { nptRemoteMepslmIfGroup  1 }

	nptRemoteMepslmCurrentEntry	OBJECT-TYPE
		SYNTAX		NptRemoteMepslmCurrentEntry
		MAX-ACCESS	not-accessible
		STATUS		current
		DESCRIPTION	"An entry in the RemoteMepslm Current table."
		INDEX		{  nptRemoteMepslmCurrentIndex  }
		::=  { nptRemoteMepslmCurrentTable 1 }

	NptRemoteMepslmCurrentEntry  ::=  SEQUENCE {
		nptRemoteMepslmCurrentIndex  Integer32,
		nptRemoteMepslmCurrentMoDescription  DisplayString,
		nptRemoteMepslmCurrentSLMFramesTransmitted  Counter64,
		nptRemoteMepslmCurrentSLRFramesReceived Counter64,
		nptRemoteMepslmCurrentLastFarEndFLR  Counter64,
		nptRemoteMepslmCurrentMinFarEndFLR  Counter64,
		nptRemoteMepslmCurrentMaxFarEndFLR  Counter64,
		nptRemoteMepslmCurrentAvgFarEndFLR  Counter64,
		nptRemoteMepslmCurrentLastNearEndFLR  Counter64,
		nptRemoteMepslmCurrentMinNearEndFLR  Counter64,
		nptRemoteMepslmCurrentMaxNearEndFLR  Counter64,
		nptRemoteMepslmCurrentAvgNearEndFLR  Counter64,
		nptRemoteMepslmCurrentFarEndSES  Counter64,
		nptRemoteMepslmCurrentNearEndSES  Counter64,
		nptRemoteMepslmCurrentFarEndUAS  Counter64,
		nptRemoteMepslmCurrentNearEndUAS  Counter64
		}


	nptRemoteMepslmCurrentIndex	OBJECT-TYPE	
		SYNTAX			Integer32  ( -2147483648 .. 2147483647  ) 
		MAX-ACCESS		read-only
		STATUS			current
		DESCRIPTION		"The index value which uniquely identifies  the
            RemoteMepslm interface to which this entry is applicable."
		::=  {  nptRemoteMepslmCurrentEntry  1  }
		
	nptRemoteMepslmCurrentMoDescription	OBJECT-TYPE	
		SYNTAX			DisplayString 
		MAX-ACCESS		read-only
		STATUS			current
		DESCRIPTION		"Mo Description"
		::=  {  nptRemoteMepslmCurrentEntry  2  }


	nptRemoteMepslmCurrentSLMFramesTransmitted	OBJECT-TYPE	
		SYNTAX			Counter64
		MAX-ACCESS		read-only
		STATUS			current
		DESCRIPTION		"Number of transmitted SLM frames (i.e. number of initiated measurements )."
		::=  {  nptRemoteMepslmCurrentEntry  3  }


	nptRemoteMepslmCurrentSLRFramesReceived	OBJECT-TYPE	
		SYNTAX			Counter64
		MAX-ACCESS		read-only
		STATUS			current
		DESCRIPTION		"Number of received SLR frames (i.e. number of completed measurements )."
		::=  {  nptRemoteMepslmCurrentEntry  4  }


	nptRemoteMepslmCurrentLastFarEndFLR	OBJECT-TYPE	
		SYNTAX			Counter64
		MAX-ACCESS		read-only
		STATUS			current
		DESCRIPTION		"Last Far End FLR for the remote MEP."
		::=  {  nptRemoteMepslmCurrentEntry  5  }


	nptRemoteMepslmCurrentMinFarEndFLR	OBJECT-TYPE	
		SYNTAX			Counter64
		MAX-ACCESS		read-only
		STATUS			current
		DESCRIPTION		"The minimum Far End FLR for the remote MEP during this Measurement Interval."
		::=  {  nptRemoteMepslmCurrentEntry  6  }


	nptRemoteMepslmCurrentMaxFarEndFLR	OBJECT-TYPE	
		SYNTAX			Counter64
		MAX-ACCESS		read-only
		STATUS			current
		DESCRIPTION		"The maximum Far End FLR for the remote MEP during this Measurement Interval."
		::=  {  nptRemoteMepslmCurrentEntry  7  }


	nptRemoteMepslmCurrentAvgFarEndFLR	OBJECT-TYPE	
		SYNTAX			Counter64
		MAX-ACCESS		read-only
		STATUS			current
		DESCRIPTION		"The average Far End FLR for the remote MEP during this Measurement Interval."
		::=  {  nptRemoteMepslmCurrentEntry  8  }


	nptRemoteMepslmCurrentLastNearEndFLR	OBJECT-TYPE	
		SYNTAX			Counter64
		MAX-ACCESS		read-only
		STATUS			current
		DESCRIPTION		"Last Near End FLR for the remote MEP"
		::=  {  nptRemoteMepslmCurrentEntry  9  }


	nptRemoteMepslmCurrentMinNearEndFLR	OBJECT-TYPE	
		SYNTAX			Counter64
		MAX-ACCESS		read-only
		STATUS			current
		DESCRIPTION		"The minimum Near End FLR for the remote MEP during this Measurement Interval."
		::=  {  nptRemoteMepslmCurrentEntry  10  }
		
		
	nptRemoteMepslmCurrentMaxNearEndFLR	OBJECT-TYPE	
		SYNTAX			Counter64
		MAX-ACCESS		read-only
		STATUS			current
		DESCRIPTION		"The Maximum Near End FLR for the remote MEP during this Measurement Interval."
		::=  {  nptRemoteMepslmCurrentEntry  11  }
		
		
	nptRemoteMepslmCurrentAvgNearEndFLR	OBJECT-TYPE	
		SYNTAX			Counter64
		MAX-ACCESS		read-only
		STATUS			current
		DESCRIPTION		"The average Near End FLR for the remote MEP during this Measurement Interval."
		::=  {  nptRemoteMepslmCurrentEntry  12  }
		
		
	
	nptRemoteMepslmCurrentFarEndSES	OBJECT-TYPE	
		SYNTAX			Counter64
		MAX-ACCESS		read-only
		STATUS			current
		DESCRIPTION		"Number of seconds of Far End Severely Errored Windows (windows with FLR > MA_UNAVAIL_THRESH)"
		::=  {  nptRemoteMepslmCurrentEntry  13  }
		
		
	nptRemoteMepslmCurrentNearEndSES	OBJECT-TYPE	
		SYNTAX			Counter64
		MAX-ACCESS		read-only
		STATUS			current
		DESCRIPTION		"Number of seconds of Near End Severely Errored Windows (Wondows with FLR > MA_UNAVAIL_THRESH) "
		::=  {  nptRemoteMepslmCurrentEntry  14  }
		
		
	nptRemoteMepslmCurrentFarEndUAS	OBJECT-TYPE	
		SYNTAX			Counter64
		MAX-ACCESS		read-only
		STATUS			current
		DESCRIPTION		"Number of seconds evaluated as unavailable in the forward direction."
		::=  {  nptRemoteMepslmCurrentEntry  15  }
		
		
	nptRemoteMepslmCurrentNearEndUAS	OBJECT-TYPE	
		SYNTAX			Counter64
		MAX-ACCESS		read-only
		STATUS			current
		DESCRIPTION		"Number of seconds evaluated as available in the backward direction."
		::=  {  nptRemoteMepslmCurrentEntry  16  }
		
		
	nptRemoteMepslmTotalTable	OBJECT-TYPE
		SYNTAX		SEQUENCE  OF  NptRemoteMepslmTotalEntry
		MAX-ACCESS	not-accessible
		STATUS		current
		DESCRIPTION	"The RemoteMepslm current table contains various statistics
            being collected for the current 15 minute
            interval."
		::=  { nptRemoteMepslmIfGroup  2 }

	nptRemoteMepslmTotalEntry	OBJECT-TYPE
		SYNTAX		NptRemoteMepslmTotalEntry
		MAX-ACCESS	not-accessible
		STATUS		current
		DESCRIPTION	"An entry in the RemoteMepslm Total table."
		INDEX		{  nptRemoteMepslmTotalIndex  }
		::=  { nptRemoteMepslmTotalTable 1 }

	NptRemoteMepslmTotalEntry  ::=  SEQUENCE {
		nptRemoteMepslmTotalIndex  Integer32,
		nptRemoteMepslmTotalMoDescription  DisplayString,
		nptRemoteMepslmTotalSLMFramesTransmitted  Counter64,
		nptRemoteMepslmTotalSLRFramesReceived Counter64,
		nptRemoteMepslmTotalLastFarEndFLR  Counter64,
		nptRemoteMepslmTotalMinFarEndFLR  Counter64,
		nptRemoteMepslmTotalMaxFarEndFLR  Counter64,
		nptRemoteMepslmTotalAvgFarEndFLR  Counter64,
		nptRemoteMepslmTotalLastNearEndFLR  Counter64,
		nptRemoteMepslmTotalMinNearEndFLR  Counter64,
		nptRemoteMepslmTotalMaxNearEndFLR  Counter64,
		nptRemoteMepslmTotalAvgNearEndFLR  Counter64,
		nptRemoteMepslmTotalFarEndSES  Counter64,
		nptRemoteMepslmTotalNearEndSES  Counter64,
		nptRemoteMepslmTotalFarEndUAS  Counter64,
		nptRemoteMepslmTotalNearEndUAS  Counter64
		}


	nptRemoteMepslmTotalIndex	OBJECT-TYPE	
		SYNTAX			Integer32  ( -2147483648 .. 2147483647  ) 
		MAX-ACCESS		read-only
		STATUS			current
		DESCRIPTION		"The index value which uniquely identifies  the
            RemoteMepslm interface to which this entry is applicable."
		::=  {  nptRemoteMepslmTotalEntry  1  }
		
	nptRemoteMepslmTotalMoDescription	OBJECT-TYPE	
		SYNTAX			DisplayString 
		MAX-ACCESS		read-only
		STATUS			current
		DESCRIPTION		"Mo Description"
		::=  {  nptRemoteMepslmTotalEntry  2  }


	nptRemoteMepslmTotalSLMFramesTransmitted	OBJECT-TYPE	
		SYNTAX			Counter64
		MAX-ACCESS		read-only
		STATUS			current
		DESCRIPTION		"Number of transmitted SLM frames (i.e. number of initiated measurements )."
		::=  {  nptRemoteMepslmTotalEntry  3  }


	nptRemoteMepslmTotalSLRFramesReceived	OBJECT-TYPE	
		SYNTAX			Counter64
		MAX-ACCESS		read-only
		STATUS			current
		DESCRIPTION		"Number of received SLR frames (i.e. number of completed measurements )."
		::=  {  nptRemoteMepslmTotalEntry  4  }


	nptRemoteMepslmTotalLastFarEndFLR	OBJECT-TYPE	
		SYNTAX			Counter64
		MAX-ACCESS		read-only
		STATUS			current
		DESCRIPTION		"Last Far End FLR for the remote MEP."
		::=  {  nptRemoteMepslmTotalEntry  5  }


	nptRemoteMepslmTotalMinFarEndFLR	OBJECT-TYPE	
		SYNTAX			Counter64
		MAX-ACCESS		read-only
		STATUS			current
		DESCRIPTION		"The minimum Far End FLR for the remote MEP during this Measurement Interval."
		::=  {  nptRemoteMepslmTotalEntry  6  }


	nptRemoteMepslmTotalMaxFarEndFLR	OBJECT-TYPE	
		SYNTAX			Counter64
		MAX-ACCESS		read-only
		STATUS			current
		DESCRIPTION		"The maximum Far End FLR for the remote MEP during this Measurement Interval."
		::=  {  nptRemoteMepslmTotalEntry  7  }


	nptRemoteMepslmTotalAvgFarEndFLR	OBJECT-TYPE	
		SYNTAX			Counter64
		MAX-ACCESS		read-only
		STATUS			current
		DESCRIPTION		"The average Far End FLR for the remote MEP during this Measurement Interval."
		::=  {  nptRemoteMepslmTotalEntry  8  }


	nptRemoteMepslmTotalLastNearEndFLR	OBJECT-TYPE	
		SYNTAX			Counter64
		MAX-ACCESS		read-only
		STATUS			current
		DESCRIPTION		"Last Near End FLR for the remote MEP"
		::=  {  nptRemoteMepslmTotalEntry  9  }


	nptRemoteMepslmTotalMinNearEndFLR	OBJECT-TYPE	
		SYNTAX			Counter64
		MAX-ACCESS		read-only
		STATUS			current
		DESCRIPTION		"The minimum Near End FLR for the remote MEP during this Measurement Interval."
		::=  {  nptRemoteMepslmTotalEntry  10  }
		
		
	nptRemoteMepslmTotalMaxNearEndFLR	OBJECT-TYPE	
		SYNTAX			Counter64
		MAX-ACCESS		read-only
		STATUS			current
		DESCRIPTION		"The Maximum Near End FLR for the remote MEP during this Measurement Interval."
		::=  {  nptRemoteMepslmTotalEntry  11  }
		
		
	nptRemoteMepslmTotalAvgNearEndFLR	OBJECT-TYPE	
		SYNTAX			Counter64
		MAX-ACCESS		read-only
		STATUS			current
		DESCRIPTION		"The average Near End FLR for the remote MEP during this Measurement Interval."
		::=  {  nptRemoteMepslmTotalEntry  12  }
		
		
	
	nptRemoteMepslmTotalFarEndSES	OBJECT-TYPE	
		SYNTAX			Counter64
		MAX-ACCESS		read-only
		STATUS			current
		DESCRIPTION		"Number of seconds of Far End Severely Errored Windows (windows with FLR > MA_UNAVAIL_THRESH)"
		::=  {  nptRemoteMepslmTotalEntry  13  }
		
		
	nptRemoteMepslmTotalNearEndSES	OBJECT-TYPE	
		SYNTAX			Counter64
		MAX-ACCESS		read-only
		STATUS			current
		DESCRIPTION		"Number of seconds of Near End Severely Errored Windows (Wondows with FLR > MA_UNAVAIL_THRESH) "
		::=  {  nptRemoteMepslmTotalEntry  14  }
		
		
	nptRemoteMepslmTotalFarEndUAS	OBJECT-TYPE	
		SYNTAX			Counter64
		MAX-ACCESS		read-only
		STATUS			current
		DESCRIPTION		"Number of seconds evaluated as unavailable in the forward direction."
		::=  {  nptRemoteMepslmTotalEntry  15  }
		
		
	nptRemoteMepslmTotalNearEndUAS	OBJECT-TYPE	
		SYNTAX			Counter64
		MAX-ACCESS		read-only
		STATUS			current
		DESCRIPTION		"Number of seconds evaluated as available in the backward direction."
		::=  {  nptRemoteMepslmTotalEntry  16  }
		
	nptODU2CurrentTable	OBJECT-TYPE
		SYNTAX		SEQUENCE  OF  NptODU2CurrentEntry
		MAX-ACCESS	not-accessible
		STATUS		current
		DESCRIPTION	"The ODU2 current table contains various statistics
            being collected for the current 15 minute
            interval."
		::=  { nptODU2Port  1 }

	nptODU2CurrentEntry	OBJECT-TYPE
		SYNTAX		NptODU2CurrentEntry
		MAX-ACCESS	not-accessible
		STATUS		current
		DESCRIPTION	"An entry in the ODU2 Current table."
		INDEX		{  nptODU2CurrentIndex  }
		::=  { nptODU2CurrentTable 1 }

	NptODU2CurrentEntry  ::=  SEQUENCE {
		nptODU2CurrentIndex  Integer32,
		nptODU2CurrentMoDescription  DisplayString,
		nptODU2CurrentBBENE  Counter64,
		nptODU2CurrentESNE Counter64,
		nptODU2CurrentSESNE  Counter64,
		nptODU2CurrentUASNE  Counter64,
		nptODU2CurrentBBEFE  Counter64,
		nptODU2CurrentESFE  Counter64,
		nptODU2CurrentSESFE  Counter64,
		nptODU2CurrentUASFE  Counter64,
		nptODU2CurrentTSE  Counter64
		}


	nptODU2CurrentIndex	OBJECT-TYPE	
		SYNTAX			Integer32  ( -2147483648 .. 2147483647  ) 
		MAX-ACCESS		read-only
		STATUS			current
		DESCRIPTION		"The index value which uniquely identifies  the
            ODU2 interface to which this entry is applicable."
		::=  {  nptODU2CurrentEntry  1  }
		
	nptODU2CurrentMoDescription	OBJECT-TYPE	
		SYNTAX			DisplayString 
		MAX-ACCESS		read-only
		STATUS			current
		DESCRIPTION		"Mo Description"
		::=  {  nptODU2CurrentEntry  2  }


	nptODU2CurrentBBENE	OBJECT-TYPE	
		SYNTAX			Counter64
		MAX-ACCESS		read-only
		STATUS			current
		DESCRIPTION		"Background block error Near end An errored block not occurring as part of SES"
		::=  {  nptODU2CurrentEntry  3  }


	nptODU2CurrentESNE	OBJECT-TYPE	
		SYNTAX			Counter64
		MAX-ACCESS		read-only
		STATUS			current
		DESCRIPTION		"Errored second Near end 1-second period which contains at least one errored blocks or at least one defect"
		::=  {  nptODU2CurrentEntry  4  }


	nptODU2CurrentSESNE	OBJECT-TYPE	
		SYNTAX			Counter64
		MAX-ACCESS		read-only
		STATUS			current
		DESCRIPTION		"Severely errored second Near end 1-second period which contains ?Y15% errored blocks or at least one defect"
		::=  {  nptODU2CurrentEntry  5  }


	nptODU2CurrentUASNE	OBJECT-TYPE	
		SYNTAX			Counter64
		MAX-ACCESS		read-only
		STATUS			current
		DESCRIPTION		"Unavailable seconds near end"
		::=  {  nptODU2CurrentEntry  6  }


	nptODU2CurrentBBEFE	OBJECT-TYPE	
		SYNTAX			Counter64
		MAX-ACCESS		read-only
		STATUS			current
		DESCRIPTION		"Background block error Far end An errored block not occurring as part of SES-FE"
		::=  {  nptODU2CurrentEntry  7  }


	nptODU2CurrentESFE	OBJECT-TYPE	
		SYNTAX			Counter64
		MAX-ACCESS		read-only
		STATUS			current
		DESCRIPTION		"Errored second Far end 1-second period which contains at least one errored blocks or at least one defect"
		::=  {  nptODU2CurrentEntry  8  }


	nptODU2CurrentSESFE	OBJECT-TYPE	
		SYNTAX			Counter64
		MAX-ACCESS		read-only
		STATUS			current
		DESCRIPTION		"Severely errored second Far end 1-second period which contains ?Y15% errored blocks or at least one defect"
		::=  {  nptODU2CurrentEntry  9  }


	nptODU2CurrentUASFE	OBJECT-TYPE	
		SYNTAX			Counter64
		MAX-ACCESS		read-only
		STATUS			current
		DESCRIPTION		"Unavailable second far end"
		::=  {  nptODU2CurrentEntry  10  }
		
		
	nptODU2CurrentTSE	OBJECT-TYPE	
		SYNTAX			Counter64
		MAX-ACCESS		read-only
		STATUS			current
		DESCRIPTION		"Test Sequence Error. Counts the number of invalid test pattern"
		::=  {  nptODU2CurrentEntry  11  }
		
	nptODU2TotalTable	OBJECT-TYPE
		SYNTAX		SEQUENCE  OF  NptODU2TotalEntry
		MAX-ACCESS	not-accessible
		STATUS		current
		DESCRIPTION	"The ODU2 current table contains various statistics
            being collected for the current 15 minute
            interval."
		::=  { nptODU2Port  2 }

	nptODU2TotalEntry	OBJECT-TYPE
		SYNTAX		NptODU2TotalEntry
		MAX-ACCESS	not-accessible
		STATUS		current
		DESCRIPTION	"An entry in the ODU2 Total table."
		INDEX		{  nptODU2TotalIndex  }
		::=  { nptODU2TotalTable 1 }

	NptODU2TotalEntry  ::=  SEQUENCE {
		nptODU2TotalIndex  Integer32,
		nptODU2TotalMoDescription  DisplayString,
		nptODU2TotalBBENE  Counter64,
		nptODU2TotalESNE Counter64,
		nptODU2TotalSESNE  Counter64,
		nptODU2TotalUASNE  Counter64,
		nptODU2TotalBBEFE  Counter64,
		nptODU2TotalESFE  Counter64,
		nptODU2TotalSESFE  Counter64,
		nptODU2TotalUASFE  Counter64,
		nptODU2TotalTSE  Counter64
		}


	nptODU2TotalIndex	OBJECT-TYPE	
		SYNTAX			Integer32  ( -2147483648 .. 2147483647  ) 
		MAX-ACCESS		read-only
		STATUS			current
		DESCRIPTION		"The index value which uniquely identifies  the
            ODU2 interface to which this entry is applicable."
		::=  {  nptODU2TotalEntry  1  }
		
	nptODU2TotalMoDescription	OBJECT-TYPE	
		SYNTAX			DisplayString 
		MAX-ACCESS		read-only
		STATUS			current
		DESCRIPTION		"Mo Description"
		::=  {  nptODU2TotalEntry  2  }


	nptODU2TotalBBENE	OBJECT-TYPE	
		SYNTAX			Counter64
		MAX-ACCESS		read-only
		STATUS			current
		DESCRIPTION		"Background block error Near end An errored block not occurring as part of SES"
		::=  {  nptODU2TotalEntry  3  }


	nptODU2TotalESNE	OBJECT-TYPE	
		SYNTAX			Counter64
		MAX-ACCESS		read-only
		STATUS			current
		DESCRIPTION		"Errored second Near end 1-second period which contains at least one errored blocks or at least one defect"
		::=  {  nptODU2TotalEntry  4  }


	nptODU2TotalSESNE	OBJECT-TYPE	
		SYNTAX			Counter64
		MAX-ACCESS		read-only
		STATUS			current
		DESCRIPTION		"Severely errored second Near end 1-second period which contains ?Y15% errored blocks or at least one defect"
		::=  {  nptODU2TotalEntry  5  }


	nptODU2TotalUASNE	OBJECT-TYPE	
		SYNTAX			Counter64
		MAX-ACCESS		read-only
		STATUS			current
		DESCRIPTION		"Unavailable seconds near end"
		::=  {  nptODU2TotalEntry  6  }


	nptODU2TotalBBEFE	OBJECT-TYPE	
		SYNTAX			Counter64
		MAX-ACCESS		read-only
		STATUS			current
		DESCRIPTION		"Background block error Far end An errored block not occurring as part of SES-FE"
		::=  {  nptODU2TotalEntry  7  }


	nptODU2TotalESFE	OBJECT-TYPE	
		SYNTAX			Counter64
		MAX-ACCESS		read-only
		STATUS			current
		DESCRIPTION		"Errored second Far end 1-second period which contains at least one errored blocks or at least one defect"
		::=  {  nptODU2TotalEntry  8  }


	nptODU2TotalSESFE	OBJECT-TYPE	
		SYNTAX			Counter64
		MAX-ACCESS		read-only
		STATUS			current
		DESCRIPTION		"Severely errored second Far end 1-second period which contains ?Y15% errored blocks or at least one defect"
		::=  {  nptODU2TotalEntry  9  }


	nptODU2TotalUASFE	OBJECT-TYPE	
		SYNTAX			Counter64
		MAX-ACCESS		read-only
		STATUS			current
		DESCRIPTION		"Unavailable second far end"
		::=  {  nptODU2TotalEntry  10  }
		
		
	nptODU2TotalTSE	OBJECT-TYPE	
		SYNTAX			Counter64
		MAX-ACCESS		read-only
		STATUS			current
		DESCRIPTION		"Test Sequence Error. Counts the number of invalid test pattern"
		::=  {  nptODU2TotalEntry  11  }
		
	nptODU2eCurrentTable	OBJECT-TYPE
		SYNTAX		SEQUENCE  OF  NptODU2eCurrentEntry
		MAX-ACCESS	not-accessible
		STATUS		current
		DESCRIPTION	"The ODU2e current table contains various statistics
            being collected for the current 15 minute
            interval."
		::=  { nptODU2ePort  1 }

	nptODU2eCurrentEntry	OBJECT-TYPE
		SYNTAX		NptODU2eCurrentEntry
		MAX-ACCESS	not-accessible
		STATUS		current
		DESCRIPTION	"An entry in the ODU2e Current table."
		INDEX		{  nptODU2eCurrentIndex  }
		::=  { nptODU2eCurrentTable 1 }

	NptODU2eCurrentEntry  ::=  SEQUENCE {
		nptODU2eCurrentIndex  Integer32,
		nptODU2eCurrentMoDescription  DisplayString,
		nptODU2eCurrentBBENE  Counter64,
		nptODU2eCurrentESNE Counter64,
		nptODU2eCurrentSESNE  Counter64,
		nptODU2eCurrentUASNE  Counter64,
		nptODU2eCurrentBBEFE  Counter64,
		nptODU2eCurrentESFE  Counter64,
		nptODU2eCurrentSESFE  Counter64,
		nptODU2eCurrentUASFE  Counter64,
		nptODU2eCurrentTSE  Counter64
		}


	nptODU2eCurrentIndex	OBJECT-TYPE	
		SYNTAX			Integer32  ( -2147483648 .. 2147483647  ) 
		MAX-ACCESS		read-only
		STATUS			current
		DESCRIPTION		"The index value which uniquely identifies  the
            ODU2e interface to which this entry is applicable."
		::=  {  nptODU2eCurrentEntry  1  }
		
	nptODU2eCurrentMoDescription	OBJECT-TYPE	
		SYNTAX			DisplayString 
		MAX-ACCESS		read-only
		STATUS			current
		DESCRIPTION		"Mo Description"
		::=  {  nptODU2eCurrentEntry  2  }


	nptODU2eCurrentBBENE	OBJECT-TYPE	
		SYNTAX			Counter64
		MAX-ACCESS		read-only
		STATUS			current
		DESCRIPTION		"Background block error Near end An errored block not occurring as part of SES"
		::=  {  nptODU2eCurrentEntry  3  }


	nptODU2eCurrentESNE	OBJECT-TYPE	
		SYNTAX			Counter64
		MAX-ACCESS		read-only
		STATUS			current
		DESCRIPTION		"Errored second Near end 1-second period which contains at least one errored blocks or at least one defect"
		::=  {  nptODU2eCurrentEntry  4  }


	nptODU2eCurrentSESNE	OBJECT-TYPE	
		SYNTAX			Counter64
		MAX-ACCESS		read-only
		STATUS			current
		DESCRIPTION		"Severely errored second Near end 1-second period which contains ?Y15% errored blocks or at least one defect"
		::=  {  nptODU2eCurrentEntry  5  }


	nptODU2eCurrentUASNE	OBJECT-TYPE	
		SYNTAX			Counter64
		MAX-ACCESS		read-only
		STATUS			current
		DESCRIPTION		"Unavailable seconds near end"
		::=  {  nptODU2eCurrentEntry  6  }


	nptODU2eCurrentBBEFE	OBJECT-TYPE	
		SYNTAX			Counter64
		MAX-ACCESS		read-only
		STATUS			current
		DESCRIPTION		"Background block error Far end An errored block not occurring as part of SES-FE"
		::=  {  nptODU2eCurrentEntry  7  }


	nptODU2eCurrentESFE	OBJECT-TYPE	
		SYNTAX			Counter64
		MAX-ACCESS		read-only
		STATUS			current
		DESCRIPTION		"Errored second Far end 1-second period which contains at least one errored blocks or at least one defect"
		::=  {  nptODU2eCurrentEntry  8  }


	nptODU2eCurrentSESFE	OBJECT-TYPE	
		SYNTAX			Counter64
		MAX-ACCESS		read-only
		STATUS			current
		DESCRIPTION		"Severely errored second Far end 1-second period which contains ?Y15% errored blocks or at least one defect"
		::=  {  nptODU2eCurrentEntry  9  }


	nptODU2eCurrentUASFE	OBJECT-TYPE	
		SYNTAX			Counter64
		MAX-ACCESS		read-only
		STATUS			current
		DESCRIPTION		"Unavailable second far end"
		::=  {  nptODU2eCurrentEntry  10  }
		
		
	nptODU2eCurrentTSE	OBJECT-TYPE	
		SYNTAX			Counter64
		MAX-ACCESS		read-only
		STATUS			current
		DESCRIPTION		"Test Sequence Error. Counts the number of invalid test pattern"
		::=  {  nptODU2eCurrentEntry  11  }
		
	nptODU2eTotalTable	OBJECT-TYPE
		SYNTAX		SEQUENCE  OF  NptODU2eTotalEntry
		MAX-ACCESS	not-accessible
		STATUS		current
		DESCRIPTION	"The ODU2e current table contains various statistics
            being collected for the current 15 minute
            interval."
		::=  { nptODU2ePort  2 }

	nptODU2eTotalEntry	OBJECT-TYPE
		SYNTAX		NptODU2eTotalEntry
		MAX-ACCESS	not-accessible
		STATUS		current
		DESCRIPTION	"An entry in the ODU2e Total table."
		INDEX		{  nptODU2eTotalIndex  }
		::=  { nptODU2eTotalTable 1 }

	NptODU2eTotalEntry  ::=  SEQUENCE {
		nptODU2eTotalIndex  Integer32,
		nptODU2eTotalMoDescription  DisplayString,
		nptODU2eTotalBBENE  Counter64,
		nptODU2eTotalESNE Counter64,
		nptODU2eTotalSESNE  Counter64,
		nptODU2eTotalUASNE  Counter64,
		nptODU2eTotalBBEFE  Counter64,
		nptODU2eTotalESFE  Counter64,
		nptODU2eTotalSESFE  Counter64,
		nptODU2eTotalUASFE  Counter64,
		nptODU2eTotalTSE  Counter64
		}


	nptODU2eTotalIndex	OBJECT-TYPE	
		SYNTAX			Integer32  ( -2147483648 .. 2147483647  ) 
		MAX-ACCESS		read-only
		STATUS			current
		DESCRIPTION		"The index value which uniquely identifies  the
            ODU2e interface to which this entry is applicable."
		::=  {  nptODU2eTotalEntry  1  }
		
	nptODU2eTotalMoDescription	OBJECT-TYPE	
		SYNTAX			DisplayString 
		MAX-ACCESS		read-only
		STATUS			current
		DESCRIPTION		"Mo Description"
		::=  {  nptODU2eTotalEntry  2  }


	nptODU2eTotalBBENE	OBJECT-TYPE	
		SYNTAX			Counter64
		MAX-ACCESS		read-only
		STATUS			current
		DESCRIPTION		"Background block error Near end An errored block not occurring as part of SES"
		::=  {  nptODU2eTotalEntry  3  }


	nptODU2eTotalESNE	OBJECT-TYPE	
		SYNTAX			Counter64
		MAX-ACCESS		read-only
		STATUS			current
		DESCRIPTION		"Errored second Near end 1-second period which contains at least one errored blocks or at least one defect"
		::=  {  nptODU2eTotalEntry  4  }


	nptODU2eTotalSESNE	OBJECT-TYPE	
		SYNTAX			Counter64
		MAX-ACCESS		read-only
		STATUS			current
		DESCRIPTION		"Severely errored second Near end 1-second period which contains ?Y15% errored blocks or at least one defect"
		::=  {  nptODU2eTotalEntry  5  }


	nptODU2eTotalUASNE	OBJECT-TYPE	
		SYNTAX			Counter64
		MAX-ACCESS		read-only
		STATUS			current
		DESCRIPTION		"Unavailable seconds near end"
		::=  {  nptODU2eTotalEntry  6  }


	nptODU2eTotalBBEFE	OBJECT-TYPE	
		SYNTAX			Counter64
		MAX-ACCESS		read-only
		STATUS			current
		DESCRIPTION		"Background block error Far end An errored block not occurring as part of SES-FE"
		::=  {  nptODU2eTotalEntry  7  }


	nptODU2eTotalESFE	OBJECT-TYPE	
		SYNTAX			Counter64
		MAX-ACCESS		read-only
		STATUS			current
		DESCRIPTION		"Errored second Far end 1-second period which contains at least one errored blocks or at least one defect"
		::=  {  nptODU2eTotalEntry  8  }


	nptODU2eTotalSESFE	OBJECT-TYPE	
		SYNTAX			Counter64
		MAX-ACCESS		read-only
		STATUS			current
		DESCRIPTION		"Severely errored second Far end 1-second period which contains ?Y15% errored blocks or at least one defect"
		::=  {  nptODU2eTotalEntry  9  }


	nptODU2eTotalUASFE	OBJECT-TYPE	
		SYNTAX			Counter64
		MAX-ACCESS		read-only
		STATUS			current
		DESCRIPTION		"Unavailable second far end"
		::=  {  nptODU2eTotalEntry  10  }
		
		
	nptODU2eTotalTSE	OBJECT-TYPE	
		SYNTAX			Counter64
		MAX-ACCESS		read-only
		STATUS			current
		DESCRIPTION		"Test Sequence Error. Counts the number of invalid test pattern"
		::=  {  nptODU2eTotalEntry  11  }
		
	nptODU4CurrentTable	OBJECT-TYPE
		SYNTAX		SEQUENCE  OF  NptODU4CurrentEntry
		MAX-ACCESS	not-accessible
		STATUS		current
		DESCRIPTION	"The ODU4 current table contains various statistics
            being collected for the current 15 minute
            interval."
		::=  { nptODU4Port  1 }

	nptODU4CurrentEntry	OBJECT-TYPE
		SYNTAX		NptODU4CurrentEntry
		MAX-ACCESS	not-accessible
		STATUS		current
		DESCRIPTION	"An entry in the ODU4 Current table."
		INDEX		{  nptODU4CurrentIndex  }
		::=  { nptODU4CurrentTable 1 }

	NptODU4CurrentEntry  ::=  SEQUENCE {
		nptODU4CurrentIndex  Integer32,
		nptODU4CurrentMoDescription  DisplayString,
		nptODU4CurrentBBENE  Counter64,
		nptODU4CurrentESNE Counter64,
		nptODU4CurrentSESNE  Counter64,
		nptODU4CurrentUASNE  Counter64,
		nptODU4CurrentBBEFE  Counter64,
		nptODU4CurrentESFE  Counter64,
		nptODU4CurrentSESFE  Counter64,
		nptODU4CurrentUASFE  Counter64,
		nptODU4CurrentTSE  Counter64
		}


	nptODU4CurrentIndex	OBJECT-TYPE	
		SYNTAX			Integer32  ( -2147483648 .. 2147483647  ) 
		MAX-ACCESS		read-only
		STATUS			current
		DESCRIPTION		"The index value which uniquely identifies  the
            ODU4 interface to which this entry is applicable."
		::=  {  nptODU4CurrentEntry  1  }
		
	nptODU4CurrentMoDescription	OBJECT-TYPE	
		SYNTAX			DisplayString 
		MAX-ACCESS		read-only
		STATUS			current
		DESCRIPTION		"Mo Description"
		::=  {  nptODU4CurrentEntry  2  }


	nptODU4CurrentBBENE	OBJECT-TYPE	
		SYNTAX			Counter64
		MAX-ACCESS		read-only
		STATUS			current
		DESCRIPTION		"Background block error Near end An errored block not occurring as part of SES"
		::=  {  nptODU4CurrentEntry  3  }


	nptODU4CurrentESNE	OBJECT-TYPE	
		SYNTAX			Counter64
		MAX-ACCESS		read-only
		STATUS			current
		DESCRIPTION		"Errored second Near end 1-second period which contains at least one errored blocks or at least one defect"
		::=  {  nptODU4CurrentEntry  4  }


	nptODU4CurrentSESNE	OBJECT-TYPE	
		SYNTAX			Counter64
		MAX-ACCESS		read-only
		STATUS			current
		DESCRIPTION		"Severely errored second Near end 1-second period which contains ?Y15% errored blocks or at least one defect"
		::=  {  nptODU4CurrentEntry  5  }


	nptODU4CurrentUASNE	OBJECT-TYPE	
		SYNTAX			Counter64
		MAX-ACCESS		read-only
		STATUS			current
		DESCRIPTION		"Unavailable seconds near end"
		::=  {  nptODU4CurrentEntry  6  }


	nptODU4CurrentBBEFE	OBJECT-TYPE	
		SYNTAX			Counter64
		MAX-ACCESS		read-only
		STATUS			current
		DESCRIPTION		"Background block error Far end An errored block not occurring as part of SES-FE"
		::=  {  nptODU4CurrentEntry  7  }


	nptODU4CurrentESFE	OBJECT-TYPE	
		SYNTAX			Counter64
		MAX-ACCESS		read-only
		STATUS			current
		DESCRIPTION		"Errored second Far end 1-second period which contains at least one errored blocks or at least one defect"
		::=  {  nptODU4CurrentEntry  8  }


	nptODU4CurrentSESFE	OBJECT-TYPE	
		SYNTAX			Counter64
		MAX-ACCESS		read-only
		STATUS			current
		DESCRIPTION		"Severely errored second Far end 1-second period which contains ?Y15% errored blocks or at least one defect"
		::=  {  nptODU4CurrentEntry  9  }


	nptODU4CurrentUASFE	OBJECT-TYPE	
		SYNTAX			Counter64
		MAX-ACCESS		read-only
		STATUS			current
		DESCRIPTION		"Unavailable second far end"
		::=  {  nptODU4CurrentEntry  10  }
		
		
	nptODU4CurrentTSE	OBJECT-TYPE	
		SYNTAX			Counter64
		MAX-ACCESS		read-only
		STATUS			current
		DESCRIPTION		"Test Sequence Error. Counts the number of invalid test pattern"
		::=  {  nptODU4CurrentEntry  11  }

    nptODU4TotalTable	OBJECT-TYPE
		SYNTAX		SEQUENCE  OF  NptODU4TotalEntry
		MAX-ACCESS	not-accessible
		STATUS		current
		DESCRIPTION	"The ODU4 current table contains various statistics
            being collected for the current 15 minute
            interval."
		::=  { nptODU4Port  2 }

	nptODU4TotalEntry	OBJECT-TYPE
		SYNTAX		NptODU4TotalEntry
		MAX-ACCESS	not-accessible
		STATUS		current
		DESCRIPTION	"An entry in the ODU4 Total table."
		INDEX		{  nptODU4TotalIndex  }
		::=  { nptODU4TotalTable 1 }

	NptODU4TotalEntry  ::=  SEQUENCE {
		nptODU4TotalIndex  Integer32,
		nptODU4TotalMoDescription  DisplayString,
		nptODU4TotalBBENE  Counter64,
		nptODU4TotalESNE Counter64,
		nptODU4TotalSESNE  Counter64,
		nptODU4TotalUASNE  Counter64,
		nptODU4TotalBBEFE  Counter64,
		nptODU4TotalESFE  Counter64,
		nptODU4TotalSESFE  Counter64,
		nptODU4TotalUASFE  Counter64,
		nptODU4TotalTSE  Counter64
		}


	nptODU4TotalIndex	OBJECT-TYPE	
		SYNTAX			Integer32  ( -2147483648 .. 2147483647  ) 
		MAX-ACCESS		read-only
		STATUS			current
		DESCRIPTION		"The index value which uniquely identifies  the
            ODU4 interface to which this entry is applicable."
		::=  {  nptODU4TotalEntry  1  }
		
	nptODU4TotalMoDescription	OBJECT-TYPE	
		SYNTAX			DisplayString 
		MAX-ACCESS		read-only
		STATUS			current
		DESCRIPTION		"Mo Description"
		::=  {  nptODU4TotalEntry  2  }


	nptODU4TotalBBENE	OBJECT-TYPE	
		SYNTAX			Counter64
		MAX-ACCESS		read-only
		STATUS			current
		DESCRIPTION		"Background block error Near end An errored block not occurring as part of SES"
		::=  {  nptODU4TotalEntry  3  }


	nptODU4TotalESNE	OBJECT-TYPE	
		SYNTAX			Counter64
		MAX-ACCESS		read-only
		STATUS			current
		DESCRIPTION		"Errored second Near end 1-second period which contains at least one errored blocks or at least one defect"
		::=  {  nptODU4TotalEntry  4  }


	nptODU4TotalSESNE	OBJECT-TYPE	
		SYNTAX			Counter64
		MAX-ACCESS		read-only
		STATUS			current
		DESCRIPTION		"Severely errored second Near end 1-second period which contains ?Y15% errored blocks or at least one defect"
		::=  {  nptODU4TotalEntry  5  }


	nptODU4TotalUASNE	OBJECT-TYPE	
		SYNTAX			Counter64
		MAX-ACCESS		read-only
		STATUS			current
		DESCRIPTION		"Unavailable seconds near end"
		::=  {  nptODU4TotalEntry  6  }


	nptODU4TotalBBEFE	OBJECT-TYPE	
		SYNTAX			Counter64
		MAX-ACCESS		read-only
		STATUS			current
		DESCRIPTION		"Background block error Far end An errored block not occurring as part of SES-FE"
		::=  {  nptODU4TotalEntry  7  }


	nptODU4TotalESFE	OBJECT-TYPE	
		SYNTAX			Counter64
		MAX-ACCESS		read-only
		STATUS			current
		DESCRIPTION		"Errored second Far end 1-second period which contains at least one errored blocks or at least one defect"
		::=  {  nptODU4TotalEntry  8  }


	nptODU4TotalSESFE	OBJECT-TYPE	
		SYNTAX			Counter64
		MAX-ACCESS		read-only
		STATUS			current
		DESCRIPTION		"Severely errored second Far end 1-second period which contains ?Y15% errored blocks or at least one defect"
		::=  {  nptODU4TotalEntry  9  }


	nptODU4TotalUASFE	OBJECT-TYPE	
		SYNTAX			Counter64
		MAX-ACCESS		read-only
		STATUS			current
		DESCRIPTION		"Unavailable second far end"
		::=  {  nptODU4TotalEntry  10  }
		
		
	nptODU4TotalTSE	OBJECT-TYPE	
		SYNTAX			Counter64
		MAX-ACCESS		read-only
		STATUS			current
		DESCRIPTION		"Test Sequence Error. Counts the number of invalid test pattern"
		::=  {  nptODU4TotalEntry  11  }
		
	nptOTU2CurrentTable	OBJECT-TYPE
		SYNTAX		SEQUENCE  OF  NptOTU2CurrentEntry
		MAX-ACCESS	not-accessible
		STATUS		current
		DESCRIPTION	"The OTU2 current table contains various statistics
            being collected for the current 15 minute
            interval."
		::=  { nptOTU2Port  1 }

	nptOTU2CurrentEntry	OBJECT-TYPE
		SYNTAX		NptOTU2CurrentEntry
		MAX-ACCESS	not-accessible
		STATUS		current
		DESCRIPTION	"An entry in the OTU2 Current table."
		INDEX		{  nptOTU2CurrentIndex  }
		::=  { nptOTU2CurrentTable 1 }

	NptOTU2CurrentEntry  ::=  SEQUENCE {
		nptOTU2CurrentIndex  Integer32,
		nptOTU2CurrentMoDescription  DisplayString,
		nptOTU2CurrentFECCE  Counter64,
		nptOTU2CurrentBBENE Counter64,
		nptOTU2CurrentESNE  Counter64,
		nptOTU2CurrentSESNE  Counter64,
		nptOTU2CurrentUASNE  Counter64,
		nptOTU2CurrentOFS  Counter64,
		nptOTU2CurrentBBEFE  Counter64,
		nptOTU2CurrentESFE  Counter64,
		nptOTU2CurrentSESFE  Counter64,
		nptOTU2CurrentUASFE  Counter64,
        nptOTU2CurrentPREFECBER  DisplayString,
        nptOTU2CurrentDGDMax  DisplayString,
        nptOTU2CurrentDGDMin  DisplayString,
        nptOTU2CurrentCDMax   DisplayString,
        nptOTU2CurrentCDMin   DisplayString
		}


	nptOTU2CurrentIndex	OBJECT-TYPE	
		SYNTAX			Integer32  ( -2147483648 .. 2147483647  ) 
		MAX-ACCESS		read-only
		STATUS			current
		DESCRIPTION		"The index value which uniquely identifies  the
            OTU2 interface to which this entry is applicable."
		::=  {  nptOTU2CurrentEntry  1  }
		
	nptOTU2CurrentMoDescription	OBJECT-TYPE	
		SYNTAX			DisplayString 
		MAX-ACCESS		read-only
		STATUS			current
		DESCRIPTION		"Mo Description"
		::=  {  nptOTU2CurrentEntry  2  }


	nptOTU2CurrentFECCE	OBJECT-TYPE	
		SYNTAX			Counter64
		MAX-ACCESS		read-only
		STATUS			current
		DESCRIPTION		"FEC corrected errors;"
		::=  {  nptOTU2CurrentEntry  3  }


	nptOTU2CurrentBBENE	OBJECT-TYPE	
		SYNTAX			Counter64
		MAX-ACCESS		read-only
		STATUS			current
		DESCRIPTION		"Background block error Near end An errored block not occurring as part of SES"
		::=  {  nptOTU2CurrentEntry  4  }


	nptOTU2CurrentESNE	OBJECT-TYPE	
		SYNTAX			Counter64
		MAX-ACCESS		read-only
		STATUS			current
		DESCRIPTION		"Errored second Near end 1-second period which contains at least one errored blocks or at least one defect"
		::=  {  nptOTU2CurrentEntry  5  }


	nptOTU2CurrentSESNE	OBJECT-TYPE	
		SYNTAX			Counter64
		MAX-ACCESS		read-only
		STATUS			current
		DESCRIPTION		"Severely errored second Near end 1-second period which contains ?Y15% errored blocks or at least one defect;"
		::=  {  nptOTU2CurrentEntry  6  }


	nptOTU2CurrentUASNE	OBJECT-TYPE	
		SYNTAX			Counter64
		MAX-ACCESS		read-only
		STATUS			current
		DESCRIPTION		"Unavailable seconds near end"
		::=  {  nptOTU2CurrentEntry  7  }


	nptOTU2CurrentOFS	OBJECT-TYPE	
		SYNTAX			Counter64
		MAX-ACCESS		read-only
		STATUS			current
		DESCRIPTION		"Out-frame seconds The counter shall be increased if at least one Out Of Frame defect occurred during a second."
		::=  {  nptOTU2CurrentEntry  8  }


	nptOTU2CurrentBBEFE	OBJECT-TYPE	
		SYNTAX			Counter64
		MAX-ACCESS		read-only
		STATUS			current
		DESCRIPTION		"Background block error Far end An errored block not occurring as part of SES-FE"
		::=  {  nptOTU2CurrentEntry  9  }


	nptOTU2CurrentESFE	OBJECT-TYPE	
		SYNTAX			Counter64
		MAX-ACCESS		read-only
		STATUS			current
		DESCRIPTION		"Errored second Far end 1-second period which contains at least one errored blocks or at least one defect"
		::=  {  nptOTU2CurrentEntry  10  }
		
		
	nptOTU2CurrentSESFE	OBJECT-TYPE	
		SYNTAX			Counter64
		MAX-ACCESS		read-only
		STATUS			current
		DESCRIPTION		"Severely errored second Far end 1-second period which contains ?Y15% errored blocks or at least one defect."
		::=  {  nptOTU2CurrentEntry  11  }

    nptOTU2CurrentUASFE	OBJECT-TYPE	
		SYNTAX			Counter64
		MAX-ACCESS		read-only
		STATUS			current
		DESCRIPTION		"Unavailable second far end"
		::=  {  nptOTU2CurrentEntry  12  }
        
    nptOTU2CurrentPREFECBER	OBJECT-TYPE	
		SYNTAX			DisplayString
		MAX-ACCESS		read-only
		STATUS			current
		DESCRIPTION		" Pre-FEC BER is a function of Corrected Errors (CE), Bit Rate (BR) and collection time (t).The function is defined as PreFEC BER=CE/(BR x t) "
		::=  {  nptOTU2CurrentEntry  13  }
        
    nptOTU2CurrentDGDMax	OBJECT-TYPE	
		SYNTAX			DisplayString
		MAX-ACCESS		read-only
		STATUS			current
		DESCRIPTION		"Differential Group Delay Maximum value"
		::=  {  nptOTU2CurrentEntry  14  }

    nptOTU2CurrentDGDMin	OBJECT-TYPE	
		SYNTAX			DisplayString
		MAX-ACCESS		read-only
		STATUS			current
		DESCRIPTION		"Differential Group Delay Minimum value"
		::=  {  nptOTU2CurrentEntry  15  }

    nptOTU2CurrentCDMax	OBJECT-TYPE	
		SYNTAX			DisplayString
		MAX-ACCESS		read-only
		STATUS			current
		DESCRIPTION		"Chromatic Dispersion Maximum value"
		::=  {  nptOTU2CurrentEntry  16  }

    nptOTU2CurrentCDMin	OBJECT-TYPE	
		SYNTAX			DisplayString
		MAX-ACCESS		read-only
		STATUS			current
		DESCRIPTION		"Chromatic Dispersion Minimum value"
		::=  {  nptOTU2CurrentEntry  17  }        

    nptOTU2TotalTable	OBJECT-TYPE
		SYNTAX		SEQUENCE  OF  NptOTU2TotalEntry
		MAX-ACCESS	not-accessible
		STATUS		current
		DESCRIPTION	"The OTU2 current table contains various statistics
            being collected for the current 15 minute
            interval."
		::=  { nptOTU2Port  2 }

	nptOTU2TotalEntry	OBJECT-TYPE
		SYNTAX		NptOTU2TotalEntry
		MAX-ACCESS	not-accessible
		STATUS		current
		DESCRIPTION	"An entry in the OTU2 Total table."
		INDEX		{  nptOTU2TotalIndex  }
		::=  { nptOTU2TotalTable 1 }

	NptOTU2TotalEntry  ::=  SEQUENCE {
		nptOTU2TotalIndex  Integer32,
		nptOTU2TotalMoDescription  DisplayString,
		nptOTU2TotalFECCE  Counter64,
		nptOTU2TotalBBENE Counter64,
		nptOTU2TotalESNE  Counter64,
		nptOTU2TotalSESNE  Counter64,
		nptOTU2TotalUASNE  Counter64,
		nptOTU2TotalOFS  Counter64,
		nptOTU2TotalBBEFE  Counter64,
		nptOTU2TotalESFE  Counter64,
		nptOTU2TotalSESFE  Counter64,
		nptOTU2TotalUASFE  Counter64,
        nptOTU2TotalPREFECBER  DisplayString,
        nptOTU2TotalDGDMax  DisplayString,
        nptOTU2TotalDGDMin  DisplayString,
        nptOTU2TotalCDMax   DisplayString,
        nptOTU2TotalCDMin   DisplayString
		}


	nptOTU2TotalIndex	OBJECT-TYPE	
		SYNTAX			Integer32  ( -2147483648 .. 2147483647  ) 
		MAX-ACCESS		read-only
		STATUS			current
		DESCRIPTION		"The index value which uniquely identifies  the
            OTU2 interface to which this entry is applicable."
		::=  {  nptOTU2TotalEntry  1  }
		
	nptOTU2TotalMoDescription	OBJECT-TYPE	
		SYNTAX			DisplayString 
		MAX-ACCESS		read-only
		STATUS			current
		DESCRIPTION		"Mo Description"
		::=  {  nptOTU2TotalEntry  2  }


	nptOTU2TotalFECCE	OBJECT-TYPE	
		SYNTAX			Counter64
		MAX-ACCESS		read-only
		STATUS			current
		DESCRIPTION		"FEC corrected errors;"
		::=  {  nptOTU2TotalEntry  3  }


	nptOTU2TotalBBENE	OBJECT-TYPE	
		SYNTAX			Counter64
		MAX-ACCESS		read-only
		STATUS			current
		DESCRIPTION		"Background block error Near end An errored block not occurring as part of SES"
		::=  {  nptOTU2TotalEntry  4  }


	nptOTU2TotalESNE	OBJECT-TYPE	
		SYNTAX			Counter64
		MAX-ACCESS		read-only
		STATUS			current
		DESCRIPTION		"Errored second Near end 1-second period which contains at least one errored blocks or at least one defect"
		::=  {  nptOTU2TotalEntry  5  }


	nptOTU2TotalSESNE	OBJECT-TYPE	
		SYNTAX			Counter64
		MAX-ACCESS		read-only
		STATUS			current
		DESCRIPTION		"Severely errored second Near end 1-second period which contains ?Y15% errored blocks or at least one defect;"
		::=  {  nptOTU2TotalEntry  6  }


	nptOTU2TotalUASNE	OBJECT-TYPE	
		SYNTAX			Counter64
		MAX-ACCESS		read-only
		STATUS			current
		DESCRIPTION		"Unavailable seconds near end"
		::=  {  nptOTU2TotalEntry  7  }


	nptOTU2TotalOFS	OBJECT-TYPE	
		SYNTAX			Counter64
		MAX-ACCESS		read-only
		STATUS			current
		DESCRIPTION		"Out-frame seconds The counter shall be increased if at least one Out Of Frame defect occurred during a second."
		::=  {  nptOTU2TotalEntry  8  }


	nptOTU2TotalBBEFE	OBJECT-TYPE	
		SYNTAX			Counter64
		MAX-ACCESS		read-only
		STATUS			current
		DESCRIPTION		"Background block error Far end An errored block not occurring as part of SES-FE"
		::=  {  nptOTU2TotalEntry  9  }


	nptOTU2TotalESFE	OBJECT-TYPE	
		SYNTAX			Counter64
		MAX-ACCESS		read-only
		STATUS			current
		DESCRIPTION		"Errored second Far end 1-second period which contains at least one errored blocks or at least one defect"
		::=  {  nptOTU2TotalEntry  10  }
				
	nptOTU2TotalSESFE	OBJECT-TYPE	
		SYNTAX			Counter64
		MAX-ACCESS		read-only
		STATUS			current
		DESCRIPTION		"Severely errored second Far end 1-second period which contains ?Y15% errored blocks or at least one defect."
		::=  {  nptOTU2TotalEntry  11  }

    nptOTU2TotalUASFE	OBJECT-TYPE	
		SYNTAX			Counter64
		MAX-ACCESS		read-only
		STATUS			current
		DESCRIPTION		"Unavailable second far end"
		::=  {  nptOTU2TotalEntry  12  }

    nptOTU2TotalPREFECBER	OBJECT-TYPE	
		SYNTAX			DisplayString
		MAX-ACCESS		read-only
		STATUS			current
		DESCRIPTION		" Pre-FEC BER is a function of Corrected Errors (CE), Bit Rate (BR) and collection time (t).The function is defined as PreFEC BER=CE/(BR x t) "
		::=  {  nptOTU2TotalEntry  13  }
        
    nptOTU2TotalDGDMax	OBJECT-TYPE	
		SYNTAX			DisplayString
		MAX-ACCESS		read-only
		STATUS			current
		DESCRIPTION		"Differential Group Delay Maximum value"
		::=  {  nptOTU2TotalEntry  14  }

    nptOTU2TotalDGDMin	OBJECT-TYPE	
		SYNTAX			DisplayString
		MAX-ACCESS		read-only
		STATUS			current
		DESCRIPTION		"Differential Group Delay Minimum value"
		::=  {  nptOTU2TotalEntry  15  }

    nptOTU2TotalCDMax	OBJECT-TYPE	
		SYNTAX			DisplayString
		MAX-ACCESS		read-only
		STATUS			current
		DESCRIPTION		"Chromatic Dispersion Maximum value"
		::=  {  nptOTU2TotalEntry  16  }

    nptOTU2TotalCDMin	OBJECT-TYPE	
		SYNTAX			DisplayString
		MAX-ACCESS		read-only
		STATUS			current
		DESCRIPTION		"Chromatic Dispersion Minimum value"
		::=  {  nptOTU2TotalEntry  17  }    
		
	nptOTU2eCurrentTable	OBJECT-TYPE
		SYNTAX		SEQUENCE  OF  NptOTU2eCurrentEntry
		MAX-ACCESS	not-accessible
		STATUS		current
		DESCRIPTION	"The OTU2e current table contains various statistics
            being collected for the current 15 minute
            interval."
		::=  { nptOTU2ePort  1 }

	nptOTU2eCurrentEntry	OBJECT-TYPE
		SYNTAX		NptOTU2eCurrentEntry
		MAX-ACCESS	not-accessible
		STATUS		current
		DESCRIPTION	"An entry in the OTU2e Current table."
		INDEX		{  nptOTU2eCurrentIndex  }
		::=  { nptOTU2eCurrentTable 1 }

	NptOTU2eCurrentEntry  ::=  SEQUENCE {
		nptOTU2eCurrentIndex  Integer32,
		nptOTU2eCurrentMoDescription  DisplayString,
		nptOTU2eCurrentFECCE  Counter64,
		nptOTU2eCurrentBBENE Counter64,
		nptOTU2eCurrentESNE  Counter64,
		nptOTU2eCurrentSESNE  Counter64,
		nptOTU2eCurrentUASNE  Counter64,
		nptOTU2eCurrentOFS  Counter64,
		nptOTU2eCurrentBBEFE  Counter64,
		nptOTU2eCurrentESFE  Counter64,
		nptOTU2eCurrentSESFE  Counter64,
		nptOTU2eCurrentUASFE  Counter64,
        nptOTU2eCurrentPREFECBER  DisplayString,
        nptOTU2eCurrentDGDMax  DisplayString,
        nptOTU2eCurrentDGDMin  DisplayString,
        nptOTU2eCurrentCDMax   DisplayString,
        nptOTU2eCurrentCDMin   DisplayString
		}


	nptOTU2eCurrentIndex	OBJECT-TYPE	
		SYNTAX			Integer32  ( -2147483648 .. 2147483647  ) 
		MAX-ACCESS		read-only
		STATUS			current
		DESCRIPTION		"The index value which uniquely identifies  the
            OTU2e interface to which this entry is applicable."
		::=  {  nptOTU2eCurrentEntry  1  }
		
	nptOTU2eCurrentMoDescription	OBJECT-TYPE	
		SYNTAX			DisplayString 
		MAX-ACCESS		read-only
		STATUS			current
		DESCRIPTION		"Mo Description"
		::=  {  nptOTU2eCurrentEntry  2  }


	nptOTU2eCurrentFECCE	OBJECT-TYPE	
		SYNTAX			Counter64
		MAX-ACCESS		read-only
		STATUS			current
		DESCRIPTION		"FEC corrected errors;"
		::=  {  nptOTU2eCurrentEntry  3  }


	nptOTU2eCurrentBBENE	OBJECT-TYPE	
		SYNTAX			Counter64
		MAX-ACCESS		read-only
		STATUS			current
		DESCRIPTION		"Background block error Near end An errored block not occurring as part of SES"
		::=  {  nptOTU2eCurrentEntry  4  }


	nptOTU2eCurrentESNE	OBJECT-TYPE	
		SYNTAX			Counter64
		MAX-ACCESS		read-only
		STATUS			current
		DESCRIPTION		"Errored second Near end 1-second period which contains at least one errored blocks or at least one defect"
		::=  {  nptOTU2eCurrentEntry  5  }


	nptOTU2eCurrentSESNE	OBJECT-TYPE	
		SYNTAX			Counter64
		MAX-ACCESS		read-only
		STATUS			current
		DESCRIPTION		"Severely errored second Near end 1-second period which contains ?Y15% errored blocks or at least one defect;"
		::=  {  nptOTU2eCurrentEntry  6  }


	nptOTU2eCurrentUASNE	OBJECT-TYPE	
		SYNTAX			Counter64
		MAX-ACCESS		read-only
		STATUS			current
		DESCRIPTION		"Unavailable seconds near end"
		::=  {  nptOTU2eCurrentEntry  7  }


	nptOTU2eCurrentOFS	OBJECT-TYPE	
		SYNTAX			Counter64
		MAX-ACCESS		read-only
		STATUS			current
		DESCRIPTION		"Out-frame seconds The counter shall be increased if at least one Out Of Frame defect occurred during a second."
		::=  {  nptOTU2eCurrentEntry  8  }


	nptOTU2eCurrentBBEFE	OBJECT-TYPE	
		SYNTAX			Counter64
		MAX-ACCESS		read-only
		STATUS			current
		DESCRIPTION		"Background block error Far end An errored block not occurring as part of SES-FE"
		::=  {  nptOTU2eCurrentEntry  9  }


	nptOTU2eCurrentESFE	OBJECT-TYPE	
		SYNTAX			Counter64
		MAX-ACCESS		read-only
		STATUS			current
		DESCRIPTION		"Errored second Far end 1-second period which contains at least one errored blocks or at least one defect"
		::=  {  nptOTU2eCurrentEntry  10  }
		
		
	nptOTU2eCurrentSESFE	OBJECT-TYPE	
		SYNTAX			Counter64
		MAX-ACCESS		read-only
		STATUS			current
		DESCRIPTION		"Severely errored second Far end 1-second period which contains ?Y15% errored blocks or at least one defect."
		::=  {  nptOTU2eCurrentEntry  11  }

    nptOTU2eCurrentUASFE	OBJECT-TYPE	
		SYNTAX			Counter64
		MAX-ACCESS		read-only
		STATUS			current
		DESCRIPTION		"Unavailable second far end"
		::=  {  nptOTU2eCurrentEntry  12  }
        
    nptOTU2eCurrentPREFECBER	OBJECT-TYPE	
		SYNTAX			DisplayString
		MAX-ACCESS		read-only
		STATUS			current
		DESCRIPTION		" Pre-FEC BER is a function of Corrected Errors (CE), Bit Rate (BR) and collection time (t).The function is defined as PreFEC BER=CE/(BR x t) "
		::=  {  nptOTU2eCurrentEntry  13  }
        
    nptOTU2eCurrentDGDMax	OBJECT-TYPE	
		SYNTAX			DisplayString
		MAX-ACCESS		read-only
		STATUS			current
		DESCRIPTION		"Differential Group Delay Maximum value"
		::=  {  nptOTU2eCurrentEntry  14  }

    nptOTU2eCurrentDGDMin	OBJECT-TYPE	
		SYNTAX			DisplayString
		MAX-ACCESS		read-only
		STATUS			current
		DESCRIPTION		"Differential Group Delay Minimum value"
		::=  {  nptOTU2eCurrentEntry  15  }

    nptOTU2eCurrentCDMax	OBJECT-TYPE	
		SYNTAX			DisplayString
		MAX-ACCESS		read-only
		STATUS			current
		DESCRIPTION		"Chromatic Dispersion Maximum value"
		::=  {  nptOTU2eCurrentEntry  16  }

    nptOTU2eCurrentCDMin	OBJECT-TYPE	
		SYNTAX			DisplayString
		MAX-ACCESS		read-only
		STATUS			current
		DESCRIPTION		"Chromatic Dispersion Minimum value"
		::=  {  nptOTU2eCurrentEntry  17  }  
        
    nptOTU2eTotalTable	OBJECT-TYPE
		SYNTAX		SEQUENCE  OF  NptOTU2eTotalEntry
		MAX-ACCESS	not-accessible
		STATUS		current
		DESCRIPTION	"The OTU2e current table contains various statistics
            being collected for the current 15 minute
            interval."
		::=  { nptOTU2ePort  2 }

	nptOTU2eTotalEntry	OBJECT-TYPE
		SYNTAX		NptOTU2eTotalEntry
		MAX-ACCESS	not-accessible
		STATUS		current
		DESCRIPTION	"An entry in the OTU2e Total table."
		INDEX		{  nptOTU2eTotalIndex  }
		::=  { nptOTU2eTotalTable 1 }

	NptOTU2eTotalEntry  ::=  SEQUENCE {
		nptOTU2eTotalIndex  Integer32,
		nptOTU2eTotalMoDescription  DisplayString,
		nptOTU2eTotalFECCE  Counter64,
		nptOTU2eTotalBBENE Counter64,
		nptOTU2eTotalESNE  Counter64,
		nptOTU2eTotalSESNE  Counter64,
		nptOTU2eTotalUASNE  Counter64,
		nptOTU2eTotalOFS  Counter64,
		nptOTU2eTotalBBEFE  Counter64,
		nptOTU2eTotalESFE  Counter64,
		nptOTU2eTotalSESFE  Counter64,
		nptOTU2eTotalUASFE  Counter64,
        nptOTU2eTotalPREFECBER  DisplayString,
        nptOTU2eTotalDGDMax  DisplayString,
        nptOTU2eTotalDGDMin  DisplayString,
        nptOTU2eTotalCDMax   DisplayString,
        nptOTU2eTotalCDMin   DisplayString
		}


	nptOTU2eTotalIndex	OBJECT-TYPE	
		SYNTAX			Integer32  ( -2147483648 .. 2147483647  ) 
		MAX-ACCESS		read-only
		STATUS			current
		DESCRIPTION		"The index value which uniquely identifies  the
            OTU2e interface to which this entry is applicable."
		::=  {  nptOTU2eTotalEntry  1  }
		
	nptOTU2eTotalMoDescription	OBJECT-TYPE	
		SYNTAX			DisplayString 
		MAX-ACCESS		read-only
		STATUS			current
		DESCRIPTION		"Mo Description"
		::=  {  nptOTU2eTotalEntry  2  }


	nptOTU2eTotalFECCE	OBJECT-TYPE	
		SYNTAX			Counter64
		MAX-ACCESS		read-only
		STATUS			current
		DESCRIPTION		"FEC corrected errors;"
		::=  {  nptOTU2eTotalEntry  3  }


	nptOTU2eTotalBBENE	OBJECT-TYPE	
		SYNTAX			Counter64
		MAX-ACCESS		read-only
		STATUS			current
		DESCRIPTION		"Background block error Near end An errored block not occurring as part of SES"
		::=  {  nptOTU2eTotalEntry  4  }


	nptOTU2eTotalESNE	OBJECT-TYPE	
		SYNTAX			Counter64
		MAX-ACCESS		read-only
		STATUS			current
		DESCRIPTION		"Errored second Near end 1-second period which contains at least one errored blocks or at least one defect"
		::=  {  nptOTU2eTotalEntry  5  }


	nptOTU2eTotalSESNE	OBJECT-TYPE	
		SYNTAX			Counter64
		MAX-ACCESS		read-only
		STATUS			current
		DESCRIPTION		"Severely errored second Near end 1-second period which contains ?Y15% errored blocks or at least one defect;"
		::=  {  nptOTU2eTotalEntry  6  }


	nptOTU2eTotalUASNE	OBJECT-TYPE	
		SYNTAX			Counter64
		MAX-ACCESS		read-only
		STATUS			current
		DESCRIPTION		"Unavailable seconds near end"
		::=  {  nptOTU2eTotalEntry  7  }


	nptOTU2eTotalOFS	OBJECT-TYPE	
		SYNTAX			Counter64
		MAX-ACCESS		read-only
		STATUS			current
		DESCRIPTION		"Out-frame seconds The counter shall be increased if at least one Out Of Frame defect occurred during a second."
		::=  {  nptOTU2eTotalEntry  8  }


	nptOTU2eTotalBBEFE	OBJECT-TYPE	
		SYNTAX			Counter64
		MAX-ACCESS		read-only
		STATUS			current
		DESCRIPTION		"Background block error Far end An errored block not occurring as part of SES-FE"
		::=  {  nptOTU2eTotalEntry  9  }


	nptOTU2eTotalESFE	OBJECT-TYPE	
		SYNTAX			Counter64
		MAX-ACCESS		read-only
		STATUS			current
		DESCRIPTION		"Errored second Far end 1-second period which contains at least one errored blocks or at least one defect"
		::=  {  nptOTU2eTotalEntry  10  }
		
		
	nptOTU2eTotalSESFE	OBJECT-TYPE	
		SYNTAX			Counter64
		MAX-ACCESS		read-only
		STATUS			current
		DESCRIPTION		"Severely errored second Far end 1-second period which contains ?Y15% errored blocks or at least one defect."
		::=  {  nptOTU2eTotalEntry  11  }

    nptOTU2eTotalUASFE	OBJECT-TYPE	
		SYNTAX			Counter64
		MAX-ACCESS		read-only
		STATUS			current
		DESCRIPTION		"Unavailable second far end"
		::=  {  nptOTU2eTotalEntry  12  }
        
    nptOTU2eTotalPREFECBER	OBJECT-TYPE	
		SYNTAX			DisplayString
		MAX-ACCESS		read-only
		STATUS			current
		DESCRIPTION		" Pre-FEC BER is a function of Corrected Errors (CE), Bit Rate (BR) and collection time (t).The function is defined as PreFEC BER=CE/(BR x t) "
		::=  {  nptOTU2eTotalEntry  13  }
        
    nptOTU2eTotalDGDMax	OBJECT-TYPE	
		SYNTAX			DisplayString
		MAX-ACCESS		read-only
		STATUS			current
		DESCRIPTION		"Differential Group Delay Maximum value"
		::=  {  nptOTU2eTotalEntry  14  }

    nptOTU2eTotalDGDMin	OBJECT-TYPE	
		SYNTAX			DisplayString
		MAX-ACCESS		read-only
		STATUS			current
		DESCRIPTION		"Differential Group Delay Minimum value"
		::=  {  nptOTU2eTotalEntry  15  }

    nptOTU2eTotalCDMax	OBJECT-TYPE	
		SYNTAX			DisplayString
		MAX-ACCESS		read-only
		STATUS			current
		DESCRIPTION		"Chromatic Dispersion Maximum value"
		::=  {  nptOTU2eTotalEntry  16  }

    nptOTU2eTotalCDMin	OBJECT-TYPE	
		SYNTAX			DisplayString
		MAX-ACCESS		read-only
		STATUS			current
		DESCRIPTION		"Chromatic Dispersion Minimum value"
		::=  {  nptOTU2eTotalEntry  17  }          
		
	nptOTU4CurrentTable	OBJECT-TYPE
		SYNTAX		SEQUENCE  OF  NptOTU4CurrentEntry
		MAX-ACCESS	not-accessible
		STATUS		current
		DESCRIPTION	"The OTU4 current table contains various statistics
            being collected for the current 15 minute
            interval."
		::=  { nptOTU4Port  1 }

	nptOTU4CurrentEntry	OBJECT-TYPE
		SYNTAX		NptOTU4CurrentEntry
		MAX-ACCESS	not-accessible
		STATUS		current
		DESCRIPTION	"An entry in the OTU4 Current table."
		INDEX		{  nptOTU4CurrentIndex  }
		::=  { nptOTU4CurrentTable 1 }

	NptOTU4CurrentEntry  ::=  SEQUENCE {
		nptOTU4CurrentIndex  Integer32,
		nptOTU4CurrentMoDescription  DisplayString,
		nptOTU4CurrentFECCE  Counter64,
		nptOTU4CurrentBBENE Counter64,
		nptOTU4CurrentESNE  Counter64,
		nptOTU4CurrentSESNE  Counter64,
		nptOTU4CurrentUASNE  Counter64,
		nptOTU4CurrentOFS  Counter64,
		nptOTU4CurrentBBEFE  Counter64,
		nptOTU4CurrentESFE  Counter64,
		nptOTU4CurrentSESFE  Counter64,
		nptOTU4CurrentUASFE  Counter64,
        nptOTU4CurrentPREFECBER  DisplayString,
        nptOTU4CurrentDGDMax  DisplayString,
        nptOTU4CurrentDGDMin  DisplayString,
        nptOTU4CurrentCDMax   DisplayString,
        nptOTU4CurrentCDMin   DisplayString
		}


	nptOTU4CurrentIndex	OBJECT-TYPE	
		SYNTAX			Integer32  ( -2147483648 .. 2147483647  ) 
		MAX-ACCESS		read-only
		STATUS			current
		DESCRIPTION		"The index value which uniquely identifies  the
            OTU4 interface to which this entry is applicable."
		::=  {  nptOTU4CurrentEntry  1  }
		
	nptOTU4CurrentMoDescription	OBJECT-TYPE	
		SYNTAX			DisplayString 
		MAX-ACCESS		read-only
		STATUS			current
		DESCRIPTION		"Mo Description"
		::=  {  nptOTU4CurrentEntry  2  }


	nptOTU4CurrentFECCE	OBJECT-TYPE	
		SYNTAX			Counter64
		MAX-ACCESS		read-only
		STATUS			current
		DESCRIPTION		"FEC corrected errors;"
		::=  {  nptOTU4CurrentEntry  3  }


	nptOTU4CurrentBBENE	OBJECT-TYPE	
		SYNTAX			Counter64
		MAX-ACCESS		read-only
		STATUS			current
		DESCRIPTION		"Background block error Near end An errored block not occurring as part of SES"
		::=  {  nptOTU4CurrentEntry  4  }


	nptOTU4CurrentESNE	OBJECT-TYPE	
		SYNTAX			Counter64
		MAX-ACCESS		read-only
		STATUS			current
		DESCRIPTION		"Errored second Near end 1-second period which contains at least one errored blocks or at least one defect"
		::=  {  nptOTU4CurrentEntry  5  }


	nptOTU4CurrentSESNE	OBJECT-TYPE	
		SYNTAX			Counter64
		MAX-ACCESS		read-only
		STATUS			current
		DESCRIPTION		"Severely errored second Near end 1-second period which contains ?Y15% errored blocks or at least one defect;"
		::=  {  nptOTU4CurrentEntry  6  }


	nptOTU4CurrentUASNE	OBJECT-TYPE	
		SYNTAX			Counter64
		MAX-ACCESS		read-only
		STATUS			current
		DESCRIPTION		"Unavailable seconds near end"
		::=  {  nptOTU4CurrentEntry  7  }


	nptOTU4CurrentOFS	OBJECT-TYPE	
		SYNTAX			Counter64
		MAX-ACCESS		read-only
		STATUS			current
		DESCRIPTION		"Out-frame seconds The counter shall be increased if at least one Out Of Frame defect occurred during a second."
		::=  {  nptOTU4CurrentEntry  8  }


	nptOTU4CurrentBBEFE	OBJECT-TYPE	
		SYNTAX			Counter64
		MAX-ACCESS		read-only
		STATUS			current
		DESCRIPTION		"Background block error Far end An errored block not occurring as part of SES-FE"
		::=  {  nptOTU4CurrentEntry  9  }


	nptOTU4CurrentESFE	OBJECT-TYPE	
		SYNTAX			Counter64
		MAX-ACCESS		read-only
		STATUS			current
		DESCRIPTION		"Errored second Far end 1-second period which contains at least one errored blocks or at least one defect"
		::=  {  nptOTU4CurrentEntry  10  }
		
		
	nptOTU4CurrentSESFE	OBJECT-TYPE	
		SYNTAX			Counter64
		MAX-ACCESS		read-only
		STATUS			current
		DESCRIPTION		"Severely errored second Far end 1-second period which contains ?Y15% errored blocks or at least one defect."
		::=  {  nptOTU4CurrentEntry  11  }

    nptOTU4CurrentUASFE	OBJECT-TYPE	
		SYNTAX			Counter64
		MAX-ACCESS		read-only
		STATUS			current
		DESCRIPTION		"Unavailable second far end"
		::=  {  nptOTU4CurrentEntry  12  }
        
    nptOTU4CurrentPREFECBER	OBJECT-TYPE	
		SYNTAX			DisplayString
		MAX-ACCESS		read-only
		STATUS			current
		DESCRIPTION		" Pre-FEC BER is a function of Corrected Errors (CE), Bit Rate (BR) and collection time (t).The function is defined as PreFEC BER=CE/(BR x t) "
		::=  {  nptOTU4CurrentEntry  13  }
        
    nptOTU4CurrentDGDMax	OBJECT-TYPE	
		SYNTAX			DisplayString
		MAX-ACCESS		read-only
		STATUS			current
		DESCRIPTION		"Differential Group Delay Maximum value"
		::=  {  nptOTU4CurrentEntry  14  }

    nptOTU4CurrentDGDMin	OBJECT-TYPE	
		SYNTAX			DisplayString
		MAX-ACCESS		read-only
		STATUS			current
		DESCRIPTION		"Differential Group Delay Minimum value"
		::=  {  nptOTU4CurrentEntry  15  }

    nptOTU4CurrentCDMax	OBJECT-TYPE	
		SYNTAX			DisplayString
		MAX-ACCESS		read-only
		STATUS			current
		DESCRIPTION		"Chromatic Dispersion Maximum value"
		::=  {  nptOTU4CurrentEntry  16  }

    nptOTU4CurrentCDMin	OBJECT-TYPE	
		SYNTAX			DisplayString
		MAX-ACCESS		read-only
		STATUS			current
		DESCRIPTION		"Chromatic Dispersion Minimum value"
		::=  {  nptOTU4CurrentEntry  17  }          

    nptOTU4TotalTable	OBJECT-TYPE
		SYNTAX		SEQUENCE  OF  NptOTU4TotalEntry
		MAX-ACCESS	not-accessible
		STATUS		current
		DESCRIPTION	"The OTU4 current table contains various statistics
            being collected for the current 15 minute
            interval."
		::=  { nptOTU4Port  2 }

	nptOTU4TotalEntry	OBJECT-TYPE
		SYNTAX		NptOTU4TotalEntry
		MAX-ACCESS	not-accessible
		STATUS		current
		DESCRIPTION	"An entry in the OTU4 Total table."
		INDEX		{  nptOTU4TotalIndex  }
		::=  { nptOTU4TotalTable 1 }

	NptOTU4TotalEntry  ::=  SEQUENCE {
		nptOTU4TotalIndex  Integer32,
		nptOTU4TotalMoDescription  DisplayString,
		nptOTU4TotalFECCE  Counter64,
		nptOTU4TotalBBENE Counter64,
		nptOTU4TotalESNE  Counter64,
		nptOTU4TotalSESNE  Counter64,
		nptOTU4TotalUASNE  Counter64,
		nptOTU4TotalOFS  Counter64,
		nptOTU4TotalBBEFE  Counter64,
		nptOTU4TotalESFE  Counter64,
		nptOTU4TotalSESFE  Counter64,
		nptOTU4TotalUASFE  Counter64,
        nptOTU4TotalPREFECBER  DisplayString,
        nptOTU4TotalDGDMax  DisplayString,
        nptOTU4TotalDGDMin  DisplayString,
        nptOTU4TotalCDMax   DisplayString,
        nptOTU4TotalCDMin   DisplayString
		}


	nptOTU4TotalIndex	OBJECT-TYPE	
		SYNTAX			Integer32  ( -2147483648 .. 2147483647  ) 
		MAX-ACCESS		read-only
		STATUS			current
		DESCRIPTION		"The index value which uniquely identifies  the
            OTU4 interface to which this entry is applicable."
		::=  {  nptOTU4TotalEntry  1  }
		
	nptOTU4TotalMoDescription	OBJECT-TYPE	
		SYNTAX			DisplayString 
		MAX-ACCESS		read-only
		STATUS			current
		DESCRIPTION		"Mo Description"
		::=  {  nptOTU4TotalEntry  2  }


	nptOTU4TotalFECCE	OBJECT-TYPE	
		SYNTAX			Counter64
		MAX-ACCESS		read-only
		STATUS			current
		DESCRIPTION		"FEC corrected errors;"
		::=  {  nptOTU4TotalEntry  3  }


	nptOTU4TotalBBENE	OBJECT-TYPE	
		SYNTAX			Counter64
		MAX-ACCESS		read-only
		STATUS			current
		DESCRIPTION		"Background block error Near end An errored block not occurring as part of SES"
		::=  {  nptOTU4TotalEntry  4  }


	nptOTU4TotalESNE	OBJECT-TYPE	
		SYNTAX			Counter64
		MAX-ACCESS		read-only
		STATUS			current
		DESCRIPTION		"Errored second Near end 1-second period which contains at least one errored blocks or at least one defect"
		::=  {  nptOTU4TotalEntry  5  }


	nptOTU4TotalSESNE	OBJECT-TYPE	
		SYNTAX			Counter64
		MAX-ACCESS		read-only
		STATUS			current
		DESCRIPTION		"Severely errored second Near end 1-second period which contains ?Y15% errored blocks or at least one defect;"
		::=  {  nptOTU4TotalEntry  6  }


	nptOTU4TotalUASNE	OBJECT-TYPE	
		SYNTAX			Counter64
		MAX-ACCESS		read-only
		STATUS			current
		DESCRIPTION		"Unavailable seconds near end"
		::=  {  nptOTU4TotalEntry  7  }


	nptOTU4TotalOFS	OBJECT-TYPE	
		SYNTAX			Counter64
		MAX-ACCESS		read-only
		STATUS			current
		DESCRIPTION		"Out-frame seconds The counter shall be increased if at least one Out Of Frame defect occurred during a second."
		::=  {  nptOTU4TotalEntry  8  }


	nptOTU4TotalBBEFE	OBJECT-TYPE	
		SYNTAX			Counter64
		MAX-ACCESS		read-only
		STATUS			current
		DESCRIPTION		"Background block error Far end An errored block not occurring as part of SES-FE"
		::=  {  nptOTU4TotalEntry  9  }


	nptOTU4TotalESFE	OBJECT-TYPE	
		SYNTAX			Counter64
		MAX-ACCESS		read-only
		STATUS			current
		DESCRIPTION		"Errored second Far end 1-second period which contains at least one errored blocks or at least one defect"
		::=  {  nptOTU4TotalEntry  10  }
		
		
	nptOTU4TotalSESFE	OBJECT-TYPE	
		SYNTAX			Counter64
		MAX-ACCESS		read-only
		STATUS			current
		DESCRIPTION		"Severely errored second Far end 1-second period which contains ?Y15% errored blocks or at least one defect."
		::=  {  nptOTU4TotalEntry  11  }

    nptOTU4TotalUASFE	OBJECT-TYPE	
		SYNTAX			Counter64
		MAX-ACCESS		read-only
		STATUS			current
		DESCRIPTION		"Unavailable second far end"
		::=  {  nptOTU4TotalEntry  12  }
        
    nptOTU4TotalPREFECBER	OBJECT-TYPE	
		SYNTAX			DisplayString
		MAX-ACCESS		read-only
		STATUS			current
		DESCRIPTION		" Pre-FEC BER is a function of Corrected Errors (CE), Bit Rate (BR) and collection time (t).The function is defined as PreFEC BER=CE/(BR x t) "
		::=  {  nptOTU4TotalEntry  13  }
        
    nptOTU4TotalDGDMax	OBJECT-TYPE	
		SYNTAX			DisplayString
		MAX-ACCESS		read-only
		STATUS			current
		DESCRIPTION		"Differential Group Delay Maximum value"
		::=  {  nptOTU4TotalEntry  14  }

    nptOTU4TotalDGDMin	OBJECT-TYPE	
		SYNTAX			DisplayString
		MAX-ACCESS		read-only
		STATUS			current
		DESCRIPTION		"Differential Group Delay Minimum value"
		::=  {  nptOTU4TotalEntry  15  }

    nptOTU4TotalCDMax	OBJECT-TYPE	
		SYNTAX			DisplayString
		MAX-ACCESS		read-only
		STATUS			current
		DESCRIPTION		"Chromatic Dispersion Maximum value"
		::=  {  nptOTU4TotalEntry  16  }

    nptOTU4TotalCDMin	OBJECT-TYPE	
		SYNTAX			DisplayString
		MAX-ACCESS		read-only
		STATUS			current
		DESCRIPTION		"Chromatic Dispersion Minimum value"
		::=  {  nptOTU4TotalEntry  17  }         
        
	nptOTUC2CurrentTable	OBJECT-TYPE
		SYNTAX		SEQUENCE  OF  NptOTUC2CurrentEntry
		MAX-ACCESS	not-accessible
		STATUS		current
		DESCRIPTION	"The OTUC2 current table contains various statistics
            being collected for the current 15 minute
            interval."
		::=  { nptOTUC2Port  1 }

	nptOTUC2CurrentEntry	OBJECT-TYPE
		SYNTAX		NptOTUC2CurrentEntry
		MAX-ACCESS	not-accessible
		STATUS		current
		DESCRIPTION	"An entry in the OTUC2 Current table."
		INDEX		{  nptOTUC2CurrentIndex  }
		::=  { nptOTUC2CurrentTable 1 }

	NptOTUC2CurrentEntry  ::=  SEQUENCE {
		nptOTUC2CurrentIndex  Integer32,
		nptOTUC2CurrentMoDescription  DisplayString,
		nptOTUC2CurrentFECCE  Counter64,
        nptOTUC2CurrentFECUCE  Counter64, 
		nptOTUC2CurrentBBENE Counter64,
		nptOTUC2CurrentESNE  Counter64,
		nptOTUC2CurrentSESNE  Counter64,
		nptOTUC2CurrentUASNE  Counter64,
		nptOTUC2CurrentOFS  Counter64,
		nptOTUC2CurrentBBEFE  Counter64,
		nptOTUC2CurrentESFE  Counter64,
		nptOTUC2CurrentSESFE  Counter64,
		nptOTUC2CurrentUASFE  Counter64,
        nptOTUC2CurrentPREFECBER  DisplayString,
        nptOTUC2CurrentDGDMax  DisplayString,
        nptOTUC2CurrentDGDMin  DisplayString,
        nptOTUC2CurrentCDMax  DisplayString,
        nptOTUC2CurrentCDMin  DisplayString,
        nptOTUC2CurrentOSNRMax  DisplayString,
        nptOTUC2CurrentOSNRMin  DisplayString,
        nptOTUC2CurrentMaxRxPower  DisplayString,
        nptOTUC2CurrentMinRxPower  DisplayString,
        nptOTUC2CurrentTxPower  DisplayString
		}


	nptOTUC2CurrentIndex	OBJECT-TYPE	
		SYNTAX			Integer32  ( -2147483648 .. 2147483647  ) 
		MAX-ACCESS		read-only
		STATUS			current
		DESCRIPTION		"The index value which uniquely identifies  the
            OTUC2 interface to which this entry is applicable."
		::=  {  nptOTUC2CurrentEntry  1  }
		
	nptOTUC2CurrentMoDescription	OBJECT-TYPE	
		SYNTAX			DisplayString 
		MAX-ACCESS		read-only
		STATUS			current
		DESCRIPTION		"Mo Description"
		::=  {  nptOTUC2CurrentEntry  2  }


	nptOTUC2CurrentFECCE	OBJECT-TYPE	
		SYNTAX			Counter64
		MAX-ACCESS		read-only
		STATUS			current
		DESCRIPTION		"FEC corrected errors;"
		::=  {  nptOTUC2CurrentEntry  3  }

	nptOTUC2CurrentFECUCE	OBJECT-TYPE	
		SYNTAX			Counter64
		MAX-ACCESS		read-only
		STATUS			current
		DESCRIPTION		"FEC Uncorrected errors;"
		::=  {  nptOTUC2CurrentEntry  4  }

	nptOTUC2CurrentBBENE	OBJECT-TYPE	
		SYNTAX			Counter64
		MAX-ACCESS		read-only
		STATUS			current
		DESCRIPTION		"Background block error Near end An errored block not occurring as part of SES"
		::=  {  nptOTUC2CurrentEntry  5  }


	nptOTUC2CurrentESNE	OBJECT-TYPE	
		SYNTAX			Counter64
		MAX-ACCESS		read-only
		STATUS			current
		DESCRIPTION		"Errored second Near end 1-second period which contains at least one errored blocks or at least one defect"
		::=  {  nptOTUC2CurrentEntry  6  }


	nptOTUC2CurrentSESNE	OBJECT-TYPE	
		SYNTAX			Counter64
		MAX-ACCESS		read-only
		STATUS			current
		DESCRIPTION		"Severely errored second Near end 1-second period which contains ?Y15% errored blocks or at least one defect;"
		::=  {  nptOTUC2CurrentEntry  7  }


	nptOTUC2CurrentUASNE	OBJECT-TYPE	
		SYNTAX			Counter64
		MAX-ACCESS		read-only
		STATUS			current
		DESCRIPTION		"Unavailable seconds near end"
		::=  {  nptOTUC2CurrentEntry  8  }


	nptOTUC2CurrentOFS	OBJECT-TYPE	
		SYNTAX			Counter64
		MAX-ACCESS		read-only
		STATUS			current
		DESCRIPTION		"Out-frame seconds The counter shall be increased if at least one Out Of Frame defect occurred during a second."
		::=  {  nptOTUC2CurrentEntry  9  }


	nptOTUC2CurrentBBEFE	OBJECT-TYPE	
		SYNTAX			Counter64
		MAX-ACCESS		read-only
		STATUS			current
		DESCRIPTION		"Background block error Far end An errored block not occurring as part of SES-FE"
		::=  {  nptOTUC2CurrentEntry  10  }


	nptOTUC2CurrentESFE	OBJECT-TYPE	
		SYNTAX			Counter64
		MAX-ACCESS		read-only
		STATUS			current
		DESCRIPTION		"Errored second Far end 1-second period which contains at least one errored blocks or at least one defect"
		::=  {  nptOTUC2CurrentEntry  11  }
		
		
	nptOTUC2CurrentSESFE	OBJECT-TYPE	
		SYNTAX			Counter64
		MAX-ACCESS		read-only
		STATUS			current
		DESCRIPTION		"Severely errored second Far end 1-second period which contains ?Y15% errored blocks or at least one defect."
		::=  {  nptOTUC2CurrentEntry  12  }

    nptOTUC2CurrentUASFE	OBJECT-TYPE	
		SYNTAX			Counter64
		MAX-ACCESS		read-only
		STATUS			current
		DESCRIPTION		"Unavailable second far end"
		::=  {  nptOTUC2CurrentEntry  13  }
        
    nptOTUC2CurrentPREFECBER	OBJECT-TYPE	
		SYNTAX			DisplayString
		MAX-ACCESS		read-only
		STATUS			current
		DESCRIPTION		" Pre-FEC BER is a function of Corrected Errors (CE), Bit Rate (BR) and collection time (t).The function is defined as PreFEC BER=CE/(BR x t) "
		::=  {  nptOTUC2CurrentEntry  14  }

    nptOTUC2CurrentDGDMax	OBJECT-TYPE	
		SYNTAX			DisplayString
		MAX-ACCESS		read-only
		STATUS			current
		DESCRIPTION		"Differential Group Delay Maximum value"
		::=  {  nptOTUC2CurrentEntry  15  }        

    nptOTUC2CurrentDGDMin	OBJECT-TYPE	
		SYNTAX			DisplayString
		MAX-ACCESS		read-only
		STATUS			current
		DESCRIPTION		"Differential Group Delay Minimum value"
		::=  {  nptOTUC2CurrentEntry  16  }

    nptOTUC2CurrentCDMax	OBJECT-TYPE	
		SYNTAX			DisplayString
		MAX-ACCESS		read-only
		STATUS			current
		DESCRIPTION		"Chromatic Dispersion Maximum value"
		::=  {  nptOTUC2CurrentEntry  17  }

    nptOTUC2CurrentCDMin	OBJECT-TYPE	
		SYNTAX			DisplayString
		MAX-ACCESS		read-only
		STATUS			current
		DESCRIPTION		"Chromatic Dispersion Minimum value"
		::=  {  nptOTUC2CurrentEntry  18  }
               
    nptOTUC2CurrentOSNRMax	OBJECT-TYPE	
		SYNTAX			DisplayString
		MAX-ACCESS		read-only
		STATUS			current
		DESCRIPTION		"The maximal value of Optical Signal to Noise Rate "
		::=  {  nptOTUC2CurrentEntry  19  }
        
    nptOTUC2CurrentOSNRMin	OBJECT-TYPE	
		SYNTAX			DisplayString
		MAX-ACCESS		read-only
		STATUS			current
		DESCRIPTION		"The minimal  value of Optical Signal to Noise Rate "
		::=  {  nptOTUC2CurrentEntry  20  }
        
    nptOTUC2CurrentMaxRxPower	OBJECT-TYPE	
		SYNTAX			DisplayString
		MAX-ACCESS		read-only
		STATUS			current
		DESCRIPTION		"The maximal receive optical power in monitored duration"
		::=  {  nptOTUC2CurrentEntry  21  }
        
    nptOTUC2CurrentMinRxPower	OBJECT-TYPE	
		SYNTAX			DisplayString
		MAX-ACCESS		read-only
		STATUS			current
		DESCRIPTION		"The minimal receive optical power in monitored duration"
		::=  {  nptOTUC2CurrentEntry  22  }
        
    nptOTUC2CurrentTxPower	OBJECT-TYPE	
		SYNTAX			DisplayString
		MAX-ACCESS		read-only
		STATUS			current
		DESCRIPTION		"The maximal Transmit optical power in monitored duration"
		::=  {  nptOTUC2CurrentEntry  23  }
                       
                       
	nptOTUC2TotalTable	OBJECT-TYPE
		SYNTAX		SEQUENCE  OF  NptOTUC2TotalEntry
		MAX-ACCESS	not-accessible
		STATUS		current
		DESCRIPTION	"The OTUC2 current table contains various statistics
            being collected for the current 15 minute
            interval."
		::=  { nptOTUC2Port  2 }

	nptOTUC2TotalEntry	OBJECT-TYPE
		SYNTAX		NptOTUC2TotalEntry
		MAX-ACCESS	not-accessible
		STATUS		current
		DESCRIPTION	"An entry in the OTUC2 Total table."
		INDEX		{  nptOTUC2TotalIndex  }
		::=  { nptOTUC2TotalTable 1 }

	NptOTUC2TotalEntry  ::=  SEQUENCE {
		nptOTUC2TotalIndex  Integer32,
		nptOTUC2TotalMoDescription  DisplayString,
		nptOTUC2TotalFECCE  Counter64,
        nptOTUC2TotalFECUCE  Counter64, 
		nptOTUC2TotalBBENE Counter64,
		nptOTUC2TotalESNE  Counter64,
		nptOTUC2TotalSESNE  Counter64,
		nptOTUC2TotalUASNE  Counter64,
		nptOTUC2TotalOFS  Counter64,
		nptOTUC2TotalBBEFE  Counter64,
		nptOTUC2TotalESFE  Counter64,
		nptOTUC2TotalSESFE  Counter64,
		nptOTUC2TotalUASFE  Counter64,
        nptOTUC2TotalPREFECBER  DisplayString,
        nptOTUC2TotalDGDMax  DisplayString,
        nptOTUC2TotalDGDMin  DisplayString,
        nptOTUC2TotalCDMax  DisplayString,
        nptOTUC2TotalCDMin  DisplayString,
        nptOTUC2TotalOSNRMax  DisplayString,
        nptOTUC2TotalOSNRMin  DisplayString,
        nptOTUC2TotalMaxRxPower  DisplayString,
        nptOTUC2TotalMinRxPower  DisplayString,
        nptOTUC2TotalTxPower  DisplayString
		}

	nptOTUC2TotalIndex	OBJECT-TYPE	
		SYNTAX			Integer32  ( -2147483648 .. 2147483647  ) 
		MAX-ACCESS		read-only
		STATUS			current
		DESCRIPTION		"The index value which uniquely identifies  the
            OTUC2 interface to which this entry is applicable."
		::=  {  nptOTUC2TotalEntry  1  }
		
	nptOTUC2TotalMoDescription	OBJECT-TYPE	
		SYNTAX			DisplayString 
		MAX-ACCESS		read-only
		STATUS			current
		DESCRIPTION		"Mo Description"
		::=  {  nptOTUC2TotalEntry  2  }


	nptOTUC2TotalFECCE	OBJECT-TYPE	
		SYNTAX			Counter64
		MAX-ACCESS		read-only
		STATUS			current
		DESCRIPTION		"FEC corrected errors;"
		::=  {  nptOTUC2TotalEntry  3  }

	nptOTUC2TotalFECUCE	OBJECT-TYPE	
		SYNTAX			Counter64
		MAX-ACCESS		read-only
		STATUS			current
		DESCRIPTION		"FEC Uncorrected errors;"
		::=  {  nptOTUC2TotalEntry  4  }

	nptOTUC2TotalBBENE	OBJECT-TYPE	
		SYNTAX			Counter64
		MAX-ACCESS		read-only
		STATUS			current
		DESCRIPTION		"Background block error Near end An errored block not occurring as part of SES"
		::=  {  nptOTUC2TotalEntry  5  }


	nptOTUC2TotalESNE	OBJECT-TYPE	
		SYNTAX			Counter64
		MAX-ACCESS		read-only
		STATUS			current
		DESCRIPTION		"Errored second Near end 1-second period which contains at least one errored blocks or at least one defect"
		::=  {  nptOTUC2TotalEntry  6  }


	nptOTUC2TotalSESNE	OBJECT-TYPE	
		SYNTAX			Counter64
		MAX-ACCESS		read-only
		STATUS			current
		DESCRIPTION		"Severely errored second Near end 1-second period which contains ?Y15% errored blocks or at least one defect;"
		::=  {  nptOTUC2TotalEntry  7  }


	nptOTUC2TotalUASNE	OBJECT-TYPE	
		SYNTAX			Counter64
		MAX-ACCESS		read-only
		STATUS			current
		DESCRIPTION		"Unavailable seconds near end"
		::=  {  nptOTUC2TotalEntry  8  }


	nptOTUC2TotalOFS	OBJECT-TYPE	
		SYNTAX			Counter64
		MAX-ACCESS		read-only
		STATUS			current
		DESCRIPTION		"Out-frame seconds The counter shall be increased if at least one Out Of Frame defect occurred during a second."
		::=  {  nptOTUC2TotalEntry  9  }


	nptOTUC2TotalBBEFE	OBJECT-TYPE	
		SYNTAX			Counter64
		MAX-ACCESS		read-only
		STATUS			current
		DESCRIPTION		"Background block error Far end An errored block not occurring as part of SES-FE"
		::=  {  nptOTUC2TotalEntry  10  }


	nptOTUC2TotalESFE	OBJECT-TYPE	
		SYNTAX			Counter64
		MAX-ACCESS		read-only
		STATUS			current
		DESCRIPTION		"Errored second Far end 1-second period which contains at least one errored blocks or at least one defect"
		::=  {  nptOTUC2TotalEntry  11  }
		
		
	nptOTUC2TotalSESFE	OBJECT-TYPE	
		SYNTAX			Counter64
		MAX-ACCESS		read-only
		STATUS			current
		DESCRIPTION		"Severely errored second Far end 1-second period which contains ?Y15% errored blocks or at least one defect."
		::=  {  nptOTUC2TotalEntry  12  }

    nptOTUC2TotalUASFE	OBJECT-TYPE	
		SYNTAX			Counter64
		MAX-ACCESS		read-only
		STATUS			current
		DESCRIPTION		"Unavailable second far end"
		::=  {  nptOTUC2TotalEntry  13  }
        
    nptOTUC2TotalPREFECBER	OBJECT-TYPE	
		SYNTAX			DisplayString
		MAX-ACCESS		read-only
		STATUS			current
		DESCRIPTION		" Pre-FEC BER is a function of Corrected Errors (CE), Bit Rate (BR) and collection time (t).The function is defined as PreFEC BER=CE/(BR x t) "
		::=  {  nptOTUC2TotalEntry  14  }

    nptOTUC2TotalDGDMax	OBJECT-TYPE	
		SYNTAX			DisplayString
		MAX-ACCESS		read-only
		STATUS			current
		DESCRIPTION		"Differential Group Delay Maximum value"
		::=  {  nptOTUC2TotalEntry  15  }        

    nptOTUC2TotalDGDMin	OBJECT-TYPE	
		SYNTAX			DisplayString
		MAX-ACCESS		read-only
		STATUS			current
		DESCRIPTION		"Differential Group Delay Minimum value"
		::=  {  nptOTUC2TotalEntry  16  }

    nptOTUC2TotalCDMax	OBJECT-TYPE	
		SYNTAX			DisplayString
		MAX-ACCESS		read-only
		STATUS			current
		DESCRIPTION		"Chromatic Dispersion Maximum value"
		::=  {  nptOTUC2TotalEntry  17  }

    nptOTUC2TotalCDMin	OBJECT-TYPE	
		SYNTAX			DisplayString
		MAX-ACCESS		read-only
		STATUS			current
		DESCRIPTION		"Chromatic Dispersion Minimum value"
		::=  {  nptOTUC2TotalEntry  18  }
                
    nptOTUC2TotalOSNRMax	OBJECT-TYPE	
		SYNTAX			DisplayString
		MAX-ACCESS		read-only
		STATUS			current
		DESCRIPTION		"The minimal value of Optical Signal to Noise Rate "
		::=  {  nptOTUC2TotalEntry  19  }
        
    nptOTUC2TotalOSNRMin	OBJECT-TYPE	
		SYNTAX			DisplayString
		MAX-ACCESS		read-only
		STATUS			current
		DESCRIPTION		"The maximal  value of Optical Signal to Noise Rate "
		::=  {  nptOTUC2TotalEntry  20  }
        
    nptOTUC2TotalMaxRxPower	OBJECT-TYPE	
		SYNTAX			DisplayString
		MAX-ACCESS		read-only
		STATUS			current
		DESCRIPTION		"The maximal receive optical power in monitored duration"
		::=  {  nptOTUC2TotalEntry  21  }
        
    nptOTUC2TotalMinRxPower	OBJECT-TYPE	
		SYNTAX			DisplayString
		MAX-ACCESS		read-only
		STATUS			current
		DESCRIPTION		"The minimal receive optical power in monitored duration"
		::=  {  nptOTUC2TotalEntry  22  }
        
    nptOTUC2TotalTxPower	OBJECT-TYPE	
		SYNTAX			DisplayString
		MAX-ACCESS		read-only
		STATUS			current
		DESCRIPTION		"The maximal Transmit optical power in monitored duration"
		::=  {  nptOTUC2TotalEntry  23  }

	nptODUC2CurrentTable	OBJECT-TYPE
		SYNTAX		SEQUENCE  OF  NptODUC2CurrentEntry
		MAX-ACCESS	not-accessible
		STATUS		current
		DESCRIPTION	"The ODUC2 current table contains various statistics
            being collected for the current 15 minute
            interval."
		::=  { nptODUC2Port  1 }

	nptODUC2CurrentEntry	OBJECT-TYPE
		SYNTAX		NptODUC2CurrentEntry
		MAX-ACCESS	not-accessible
		STATUS		current
		DESCRIPTION	"An entry in the ODUC2 Current table."
		INDEX		{  nptODUC2CurrentIndex  }
		::=  { nptODUC2CurrentTable 1 }

	NptODUC2CurrentEntry  ::=  SEQUENCE {
		nptODUC2CurrentIndex  Integer32,
		nptODUC2CurrentMoDescription  DisplayString,
		nptODUC2CurrentBBENE  Counter64,
		nptODUC2CurrentESNE Counter64,
		nptODUC2CurrentSESNE  Counter64,
		nptODUC2CurrentUASNE  Counter64,
		nptODUC2CurrentBBEFE  Counter64,
		nptODUC2CurrentESFE  Counter64,
		nptODUC2CurrentSESFE  Counter64,
		nptODUC2CurrentUASFE  Counter64,
		nptODUC2CurrentTSE  Counter64
		}


	nptODUC2CurrentIndex	OBJECT-TYPE	
		SYNTAX			Integer32  ( -2147483648 .. 2147483647  ) 
		MAX-ACCESS		read-only
		STATUS			current
		DESCRIPTION		"The index value which uniquely identifies  the
            ODUC2 interface to which this entry is applicable."
		::=  {  nptODUC2CurrentEntry  1  }
		
	nptODUC2CurrentMoDescription	OBJECT-TYPE	
		SYNTAX			DisplayString 
		MAX-ACCESS		read-only
		STATUS			current
		DESCRIPTION		"Mo Description"
		::=  {  nptODUC2CurrentEntry  2  }


	nptODUC2CurrentBBENE	OBJECT-TYPE	
		SYNTAX			Counter64
		MAX-ACCESS		read-only
		STATUS			current
		DESCRIPTION		"Background block error Near end An errored block not occurring as part of SES"
		::=  {  nptODUC2CurrentEntry  3  }


	nptODUC2CurrentESNE	OBJECT-TYPE	
		SYNTAX			Counter64
		MAX-ACCESS		read-only
		STATUS			current
		DESCRIPTION		"Errored second Near end 1-second period which contains at least one errored blocks or at least one defect"
		::=  {  nptODUC2CurrentEntry  4  }


	nptODUC2CurrentSESNE	OBJECT-TYPE	
		SYNTAX			Counter64
		MAX-ACCESS		read-only
		STATUS			current
		DESCRIPTION		"Severely errored second Near end 1-second period which contains ?Y15% errored blocks or at least one defect"
		::=  {  nptODUC2CurrentEntry  5  }


	nptODUC2CurrentUASNE	OBJECT-TYPE	
		SYNTAX			Counter64
		MAX-ACCESS		read-only
		STATUS			current
		DESCRIPTION		"Unavailable seconds near end"
		::=  {  nptODUC2CurrentEntry  6  }


	nptODUC2CurrentBBEFE	OBJECT-TYPE	
		SYNTAX			Counter64
		MAX-ACCESS		read-only
		STATUS			current
		DESCRIPTION		"Background block error Far end An errored block not occurring as part of SES-FE"
		::=  {  nptODUC2CurrentEntry  7  }


	nptODUC2CurrentESFE	OBJECT-TYPE	
		SYNTAX			Counter64
		MAX-ACCESS		read-only
		STATUS			current
		DESCRIPTION		"Errored second Far end 1-second period which contains at least one errored blocks or at least one defect"
		::=  {  nptODUC2CurrentEntry  8  }


	nptODUC2CurrentSESFE	OBJECT-TYPE	
		SYNTAX			Counter64
		MAX-ACCESS		read-only
		STATUS			current
		DESCRIPTION		"Severely errored second Far end 1-second period which contains ?Y15% errored blocks or at least one defect"
		::=  {  nptODUC2CurrentEntry  9  }


	nptODUC2CurrentUASFE	OBJECT-TYPE	
		SYNTAX			Counter64
		MAX-ACCESS		read-only
		STATUS			current
		DESCRIPTION		"Unavailable second far end"
		::=  {  nptODUC2CurrentEntry  10  }
		
		
	nptODUC2CurrentTSE	OBJECT-TYPE	
		SYNTAX			Counter64
		MAX-ACCESS		read-only
		STATUS			current
		DESCRIPTION		"Test Sequence Error. Counts the number of invalid test pattern"
		::=  {  nptODUC2CurrentEntry  11  }

    nptODUC2TotalTable	OBJECT-TYPE
		SYNTAX		SEQUENCE  OF  NptODUC2TotalEntry
		MAX-ACCESS	not-accessible
		STATUS		current
		DESCRIPTION	"The ODUC2 current table contains various statistics
            being collected for the current 15 minute
            interval."
		::=  { nptODUC2Port  2 }

	nptODUC2TotalEntry	OBJECT-TYPE
		SYNTAX		NptODUC2TotalEntry
		MAX-ACCESS	not-accessible
		STATUS		current
		DESCRIPTION	"An entry in the ODUC2 Total table."
		INDEX		{  nptODUC2TotalIndex  }
		::=  { nptODUC2TotalTable 1 }

	NptODUC2TotalEntry  ::=  SEQUENCE {
		nptODUC2TotalIndex  Integer32,
		nptODUC2TotalMoDescription  DisplayString,
		nptODUC2TotalBBENE  Counter64,
		nptODUC2TotalESNE Counter64,
		nptODUC2TotalSESNE  Counter64,
		nptODUC2TotalUASNE  Counter64,
		nptODUC2TotalBBEFE  Counter64,
		nptODUC2TotalESFE  Counter64,
		nptODUC2TotalSESFE  Counter64,
		nptODUC2TotalUASFE  Counter64,
		nptODUC2TotalTSE  Counter64
		}


	nptODUC2TotalIndex	OBJECT-TYPE	
		SYNTAX			Integer32  ( -2147483648 .. 2147483647  ) 
		MAX-ACCESS		read-only
		STATUS			current
		DESCRIPTION		"The index value which uniquely identifies  the
            ODUC2 interface to which this entry is applicable."
		::=  {  nptODUC2TotalEntry  1  }
		
	nptODUC2TotalMoDescription	OBJECT-TYPE	
		SYNTAX			DisplayString 
		MAX-ACCESS		read-only
		STATUS			current
		DESCRIPTION		"Mo Description"
		::=  {  nptODUC2TotalEntry  2  }


	nptODUC2TotalBBENE	OBJECT-TYPE	
		SYNTAX			Counter64
		MAX-ACCESS		read-only
		STATUS			current
		DESCRIPTION		"Background block error Near end An errored block not occurring as part of SES"
		::=  {  nptODUC2TotalEntry  3  }


	nptODUC2TotalESNE	OBJECT-TYPE	
		SYNTAX			Counter64
		MAX-ACCESS		read-only
		STATUS			current
		DESCRIPTION		"Errored second Near end 1-second period which contains at least one errored blocks or at least one defect"
		::=  {  nptODUC2TotalEntry  4  }


	nptODUC2TotalSESNE	OBJECT-TYPE	
		SYNTAX			Counter64
		MAX-ACCESS		read-only
		STATUS			current
		DESCRIPTION		"Severely errored second Near end 1-second period which contains ?Y15% errored blocks or at least one defect"
		::=  {  nptODUC2TotalEntry  5  }


	nptODUC2TotalUASNE	OBJECT-TYPE	
		SYNTAX			Counter64
		MAX-ACCESS		read-only
		STATUS			current
		DESCRIPTION		"Unavailable seconds near end"
		::=  {  nptODUC2TotalEntry  6  }


	nptODUC2TotalBBEFE	OBJECT-TYPE	
		SYNTAX			Counter64
		MAX-ACCESS		read-only
		STATUS			current
		DESCRIPTION		"Background block error Far end An errored block not occurring as part of SES-FE"
		::=  {  nptODUC2TotalEntry  7  }


	nptODUC2TotalESFE	OBJECT-TYPE	
		SYNTAX			Counter64
		MAX-ACCESS		read-only
		STATUS			current
		DESCRIPTION		"Errored second Far end 1-second period which contains at least one errored blocks or at least one defect"
		::=  {  nptODUC2TotalEntry  8  }


	nptODUC2TotalSESFE	OBJECT-TYPE	
		SYNTAX			Counter64
		MAX-ACCESS		read-only
		STATUS			current
		DESCRIPTION		"Severely errored second Far end 1-second period which contains ?Y15% errored blocks or at least one defect"
		::=  {  nptODUC2TotalEntry  9  }


	nptODUC2TotalUASFE	OBJECT-TYPE	
		SYNTAX			Counter64
		MAX-ACCESS		read-only
		STATUS			current
		DESCRIPTION		"Unavailable second far end"
		::=  {  nptODUC2TotalEntry  10  }
		
		
	nptODUC2TotalTSE	OBJECT-TYPE	
		SYNTAX			Counter64
		MAX-ACCESS		read-only
		STATUS			current
		DESCRIPTION		"Test Sequence Error. Counts the number of invalid test pattern"
		::=  {  nptODUC2TotalEntry  11  }

	nptACLifCurrentTable	OBJECT-TYPE
		SYNTAX		SEQUENCE  OF  NptACLifCurrentEntry
		MAX-ACCESS	not-accessible
		STATUS		current
		DESCRIPTION	"The Lif current table contains various statistics
            being collected for the current 15 minute
            interval."
		::=  { nptACLifGroup  1 }

	nptACLifCurrentEntry	OBJECT-TYPE
		SYNTAX		NptACLifCurrentEntry
		MAX-ACCESS	not-accessible
		STATUS		current
		DESCRIPTION	"An entry in the Lif Total table."
		INDEX		{  nptACLifCurrentIndex  }
		::=  { nptACLifCurrentTable 1 }

	NptACLifCurrentEntry  ::=  SEQUENCE {
		nptACLifCurrentIndex  Integer32,
		nptACLifCurrentMoDescription  DisplayString,
        nptACLifCurrentRxPassOctets  Counter64,
		nptACLifCurrentRxPassPkts  Counter64,
        nptACLifCurrentRxDiscardOctets  Counter64,
        nptACLifCurrentRxDiscardPkts  Counter64, 
        nptACLifCurrentTxPassOctets  Counter64,
		nptACLifCurrentTxPassPkts  Counter64,
        nptACLifCurrentTxDiscardOctets  Counter64,
		nptACLifCurrentTxDiscardPkts  Counter64
		}

	nptACLifCurrentIndex	OBJECT-TYPE	
		SYNTAX			Integer32  ( -2147483648 .. 2147483647  ) 
		MAX-ACCESS		read-only
		STATUS			current
		DESCRIPTION		"The index value which uniquely identifies  the
            Lif interface to which this entry is applicable."
		::=  {  nptACLifCurrentEntry  1  }
		
	nptACLifCurrentMoDescription	OBJECT-TYPE	
		SYNTAX			DisplayString 
		MAX-ACCESS		read-only
		STATUS			current
		DESCRIPTION		"Mo Description"
		::=  {  nptACLifCurrentEntry  2  }
        
	nptACLifCurrentRxPassOctets 	OBJECT-TYPE	
		SYNTAX			Counter64 
		MAX-ACCESS		read-only
		STATUS			current
		DESCRIPTION		"Mo Description"
		::=  {  nptACLifCurrentEntry  3  }
        
	nptACLifCurrentRxPassPkts 	OBJECT-TYPE	
		SYNTAX			Counter64 
		MAX-ACCESS		read-only
		STATUS			current
		DESCRIPTION		"Mo Description"
		::=  {  nptACLifCurrentEntry  4  }
        
	nptACLifCurrentRxDiscardOctets	OBJECT-TYPE	
		SYNTAX		Counter64 
		MAX-ACCESS		read-only
		STATUS			current
		DESCRIPTION		"Mo Description"
		::=  {  nptACLifCurrentEntry  5  }
        
	nptACLifCurrentRxDiscardPkts	OBJECT-TYPE	
		SYNTAX		Counter64 
		MAX-ACCESS		read-only
		STATUS			current
		DESCRIPTION		"Mo Description"
		::=  {  nptACLifCurrentEntry  6  }
        
	nptACLifCurrentTxPassOctets	OBJECT-TYPE	
		SYNTAX			Counter64 
		MAX-ACCESS		read-only
		STATUS			current
		DESCRIPTION		"Mo Description"
		::=  {  nptACLifCurrentEntry  7  }
        
	nptACLifCurrentTxPassPkts	OBJECT-TYPE	
		SYNTAX			Counter64 
		MAX-ACCESS		read-only
		STATUS			current
		DESCRIPTION		"Mo Description"
		::=  {  nptACLifCurrentEntry  8  }
        
	nptACLifCurrentTxDiscardOctets	OBJECT-TYPE	
		SYNTAX			Counter64 
		MAX-ACCESS		read-only
		STATUS			current
		DESCRIPTION		"Mo Description"
		::=  {  nptACLifCurrentEntry  9  }
        
	nptACLifCurrentTxDiscardPkts	OBJECT-TYPE	
		SYNTAX			Counter64 
		MAX-ACCESS		read-only
		STATUS			current
		DESCRIPTION		"Mo Description"
		::=  {  nptACLifCurrentEntry  10  }

	nptACLifTotalTable	OBJECT-TYPE
		SYNTAX		SEQUENCE  OF  NptACLifTotalEntry
		MAX-ACCESS	not-accessible
		STATUS		current
		DESCRIPTION	"The Lif current table contains various statistics
            being collected for the current 15 minute
            interval."
		::=  { nptACLifGroup  2 }

	nptACLifTotalEntry	OBJECT-TYPE
		SYNTAX		NptACLifTotalEntry
		MAX-ACCESS	not-accessible
		STATUS		current
		DESCRIPTION	"An entry in the Lif Total table."
		INDEX		{  nptACLifTotalIndex  }
		::=  { nptACLifTotalTable 1 }

	NptACLifTotalEntry  ::=  SEQUENCE {
		nptACLifTotalIndex  Integer32,
		nptACLifTotalMoDescription  DisplayString,
        nptACLifTotalRxPassOctets  Counter64,
		nptACLifTotalRxPassPkts  Counter64,
        nptACLifTotalRxDiscardOctets  Counter64, 
        nptACLifTotalRxDiscardPkts  Counter64, 
        nptACLifTotalTxPassOctets  Counter64,
		nptACLifTotalTxPassPkts  Counter64,
        nptACLifTotalTxDiscardOctets  Counter64,
		nptACLifTotalTxDiscardPkts  Counter64
		}

	nptACLifTotalIndex	OBJECT-TYPE	
		SYNTAX			Integer32  ( -2147483648 .. 2147483647  ) 
		MAX-ACCESS		read-only
		STATUS			current
		DESCRIPTION		"The index value which uniquely identifies  the
            Lif interface to which this entry is applicable."
		::=  {  nptACLifTotalEntry  1  }
		
	nptACLifTotalMoDescription	OBJECT-TYPE	
		SYNTAX			DisplayString 
		MAX-ACCESS		read-only
		STATUS			current
		DESCRIPTION		"Mo Description"
		::=  {  nptACLifTotalEntry  2  }
        
	nptACLifTotalRxPassOctets 	OBJECT-TYPE	
		SYNTAX			Counter64 
		MAX-ACCESS		read-only
		STATUS			current
		DESCRIPTION		"Mo Description"
		::=  {  nptACLifTotalEntry  3  }
        
	nptACLifTotalRxPassPkts 	OBJECT-TYPE	
		SYNTAX			Counter64 
		MAX-ACCESS		read-only
		STATUS			current
		DESCRIPTION		"Mo Description"
		::=  {  nptACLifTotalEntry  4  }
        
	nptACLifTotalRxDiscardOctets	OBJECT-TYPE	
		SYNTAX		Counter64 
		MAX-ACCESS		read-only
		STATUS			current
		DESCRIPTION		"Mo Description"
		::=  {  nptACLifTotalEntry  5  }
        
	nptACLifTotalRxDiscardPkts	OBJECT-TYPE	
		SYNTAX		Counter64 
		MAX-ACCESS		read-only
		STATUS			current
		DESCRIPTION		"Mo Description"
		::=  {  nptACLifTotalEntry  6  }
        
	nptACLifTotalTxPassOctets	OBJECT-TYPE	
		SYNTAX			Counter64 
		MAX-ACCESS		read-only
		STATUS			current
		DESCRIPTION		"Mo Description"
		::=  {  nptACLifTotalEntry  7  }
        
	nptACLifTotalTxPassPkts	OBJECT-TYPE	
		SYNTAX			Counter64 
		MAX-ACCESS		read-only
		STATUS			current
		DESCRIPTION		"Mo Description"
		::=  {  nptACLifTotalEntry  8  }
        
	nptACLifTotalTxDiscardOctets	OBJECT-TYPE	
		SYNTAX			Counter64 
		MAX-ACCESS		read-only
		STATUS			current
		DESCRIPTION		"Mo Description"
		::=  {  nptACLifTotalEntry  9  }
        
	nptACLifTotalTxDiscardPkts	OBJECT-TYPE	
		SYNTAX			Counter64 
		MAX-ACCESS		read-only
		STATUS			current
		DESCRIPTION		"Mo Description"
		::=  {  nptACLifTotalEntry  10  }
        
        
	nptACLifRxCosCurrentTable	OBJECT-TYPE
		SYNTAX		SEQUENCE  OF  NptACLifRxCosCurrentEntry
		MAX-ACCESS	not-accessible
		STATUS		current
		DESCRIPTION	"The Lif current table contains various statistics
            being collected for the current 15 minute
            interval."
		::=  { nptACLifRxCosGroup  1 }

	nptACLifRxCosCurrentEntry	OBJECT-TYPE
		SYNTAX		NptACLifRxCosCurrentEntry
		MAX-ACCESS	not-accessible
		STATUS		current
		DESCRIPTION	"An entry in the Lif Total table."
		INDEX		{  nptACLifRxCosCurrentIndex  }
		::=  { nptACLifRxCosCurrentTable 1 }

	NptACLifRxCosCurrentEntry  ::=  SEQUENCE {
		nptACLifRxCosCurrentIndex  Integer32,
        nptACLifRxCosCurrentLifIndex  Integer32,
		nptACLifRxCosCurrentMoDescription  DisplayString,
        nptACLifRxCosCurrentCosID  Integer32,
        nptACLifRxCosCurrentPmState  DisplayString,
		nptACLifRxCosCurrentPassGreenOctets  Counter64,
        nptACLifRxCosCurrentPassYellowOctets  Counter64, 
		nptACLifRxCosCurrentDiscardGreenOrYellowOctets  Counter64,
		nptACLifRxCosCurrentDiscardRedOctets  Counter64,
        nptACLifRxCosCurrentPassGreenPkts  Counter64,
        nptACLifRxCosCurrentPassYellowPkts  Counter64,
        nptACLifRxCosCurrentDiscardGreenOrYellowPkts  Counter64,
        nptACLifRxCosCurrentDiscardRedPkts  Counter64,
        nptACLifRxCosCurrentPassOctets  Counter64,
        nptACLifRxCosCurrentPassPkts  Counter64,
        nptACLifRxCosCurrentDiscardOctets  Counter64,
        nptACLifRxCosCurrentDiscardPkts  Counter64
		}

	nptACLifRxCosCurrentIndex	OBJECT-TYPE	
		SYNTAX			Integer32  ( -2147483648 .. 2147483647  ) 
		MAX-ACCESS		read-only
		STATUS			current
		DESCRIPTION		"The index value which uniquely identifies  the
            Lif interface to which this entry is applicable."
		::=  {  nptACLifRxCosCurrentEntry  1  }
        
	nptACLifRxCosCurrentLifIndex	OBJECT-TYPE	
		SYNTAX			Integer32  ( -2147483648 .. 2147483647  ) 
		MAX-ACCESS		read-only
		STATUS			current
		DESCRIPTION		"Mo Description"
		::=  {  nptACLifRxCosCurrentEntry  2  }
		
	nptACLifRxCosCurrentMoDescription	OBJECT-TYPE	
		SYNTAX			DisplayString 
		MAX-ACCESS		read-only
		STATUS			current
		DESCRIPTION		"Mo Description"
		::=  {  nptACLifRxCosCurrentEntry  3  }
        
	nptACLifRxCosCurrentCosID	OBJECT-TYPE	
		SYNTAX			Integer32
		MAX-ACCESS		read-only
		STATUS			current
		DESCRIPTION		"The index value which uniquely identifies  the
            Lif interface to which this entry is applicable."
		::=  {  nptACLifRxCosCurrentEntry  4  }
        
	nptACLifRxCosCurrentPmState	OBJECT-TYPE	
		SYNTAX			DisplayString 
		MAX-ACCESS		read-only
		STATUS			current
		DESCRIPTION		"Mo Description"
		::=  {  nptACLifRxCosCurrentEntry  5  }
        
	nptACLifRxCosCurrentPassGreenOctets 	OBJECT-TYPE	
		SYNTAX			Counter64 
		MAX-ACCESS		read-only
		STATUS			current
		DESCRIPTION		"Mo Description"
		::=  {  nptACLifRxCosCurrentEntry  6  }
        
	nptACLifRxCosCurrentPassYellowOctets 	OBJECT-TYPE	
		SYNTAX			Counter64 
		MAX-ACCESS		read-only
		STATUS			current
		DESCRIPTION		"Mo Description"
		::=  {  nptACLifRxCosCurrentEntry  7  }
        
	nptACLifRxCosCurrentDiscardGreenOrYellowOctets	OBJECT-TYPE	
		SYNTAX		Counter64 
		MAX-ACCESS		read-only
		STATUS			current
		DESCRIPTION		"Mo Description"
		::=  {  nptACLifRxCosCurrentEntry  8  }
        
	nptACLifRxCosCurrentDiscardRedOctets	OBJECT-TYPE	
		SYNTAX			Counter64 
		MAX-ACCESS		read-only
		STATUS			current
		DESCRIPTION		"Mo Description"
		::=  {  nptACLifRxCosCurrentEntry  9  }
        
	nptACLifRxCosCurrentPassGreenPkts	OBJECT-TYPE	
		SYNTAX			Counter64 
		MAX-ACCESS		read-only
		STATUS			current
		DESCRIPTION		"Mo Description"
		::=  {  nptACLifRxCosCurrentEntry  10  }
        
	nptACLifRxCosCurrentPassYellowPkts	OBJECT-TYPE	
		SYNTAX			Counter64 
		MAX-ACCESS		read-only
		STATUS			current
		DESCRIPTION		"Mo Description"
		::=  {  nptACLifRxCosCurrentEntry  11  }
        
	nptACLifRxCosCurrentDiscardGreenOrYellowPkts	OBJECT-TYPE	
		SYNTAX			Counter64 
		MAX-ACCESS		read-only
		STATUS			current
		DESCRIPTION		"Mo Description"
		::=  {  nptACLifRxCosCurrentEntry  12  }
        
	nptACLifRxCosCurrentDiscardRedPkts	OBJECT-TYPE	
		SYNTAX			Counter64 
		MAX-ACCESS		read-only
		STATUS			current
		DESCRIPTION		"Mo Description"
		::=  {  nptACLifRxCosCurrentEntry  13  }
        
	nptACLifRxCosCurrentPassOctets	OBJECT-TYPE	
		SYNTAX			Counter64 
		MAX-ACCESS		read-only
		STATUS			current
		DESCRIPTION		"Mo Description"
		::=  {  nptACLifRxCosCurrentEntry  14  }
        
	nptACLifRxCosCurrentPassPkts	OBJECT-TYPE	
		SYNTAX			Counter64 
		MAX-ACCESS		read-only
		STATUS			current
		DESCRIPTION		"Mo Description"
		::=  {  nptACLifRxCosCurrentEntry  15  }
        
	nptACLifRxCosCurrentDiscardOctets	OBJECT-TYPE	
		SYNTAX			Counter64 
		MAX-ACCESS		read-only
		STATUS			current
		DESCRIPTION		"Mo Description"
		::=  {  nptACLifRxCosCurrentEntry  16  }
        
	nptACLifRxCosCurrentDiscardPkts	OBJECT-TYPE	
		SYNTAX			Counter64 
		MAX-ACCESS		read-only
		STATUS			current
		DESCRIPTION		"Mo Description"
		::=  {  nptACLifRxCosCurrentEntry  17  }
        
        
	nptACLifRxCosTotalTable	OBJECT-TYPE
		SYNTAX		SEQUENCE  OF  NptACLifRxCosTotalEntry
		MAX-ACCESS	not-accessible
		STATUS		current
		DESCRIPTION	"The Lif total table contains various statistics
            being collected for the history 24 hours
            interval."
		::=  { nptACLifRxCosGroup  2 }

	nptACLifRxCosTotalEntry	OBJECT-TYPE
		SYNTAX		NptACLifRxCosTotalEntry
		MAX-ACCESS	not-accessible
		STATUS		current
		DESCRIPTION	"An entry in the Lif Total table."
		INDEX		{  nptACLifRxCosTotalIndex  }
		::=  { nptACLifRxCosTotalTable 1 }

	NptACLifRxCosTotalEntry  ::=  SEQUENCE {
		nptACLifRxCosTotalIndex  Integer32,
        nptACLifRxCosTotalLifIndex  Integer32,
		nptACLifRxCosTotalMoDescription  DisplayString,
        nptACLifRxCosTotalCosID  Integer32,
        nptACLifRxCosTotalPmState  DisplayString,
		nptACLifRxCosTotalPassGreenOctets  Counter64,
        nptACLifRxCosTotalPassYellowOctets  Counter64, 
		nptACLifRxCosTotalDiscardGreenOrYellowOctets  Counter64,
		nptACLifRxCosTotalDiscardRedOctets  Counter64,
        nptACLifRxCosTotalPassGreenPkts  Counter64,
        nptACLifRxCosTotalPassYellowPkts  Counter64,
        nptACLifRxCosTotalDiscardGreenOrYellowPkts  Counter64,
        nptACLifRxCosTotalDiscardRedPkts  Counter64,
        nptACLifRxCosTotalPassOctets  Counter64,
        nptACLifRxCosTotalPassPkts  Counter64,
        nptACLifRxCosTotalDiscardOctets  Counter64,
        nptACLifRxCosTotalDiscardPkts  Counter64
		}

	nptACLifRxCosTotalIndex	OBJECT-TYPE	
		SYNTAX			Integer32  ( -2147483648 .. 2147483647  ) 
		MAX-ACCESS		read-only
		STATUS			current
		DESCRIPTION		"The index value which uniquely identifies  the
            Lif interface to which this entry is applicable."
		::=  {  nptACLifRxCosTotalEntry  1  }

	nptACLifRxCosTotalLifIndex	OBJECT-TYPE	
		SYNTAX			Integer32  ( -2147483648 .. 2147483647  ) 
		MAX-ACCESS		read-only
		STATUS			current
		DESCRIPTION		"Mo Description"
		::=  {  nptACLifRxCosTotalEntry  2  }
		
	nptACLifRxCosTotalMoDescription	OBJECT-TYPE	
		SYNTAX			DisplayString 
		MAX-ACCESS		read-only
		STATUS			current
		DESCRIPTION		"Mo Description"
		::=  {  nptACLifRxCosTotalEntry  3  }
        
	nptACLifRxCosTotalCosID	OBJECT-TYPE	
		SYNTAX			Integer32
		MAX-ACCESS		read-only
		STATUS			current
		DESCRIPTION		"The index value which uniquely identifies  the
            Lif interface to which this entry is applicable."
		::=  {  nptACLifRxCosTotalEntry  4  }
        
	nptACLifRxCosTotalPmState	OBJECT-TYPE	
		SYNTAX			DisplayString 
		MAX-ACCESS		read-only
		STATUS			current
		DESCRIPTION		"Mo Description"
		::=  {  nptACLifRxCosTotalEntry  5  }
        
	nptACLifRxCosTotalPassGreenOctets 	OBJECT-TYPE	
		SYNTAX			Counter64 
		MAX-ACCESS		read-only
		STATUS			current
		DESCRIPTION		"Mo Description"
		::=  {  nptACLifRxCosTotalEntry  6  }
        
	nptACLifRxCosTotalPassYellowOctets 	OBJECT-TYPE	
		SYNTAX			Counter64 
		MAX-ACCESS		read-only
		STATUS			current
		DESCRIPTION		"Mo Description"
		::=  {  nptACLifRxCosTotalEntry  7  }
        
	nptACLifRxCosTotalDiscardGreenOrYellowOctets	OBJECT-TYPE	
		SYNTAX		Counter64 
		MAX-ACCESS		read-only
		STATUS			current
		DESCRIPTION		"Mo Description"
		::=  {  nptACLifRxCosTotalEntry  8  }
        
	nptACLifRxCosTotalDiscardRedOctets	OBJECT-TYPE	
		SYNTAX			Counter64 
		MAX-ACCESS		read-only
		STATUS			current
		DESCRIPTION		"Mo Description"
		::=  {  nptACLifRxCosTotalEntry  9  }
        
	nptACLifRxCosTotalPassGreenPkts	OBJECT-TYPE	
		SYNTAX			Counter64 
		MAX-ACCESS		read-only
		STATUS			current
		DESCRIPTION		"Mo Description"
		::=  {  nptACLifRxCosTotalEntry  10  }
        
	nptACLifRxCosTotalPassYellowPkts	OBJECT-TYPE	
		SYNTAX			Counter64 
		MAX-ACCESS		read-only
		STATUS			current
		DESCRIPTION		"Mo Description"
		::=  {  nptACLifRxCosTotalEntry  11  }
        
	nptACLifRxCosTotalDiscardGreenOrYellowPkts	OBJECT-TYPE	
		SYNTAX			Counter64 
		MAX-ACCESS		read-only
		STATUS			current
		DESCRIPTION		"Mo Description"
		::=  {  nptACLifRxCosTotalEntry  12  }
        
	nptACLifRxCosTotalDiscardRedPkts	OBJECT-TYPE	
		SYNTAX			Counter64 
		MAX-ACCESS		read-only
		STATUS			current
		DESCRIPTION		"Mo Description"
		::=  {  nptACLifRxCosTotalEntry  13  }
        
	nptACLifRxCosTotalPassOctets	OBJECT-TYPE	
		SYNTAX			Counter64 
		MAX-ACCESS		read-only
		STATUS			current
		DESCRIPTION		"Mo Description"
		::=  {  nptACLifRxCosTotalEntry  14  }
        
	nptACLifRxCosTotalPassPkts	OBJECT-TYPE	
		SYNTAX			Counter64 
		MAX-ACCESS		read-only
		STATUS			current
		DESCRIPTION		"Mo Description"
		::=  {  nptACLifRxCosTotalEntry  15  }
        
	nptACLifRxCosTotalDiscardOctets	OBJECT-TYPE	
		SYNTAX			Counter64 
		MAX-ACCESS		read-only
		STATUS			current
		DESCRIPTION		"Mo Description"
		::=  {  nptACLifRxCosTotalEntry  16  }
        
	nptACLifRxCosTotalDiscardPkts	OBJECT-TYPE	
		SYNTAX			Counter64 
		MAX-ACCESS		read-only
		STATUS			current
		DESCRIPTION		"Mo Description"
		::=  {  nptACLifRxCosTotalEntry  17  }
        
        
	nptACLifTxCosCurrentTable	OBJECT-TYPE
		SYNTAX		SEQUENCE  OF  NptACLifTxCosCurrentEntry
		MAX-ACCESS	not-accessible
		STATUS		current
		DESCRIPTION	"The Lif current table contains various statistics
            being collected for the current 15 minute
            interval."
		::=  { nptACLifTxCosGroup  1 }

	nptACLifTxCosCurrentEntry	OBJECT-TYPE
		SYNTAX		NptACLifTxCosCurrentEntry
		MAX-ACCESS	not-accessible
		STATUS		current
		DESCRIPTION	"An entry in the Lif Total table."
		INDEX		{  nptACLifTxCosCurrentIndex  }
		::=  { nptACLifTxCosCurrentTable 1 }

	NptACLifTxCosCurrentEntry  ::=  SEQUENCE {
		nptACLifTxCosCurrentIndex  Integer32,
        nptACLifTxCosCurrentLifIndex  Integer32,
		nptACLifTxCosCurrentMoDescription  DisplayString,
        nptACLifTxCosCurrentCosID  Integer32,
        nptACLifTxCosCurrentPmState  DisplayString,
		nptACLifTxCosCurrentPassGreenOctets  Counter64,
        nptACLifTxCosCurrentPassYellowOctets  Counter64, 
		nptACLifTxCosCurrentDiscardGreenOrYellowOctets  Counter64,
		nptACLifTxCosCurrentDiscardRedOctets  Counter64,
        nptACLifTxCosCurrentPassGreenPkts  Counter64,
        nptACLifTxCosCurrentPassYellowPkts  Counter64,
        nptACLifTxCosCurrentDiscardGreenOrYellowPkts  Counter64,
        nptACLifTxCosCurrentDiscardRedPkts  Counter64,
        nptACLifTxCosCurrentPassOctets  Counter64,
        nptACLifTxCosCurrentPassPkts  Counter64,
        nptACLifTxCosCurrentDiscardOctets  Counter64,
        nptACLifTxCosCurrentDiscardPkts  Counter64
		}

	nptACLifTxCosCurrentIndex	OBJECT-TYPE	
		SYNTAX			Integer32  ( -2147483648 .. 2147483647  ) 
		MAX-ACCESS		read-only
		STATUS			current
		DESCRIPTION		"The index value which uniquely identifies  the
            Lif interface to which this entry is applicable."
		::=  {  nptACLifTxCosCurrentEntry  1  }
        
	nptACLifTxCosCurrentLifIndex	OBJECT-TYPE	
		SYNTAX			Integer32  ( -2147483648 .. 2147483647  ) 
		MAX-ACCESS		read-only
		STATUS			current
		DESCRIPTION		"Mo Description"
		::=  {  nptACLifTxCosCurrentEntry  2  }
		
	nptACLifTxCosCurrentMoDescription	OBJECT-TYPE	
		SYNTAX			DisplayString 
		MAX-ACCESS		read-only
		STATUS			current
		DESCRIPTION		"Mo Description"
		::=  {  nptACLifTxCosCurrentEntry  3  }
        
	nptACLifTxCosCurrentCosID	OBJECT-TYPE	
		SYNTAX			Integer32
		MAX-ACCESS		read-only
		STATUS			current
		DESCRIPTION		"The index value which uniquely identifies  the
            Lif interface to which this entry is applicable."
		::=  {  nptACLifTxCosCurrentEntry  4  }
        
	nptACLifTxCosCurrentPmState	OBJECT-TYPE	
		SYNTAX			DisplayString 
		MAX-ACCESS		read-only
		STATUS			current
		DESCRIPTION		"Mo Description"
		::=  {  nptACLifTxCosCurrentEntry  5  }
        
	nptACLifTxCosCurrentPassGreenOctets 	OBJECT-TYPE	
		SYNTAX			Counter64 
		MAX-ACCESS		read-only
		STATUS			current
		DESCRIPTION		"Mo Description"
		::=  {  nptACLifTxCosCurrentEntry  6  }
        
	nptACLifTxCosCurrentPassYellowOctets 	OBJECT-TYPE	
		SYNTAX			Counter64 
		MAX-ACCESS		read-only
		STATUS			current
		DESCRIPTION		"Mo Description"
		::=  {  nptACLifTxCosCurrentEntry  7  }
        
	nptACLifTxCosCurrentDiscardGreenOrYellowOctets	OBJECT-TYPE	
		SYNTAX		Counter64 
		MAX-ACCESS		read-only
		STATUS			current
		DESCRIPTION		"Mo Description"
		::=  {  nptACLifTxCosCurrentEntry  8  }
        
	nptACLifTxCosCurrentDiscardRedOctets	OBJECT-TYPE	
		SYNTAX			Counter64 
		MAX-ACCESS		read-only
		STATUS			current
		DESCRIPTION		"Mo Description"
		::=  {  nptACLifTxCosCurrentEntry  9  }
        
	nptACLifTxCosCurrentPassGreenPkts	OBJECT-TYPE	
		SYNTAX			Counter64 
		MAX-ACCESS		read-only
		STATUS			current
		DESCRIPTION		"Mo Description"
		::=  {  nptACLifTxCosCurrentEntry  10  }
        
	nptACLifTxCosCurrentPassYellowPkts	OBJECT-TYPE	
		SYNTAX			Counter64 
		MAX-ACCESS		read-only
		STATUS			current
		DESCRIPTION		"Mo Description"
		::=  {  nptACLifTxCosCurrentEntry  11  }
        
	nptACLifTxCosCurrentDiscardGreenOrYellowPkts	OBJECT-TYPE	
		SYNTAX			Counter64 
		MAX-ACCESS		read-only
		STATUS			current
		DESCRIPTION		"Mo Description"
		::=  {  nptACLifTxCosCurrentEntry  12  }
        
	nptACLifTxCosCurrentDiscardRedPkts	OBJECT-TYPE	
		SYNTAX			Counter64 
		MAX-ACCESS		read-only
		STATUS			current
		DESCRIPTION		"Mo Description"
		::=  {  nptACLifTxCosCurrentEntry  13  }
        
	nptACLifTxCosCurrentPassOctets	OBJECT-TYPE	
		SYNTAX			Counter64 
		MAX-ACCESS		read-only
		STATUS			current
		DESCRIPTION		"Mo Description"
		::=  {  nptACLifTxCosCurrentEntry  14  }
        
	nptACLifTxCosCurrentPassPkts	OBJECT-TYPE	
		SYNTAX			Counter64 
		MAX-ACCESS		read-only
		STATUS			current
		DESCRIPTION		"Mo Description"
		::=  {  nptACLifTxCosCurrentEntry  15  }
        
	nptACLifTxCosCurrentDiscardOctets	OBJECT-TYPE	
		SYNTAX			Counter64 
		MAX-ACCESS		read-only
		STATUS			current
		DESCRIPTION		"Mo Description"
		::=  {  nptACLifTxCosCurrentEntry  16  }
        
	nptACLifTxCosCurrentDiscardPkts	OBJECT-TYPE	
		SYNTAX			Counter64 
		MAX-ACCESS		read-only
		STATUS			current
		DESCRIPTION		"Mo Description"
		::=  {  nptACLifTxCosCurrentEntry  17  }
        

	nptACLifTxCosTotalTable	OBJECT-TYPE
		SYNTAX		SEQUENCE  OF  NptACLifTxCosTotalEntry
		MAX-ACCESS	not-accessible
		STATUS		current
		DESCRIPTION	"The Lif total table contains various statistics
            being collected for the history 24 hours
            interval."
		::=  { nptACLifTxCosGroup  2 }

	nptACLifTxCosTotalEntry	OBJECT-TYPE
		SYNTAX		NptACLifTxCosTotalEntry
		MAX-ACCESS	not-accessible
		STATUS		current
		DESCRIPTION	"An entry in the Lif Total table."
		INDEX		{  nptACLifTxCosTotalIndex  }
		::=  { nptACLifTxCosTotalTable 1 }

	NptACLifTxCosTotalEntry  ::=  SEQUENCE {
		nptACLifTxCosTotalIndex  Integer32,
        nptACLifTxCosTotalLifIndex  Integer32,
		nptACLifTxCosTotalMoDescription  DisplayString,
        nptACLifTxCosTotalCosID  Integer32,
        nptACLifTxCosTotalPmState  DisplayString,
		nptACLifTxCosTotalPassGreenOctets  Counter64,
        nptACLifTxCosTotalPassYellowOctets  Counter64, 
		nptACLifTxCosTotalDiscardGreenOrYellowOctets  Counter64,
		nptACLifTxCosTotalDiscardRedOctets  Counter64,
        nptACLifTxCosTotalPassGreenPkts  Counter64,
        nptACLifTxCosTotalPassYellowPkts  Counter64,
        nptACLifTxCosTotalDiscardGreenOrYellowPkts  Counter64,
        nptACLifTxCosTotalDiscardRedPkts  Counter64,
        nptACLifTxCosTotalPassOctets  Counter64,
        nptACLifTxCosTotalPassPkts  Counter64,
        nptACLifTxCosTotalDiscardOctets  Counter64,
        nptACLifTxCosTotalDiscardPkts  Counter64
		}

	nptACLifTxCosTotalIndex	OBJECT-TYPE	
		SYNTAX			Integer32  ( -2147483648 .. 2147483647  ) 
		MAX-ACCESS		read-only
		STATUS			current
		DESCRIPTION		"The index value which uniquely identifies  the
            Lif interface to which this entry is applicable."
		::=  {  nptACLifTxCosTotalEntry  1  }
        
	nptACLifTxCosTotalLifIndex	OBJECT-TYPE	
		SYNTAX			Integer32  ( -2147483648 .. 2147483647  ) 
		MAX-ACCESS		read-only
		STATUS			current
		DESCRIPTION		"Mo Description"
		::=  {  nptACLifTxCosTotalEntry  2  }
		
	nptACLifTxCosTotalMoDescription	OBJECT-TYPE	
		SYNTAX			DisplayString 
		MAX-ACCESS		read-only
		STATUS			current
		DESCRIPTION		"Mo Description"
		::=  {  nptACLifTxCosTotalEntry  3  }
        
	nptACLifTxCosTotalCosID	OBJECT-TYPE	
		SYNTAX			Integer32
		MAX-ACCESS		read-only
		STATUS			current
		DESCRIPTION		"The index value which uniquely identifies  the
            Lif interface to which this entry is applicable."
		::=  {  nptACLifTxCosTotalEntry  4  }
        
	nptACLifTxCosTotalPmState	OBJECT-TYPE	
		SYNTAX			DisplayString 
		MAX-ACCESS		read-only
		STATUS			current
		DESCRIPTION		"Mo Description"
		::=  {  nptACLifTxCosTotalEntry  5  }
        
	nptACLifTxCosTotalPassGreenOctets 	OBJECT-TYPE	
		SYNTAX			Counter64 
		MAX-ACCESS		read-only
		STATUS			current
		DESCRIPTION		"Mo Description"
		::=  {  nptACLifTxCosTotalEntry  6  }
        
	nptACLifTxCosTotalPassYellowOctets 	OBJECT-TYPE	
		SYNTAX			Counter64 
		MAX-ACCESS		read-only
		STATUS			current
		DESCRIPTION		"Mo Description"
		::=  {  nptACLifTxCosTotalEntry  7  }
        
	nptACLifTxCosTotalDiscardGreenOrYellowOctets	OBJECT-TYPE	
		SYNTAX		Counter64 
		MAX-ACCESS		read-only
		STATUS			current
		DESCRIPTION		"Mo Description"
		::=  {  nptACLifTxCosTotalEntry  8  }
        
	nptACLifTxCosTotalDiscardRedOctets	OBJECT-TYPE	
		SYNTAX			Counter64 
		MAX-ACCESS		read-only
		STATUS			current
		DESCRIPTION		"Mo Description"
		::=  {  nptACLifTxCosTotalEntry  9  }
        
	nptACLifTxCosTotalPassGreenPkts	OBJECT-TYPE	
		SYNTAX			Counter64 
		MAX-ACCESS		read-only
		STATUS			current
		DESCRIPTION		"Mo Description"
		::=  {  nptACLifTxCosTotalEntry  10  }
        
	nptACLifTxCosTotalPassYellowPkts	OBJECT-TYPE	
		SYNTAX			Counter64 
		MAX-ACCESS		read-only
		STATUS			current
		DESCRIPTION		"Mo Description"
		::=  {  nptACLifTxCosTotalEntry  11  }
        
	nptACLifTxCosTotalDiscardGreenOrYellowPkts	OBJECT-TYPE	
		SYNTAX			Counter64 
		MAX-ACCESS		read-only
		STATUS			current
		DESCRIPTION		"Mo Description"
		::=  {  nptACLifTxCosTotalEntry  12  }
        
	nptACLifTxCosTotalDiscardRedPkts	OBJECT-TYPE	
		SYNTAX			Counter64 
		MAX-ACCESS		read-only
		STATUS			current
		DESCRIPTION		"Mo Description"
		::=  {  nptACLifTxCosTotalEntry  13  }
        
	nptACLifTxCosTotalPassOctets	OBJECT-TYPE	
		SYNTAX			Counter64 
		MAX-ACCESS		read-only
		STATUS			current
		DESCRIPTION		"Mo Description"
		::=  {  nptACLifTxCosTotalEntry  14  }
        
	nptACLifTxCosTotalPassPkts	OBJECT-TYPE	
		SYNTAX			Counter64 
		MAX-ACCESS		read-only
		STATUS			current
		DESCRIPTION		"Mo Description"
		::=  {  nptACLifTxCosTotalEntry  15  }
        
	nptACLifTxCosTotalDiscardOctets	OBJECT-TYPE	
		SYNTAX			Counter64 
		MAX-ACCESS		read-only
		STATUS			current
		DESCRIPTION		"Mo Description"
		::=  {  nptACLifTxCosTotalEntry  16  }
        
	nptACLifTxCosTotalDiscardPkts	OBJECT-TYPE	
		SYNTAX			Counter64 
		MAX-ACCESS		read-only
		STATUS			current
		DESCRIPTION		"Mo Description"
		::=  {  nptACLifTxCosTotalEntry  17  }
        

	nptL3LifCurrentTable	OBJECT-TYPE
		SYNTAX		SEQUENCE  OF  NptL3LifCurrentEntry
		MAX-ACCESS	not-accessible
		STATUS		current
		DESCRIPTION	"The Lif current table contains various statistics
            being collected for the current 15 minute
            interval."
		::=  { nptL3LifGroup  1 }

	nptL3LifCurrentEntry	OBJECT-TYPE
		SYNTAX		NptL3LifCurrentEntry
		MAX-ACCESS	not-accessible
		STATUS		current
		DESCRIPTION	"An entry in the Lif Total table."
		INDEX		{  nptL3LifCurrentIndex  }
		::=  { nptL3LifCurrentTable 1 }

	NptL3LifCurrentEntry  ::=  SEQUENCE {
		nptL3LifCurrentIndex  Integer32,
		nptL3LifCurrentMoDescription  DisplayString,
        nptL3LifCurrentRxPassOctets  Counter64,
		nptL3LifCurrentRxPassPkts  Counter64,
        nptL3LifCurrentRxDiscardOctets  Counter64, 
        nptL3LifCurrentRxDiscardPkts  Counter64, 
        nptL3LifCurrentTxPassOctets  Counter64,
		nptL3LifCurrentTxPassPkts  Counter64,
        nptL3LifCurrentTxDiscardOctets  Counter64,
		nptL3LifCurrentTxDiscardPkts  Counter64
		}

	nptL3LifCurrentIndex	OBJECT-TYPE	
		SYNTAX			Integer32  ( -2147483648 .. 2147483647  ) 
		MAX-ACCESS		read-only
		STATUS			current
		DESCRIPTION		"The index value which uniquely identifies  the
            Lif interfL3e to which this entry is applicable."
		::=  {  nptL3LifCurrentEntry  1  }
		
	nptL3LifCurrentMoDescription	OBJECT-TYPE	
		SYNTAX			DisplayString 
		MAX-ACCESS		read-only
		STATUS			current
		DESCRIPTION		"Mo Description"
		::=  {  nptL3LifCurrentEntry  2  }
        
	nptL3LifCurrentRxPassOctets 	OBJECT-TYPE	
		SYNTAX			Counter64 
		MAX-ACCESS		read-only
		STATUS			current
		DESCRIPTION		"Mo Description"
		::=  {  nptL3LifCurrentEntry  3  }
        
	nptL3LifCurrentRxPassPkts 	OBJECT-TYPE	
		SYNTAX			Counter64 
		MAX-ACCESS		read-only
		STATUS			current
		DESCRIPTION		"Mo Description"
		::=  {  nptL3LifCurrentEntry  4  }
        
	nptL3LifCurrentRxDiscardOctets	OBJECT-TYPE	
		SYNTAX		Counter64 
		MAX-ACCESS		read-only
		STATUS			current
		DESCRIPTION		"Mo Description"
		::=  {  nptL3LifCurrentEntry  5  }
        
	nptL3LifCurrentRxDiscardPkts	OBJECT-TYPE	
		SYNTAX		Counter64 
		MAX-ACCESS		read-only
		STATUS			current
		DESCRIPTION		"Mo Description"
		::=  {  nptL3LifCurrentEntry  6  }
        
	nptL3LifCurrentTxPassOctets	OBJECT-TYPE	
		SYNTAX			Counter64 
		MAX-ACCESS		read-only
		STATUS			current
		DESCRIPTION		"Mo Description"
		::=  {  nptL3LifCurrentEntry  7  }
        
	nptL3LifCurrentTxPassPkts	OBJECT-TYPE	
		SYNTAX			Counter64 
		MAX-ACCESS		read-only
		STATUS			current
		DESCRIPTION		"Mo Description"
		::=  {  nptL3LifCurrentEntry  8  }
        
	nptL3LifCurrentTxDiscardOctets	OBJECT-TYPE	
		SYNTAX			Counter64 
		MAX-ACCESS		read-only
		STATUS			current
		DESCRIPTION		"Mo Description"
		::=  {  nptL3LifCurrentEntry  9  }
        
	nptL3LifCurrentTxDiscardPkts	OBJECT-TYPE	
		SYNTAX			Counter64 
		MAX-ACCESS		read-only
		STATUS			current
		DESCRIPTION		"Mo Description"
		::=  {  nptL3LifCurrentEntry  10  }

	nptL3LifTotalTable	OBJECT-TYPE
		SYNTAX		SEQUENCE  OF  NptL3LifTotalEntry
		MAX-ACCESS	not-accessible
		STATUS		current
		DESCRIPTION	"The Lif current table contains various statistics
            being collected for the current 15 minute
            interval."
		::=  { nptL3LifGroup  2 }

	nptL3LifTotalEntry	OBJECT-TYPE
		SYNTAX		NptL3LifTotalEntry
		MAX-ACCESS	not-accessible
		STATUS		current
		DESCRIPTION	"An entry in the Lif Total table."
		INDEX		{  nptL3LifTotalIndex  }
		::=  { nptL3LifTotalTable 1 }

	NptL3LifTotalEntry  ::=  SEQUENCE {
		nptL3LifTotalIndex  Integer32,
		nptL3LifTotalMoDescription  DisplayString,
		nptL3LifTotalRxPassOctets  Counter64,
        nptL3LifTotalRxPassPkts  Counter64,
        nptL3LifTotalRxDiscardOctets  Counter64, 
        nptL3LifTotalRxDiscardPkts  Counter64, 
        nptL3LifTotalTxPassOctets  Counter64,
		nptL3LifTotalTxPassPkts  Counter64,
        nptL3LifTotalTxDiscardOctets  Counter64,
		nptL3LifTotalTxDiscardPkts  Counter64
		}

	nptL3LifTotalIndex	OBJECT-TYPE	
		SYNTAX			Integer32  ( -2147483648 .. 2147483647  ) 
		MAX-ACCESS		read-only
		STATUS			current
		DESCRIPTION		"The index value which uniquely identifies  the
            Lif interfL3e to which this entry is applicable."
		::=  {  nptL3LifTotalEntry  1  }
		
	nptL3LifTotalMoDescription	OBJECT-TYPE	
		SYNTAX			DisplayString 
		MAX-ACCESS		read-only
		STATUS			current
		DESCRIPTION		"Mo Description"
		::=  {  nptL3LifTotalEntry  2  }
        
	nptL3LifTotalRxPassOctets 	OBJECT-TYPE	
		SYNTAX			Counter64 
		MAX-ACCESS		read-only
		STATUS			current
		DESCRIPTION		"Mo Description"
		::=  {  nptL3LifTotalEntry  3  }
        
	nptL3LifTotalRxPassPkts 	OBJECT-TYPE	
		SYNTAX			Counter64 
		MAX-ACCESS		read-only
		STATUS			current
		DESCRIPTION		"Mo Description"
		::=  {  nptL3LifTotalEntry  4  }
        
	nptL3LifTotalRxDiscardOctets	OBJECT-TYPE	
		SYNTAX		Counter64 
		MAX-ACCESS		read-only
		STATUS			current
		DESCRIPTION		"Mo Description"
		::=  {  nptL3LifTotalEntry  5  }
        
	nptL3LifTotalRxDiscardPkts	OBJECT-TYPE	
		SYNTAX		Counter64 
		MAX-ACCESS		read-only
		STATUS			current
		DESCRIPTION		"Mo Description"
		::=  {  nptL3LifTotalEntry  6  }
        
	nptL3LifTotalTxPassOctets	OBJECT-TYPE	
		SYNTAX			Counter64 
		MAX-ACCESS		read-only
		STATUS			current
		DESCRIPTION		"Mo Description"
		::=  {  nptL3LifTotalEntry  7  }
        
	nptL3LifTotalTxPassPkts	OBJECT-TYPE	
		SYNTAX			Counter64 
		MAX-ACCESS		read-only
		STATUS			current
		DESCRIPTION		"Mo Description"
		::=  {  nptL3LifTotalEntry  8  }
        
	nptL3LifTotalTxDiscardOctets	OBJECT-TYPE	
		SYNTAX			Counter64 
		MAX-ACCESS		read-only
		STATUS			current
		DESCRIPTION		"Mo Description"
		::=  {  nptL3LifTotalEntry  9  }
        
	nptL3LifTotalTxDiscardPkts	OBJECT-TYPE	
		SYNTAX			Counter64 
		MAX-ACCESS		read-only
		STATUS			current
		DESCRIPTION		"Mo Description"
		::=  {  nptL3LifTotalEntry  10  }
        
        
	nptL3LifRxCosCurrentTable	OBJECT-TYPE
		SYNTAX		SEQUENCE  OF  NptL3LifRxCosCurrentEntry
		MAX-ACCESS	not-accessible
		STATUS		current
		DESCRIPTION	"The Lif current table contains various statistics
            being collected for the current 15 minute
            interval."
		::=  { nptL3LifRxCosGroup  1 }

	nptL3LifRxCosCurrentEntry	OBJECT-TYPE
		SYNTAX		NptL3LifRxCosCurrentEntry
		MAX-ACCESS	not-accessible
		STATUS		current
		DESCRIPTION	"An entry in the Lif Total table."
		INDEX		{  nptL3LifRxCosCurrentIndex  }
		::=  { nptL3LifRxCosCurrentTable 1 }

	NptL3LifRxCosCurrentEntry  ::=  SEQUENCE {
		nptL3LifRxCosCurrentIndex  Integer32,
        nptL3LifRxCosCurrentLifIndex  Integer32,
		nptL3LifRxCosCurrentMoDescription  DisplayString,
        nptL3LifRxCosCurrentCosID  Integer32,
        nptL3LifRxCosCurrentPmState  DisplayString,
		nptL3LifRxCosCurrentPassGreenOctets  Counter64,
        nptL3LifRxCosCurrentPassYellowOctets  Counter64, 
		nptL3LifRxCosCurrentDiscardGreenOrYellowOctets  Counter64,
		nptL3LifRxCosCurrentDiscardRedOctets  Counter64,
        nptL3LifRxCosCurrentPassGreenPkts  Counter64,
        nptL3LifRxCosCurrentPassYellowPkts  Counter64,
        nptL3LifRxCosCurrentDiscardGreenOrYellowPkts  Counter64,
        nptL3LifRxCosCurrentDiscardRedPkts  Counter64,
        nptL3LifRxCosCurrentPassOctets  Counter64,
        nptL3LifRxCosCurrentPassPkts  Counter64,
        nptL3LifRxCosCurrentDiscardOctets  Counter64,
        nptL3LifRxCosCurrentDiscardPkts  Counter64
		}

	nptL3LifRxCosCurrentIndex	OBJECT-TYPE	
		SYNTAX			Integer32  ( -2147483648 .. 2147483647  ) 
		MAX-ACCESS		read-only
		STATUS			current
		DESCRIPTION		"The index value which uniquely identifies  the
            Lif interfL3e to which this entry is applicable."
		::=  {  nptL3LifRxCosCurrentEntry  1  }
        
	nptL3LifRxCosCurrentLifIndex	OBJECT-TYPE	
		SYNTAX			Integer32  ( -2147483648 .. 2147483647  ) 
		MAX-ACCESS		read-only
		STATUS			current
		DESCRIPTION		"Mo Description"
		::=  {  nptL3LifRxCosCurrentEntry  2  }
		
	nptL3LifRxCosCurrentMoDescription	OBJECT-TYPE	
		SYNTAX			DisplayString 
		MAX-ACCESS		read-only
		STATUS			current
		DESCRIPTION		"Mo Description"
		::=  {  nptL3LifRxCosCurrentEntry  3  }
        
	nptL3LifRxCosCurrentCosID	OBJECT-TYPE	
		SYNTAX			Integer32
		MAX-ACCESS		read-only
		STATUS			current
		DESCRIPTION		"The index value which uniquely identifies  the
            Lif interfL3e to which this entry is applicable."
		::=  {  nptL3LifRxCosCurrentEntry  4  }
        
	nptL3LifRxCosCurrentPmState	OBJECT-TYPE	
		SYNTAX			DisplayString 
		MAX-ACCESS		read-only
		STATUS			current
		DESCRIPTION		"Mo Description"
		::=  {  nptL3LifRxCosCurrentEntry  5  }
        
	nptL3LifRxCosCurrentPassGreenOctets 	OBJECT-TYPE	
		SYNTAX			Counter64 
		MAX-ACCESS		read-only
		STATUS			current
		DESCRIPTION		"Mo Description"
		::=  {  nptL3LifRxCosCurrentEntry  6  }
        
	nptL3LifRxCosCurrentPassYellowOctets 	OBJECT-TYPE	
		SYNTAX			Counter64 
		MAX-ACCESS		read-only
		STATUS			current
		DESCRIPTION		"Mo Description"
		::=  {  nptL3LifRxCosCurrentEntry  7  }
        
	nptL3LifRxCosCurrentDiscardGreenOrYellowOctets	OBJECT-TYPE	
		SYNTAX		Counter64 
		MAX-ACCESS		read-only
		STATUS			current
		DESCRIPTION		"Mo Description"
		::=  {  nptL3LifRxCosCurrentEntry  8  }
        
	nptL3LifRxCosCurrentDiscardRedOctets	OBJECT-TYPE	
		SYNTAX			Counter64 
		MAX-ACCESS		read-only
		STATUS			current
		DESCRIPTION		"Mo Description"
		::=  {  nptL3LifRxCosCurrentEntry  9  }
        
	nptL3LifRxCosCurrentPassGreenPkts	OBJECT-TYPE	
		SYNTAX			Counter64 
		MAX-ACCESS		read-only
		STATUS			current
		DESCRIPTION		"Mo Description"
		::=  {  nptL3LifRxCosCurrentEntry  10  }
        
	nptL3LifRxCosCurrentPassYellowPkts	OBJECT-TYPE	
		SYNTAX			Counter64 
		MAX-ACCESS		read-only
		STATUS			current
		DESCRIPTION		"Mo Description"
		::=  {  nptL3LifRxCosCurrentEntry  11  }
        
	nptL3LifRxCosCurrentDiscardGreenOrYellowPkts	OBJECT-TYPE	
		SYNTAX			Counter64 
		MAX-ACCESS		read-only
		STATUS			current
		DESCRIPTION		"Mo Description"
		::=  {  nptL3LifRxCosCurrentEntry  12  }
        
	nptL3LifRxCosCurrentDiscardRedPkts	OBJECT-TYPE	
		SYNTAX			Counter64 
		MAX-ACCESS		read-only
		STATUS			current
		DESCRIPTION		"Mo Description"
		::=  {  nptL3LifRxCosCurrentEntry  13  }
        
	nptL3LifRxCosCurrentPassOctets	OBJECT-TYPE	
		SYNTAX			Counter64 
		MAX-ACCESS		read-only
		STATUS			current
		DESCRIPTION		"Mo Description"
		::=  {  nptL3LifRxCosCurrentEntry  14  }
        
	nptL3LifRxCosCurrentPassPkts	OBJECT-TYPE	
		SYNTAX			Counter64 
		MAX-ACCESS		read-only
		STATUS			current
		DESCRIPTION		"Mo Description"
		::=  {  nptL3LifRxCosCurrentEntry  15  }
        
	nptL3LifRxCosCurrentDiscardOctets	OBJECT-TYPE	
		SYNTAX			Counter64 
		MAX-ACCESS		read-only
		STATUS			current
		DESCRIPTION		"Mo Description"
		::=  {  nptL3LifRxCosCurrentEntry  16  }
        
	nptL3LifRxCosCurrentDiscardPkts	OBJECT-TYPE	
		SYNTAX			Counter64 
		MAX-ACCESS		read-only
		STATUS			current
		DESCRIPTION		"Mo Description"
		::=  {  nptL3LifRxCosCurrentEntry  17  }
        

	nptL3LifRxCosTotalTable	OBJECT-TYPE
		SYNTAX		SEQUENCE  OF  NptL3LifRxCosTotalEntry
		MAX-ACCESS	not-accessible
		STATUS		current
		DESCRIPTION	"The Lif total table contains various statistics
            being collected for the history 24 hours
            interval."
		::=  { nptL3LifRxCosGroup  2 }

	nptL3LifRxCosTotalEntry	OBJECT-TYPE
		SYNTAX		NptL3LifRxCosTotalEntry
		MAX-ACCESS	not-accessible
		STATUS		current
		DESCRIPTION	"An entry in the Lif Total table."
		INDEX		{  nptL3LifRxCosTotalIndex  }
		::=  { nptL3LifRxCosTotalTable 1 }

	NptL3LifRxCosTotalEntry  ::=  SEQUENCE {
		nptL3LifRxCosTotalIndex  Integer32,
        nptL3LifRxCosTotalLifIndex  Integer32,
		nptL3LifRxCosTotalMoDescription  DisplayString,
        nptL3LifRxCosTotalCosID  Integer32,
        nptL3LifRxCosTotalPmState  DisplayString,
		nptL3LifRxCosTotalPassGreenOctets  Counter64,
        nptL3LifRxCosTotalPassYellowOctets  Counter64, 
		nptL3LifRxCosTotalDiscardGreenOrYellowOctets  Counter64,
		nptL3LifRxCosTotalDiscardRedOctets  Counter64,
        nptL3LifRxCosTotalPassGreenPkts  Counter64,
        nptL3LifRxCosTotalPassYellowPkts  Counter64,
        nptL3LifRxCosTotalDiscardGreenOrYellowPkts  Counter64,
        nptL3LifRxCosTotalDiscardRedPkts  Counter64,
        nptL3LifRxCosTotalPassOctets  Counter64,
        nptL3LifRxCosTotalPassPkts  Counter64,
        nptL3LifRxCosTotalDiscardOctets  Counter64,
        nptL3LifRxCosTotalDiscardPkts  Counter64
		}

	nptL3LifRxCosTotalIndex	OBJECT-TYPE	
		SYNTAX			Integer32  ( -2147483648 .. 2147483647  ) 
		MAX-ACCESS		read-only
		STATUS			current
		DESCRIPTION		"The index value which uniquely identifies  the
            Lif interfL3e to which this entry is applicable."
		::=  {  nptL3LifRxCosTotalEntry  1  }
		
	nptL3LifRxCosTotalLifIndex	OBJECT-TYPE	
		SYNTAX			Integer32  ( -2147483648 .. 2147483647  ) 
		MAX-ACCESS		read-only
		STATUS			current
		DESCRIPTION		"Mo Description"
		::=  {  nptL3LifRxCosTotalEntry  2  }
        
	nptL3LifRxCosTotalMoDescription	OBJECT-TYPE	
		SYNTAX			DisplayString 
		MAX-ACCESS		read-only
		STATUS			current
		DESCRIPTION		"Mo Description"
		::=  {  nptL3LifRxCosTotalEntry  3  }
        
	nptL3LifRxCosTotalCosID	OBJECT-TYPE	
		SYNTAX			Integer32
		MAX-ACCESS		read-only
		STATUS			current
		DESCRIPTION		"The index value which uniquely identifies  the
            Lif interfL3e to which this entry is applicable."
		::=  {  nptL3LifRxCosTotalEntry  4  }
        
	nptL3LifRxCosTotalPmState	OBJECT-TYPE	
		SYNTAX			DisplayString 
		MAX-ACCESS		read-only
		STATUS			current
		DESCRIPTION		"Mo Description"
		::=  {  nptL3LifRxCosTotalEntry  5  }
        
	nptL3LifRxCosTotalPassGreenOctets 	OBJECT-TYPE	
		SYNTAX			Counter64 
		MAX-ACCESS		read-only
		STATUS			current
		DESCRIPTION		"Mo Description"
		::=  {  nptL3LifRxCosTotalEntry  6  }
        
	nptL3LifRxCosTotalPassYellowOctets 	OBJECT-TYPE	
		SYNTAX			Counter64 
		MAX-ACCESS		read-only
		STATUS			current
		DESCRIPTION		"Mo Description"
		::=  {  nptL3LifRxCosTotalEntry  7  }
        
	nptL3LifRxCosTotalDiscardGreenOrYellowOctets	OBJECT-TYPE	
		SYNTAX		Counter64 
		MAX-ACCESS		read-only
		STATUS			current
		DESCRIPTION		"Mo Description"
		::=  {  nptL3LifRxCosTotalEntry  8  }
        
	nptL3LifRxCosTotalDiscardRedOctets	OBJECT-TYPE	
		SYNTAX			Counter64 
		MAX-ACCESS		read-only
		STATUS			current
		DESCRIPTION		"Mo Description"
		::=  {  nptL3LifRxCosTotalEntry  9  }
        
	nptL3LifRxCosTotalPassGreenPkts	OBJECT-TYPE	
		SYNTAX			Counter64 
		MAX-ACCESS		read-only
		STATUS			current
		DESCRIPTION		"Mo Description"
		::=  {  nptL3LifRxCosTotalEntry  10  }
        
	nptL3LifRxCosTotalPassYellowPkts	OBJECT-TYPE	
		SYNTAX			Counter64 
		MAX-ACCESS		read-only
		STATUS			current
		DESCRIPTION		"Mo Description"
		::=  {  nptL3LifRxCosTotalEntry  11  }
        
	nptL3LifRxCosTotalDiscardGreenOrYellowPkts	OBJECT-TYPE	
		SYNTAX			Counter64 
		MAX-ACCESS		read-only
		STATUS			current
		DESCRIPTION		"Mo Description"
		::=  {  nptL3LifRxCosTotalEntry  12  }
        
	nptL3LifRxCosTotalDiscardRedPkts	OBJECT-TYPE	
		SYNTAX			Counter64 
		MAX-ACCESS		read-only
		STATUS			current
		DESCRIPTION		"Mo Description"
		::=  {  nptL3LifRxCosTotalEntry  13  }
        
	nptL3LifRxCosTotalPassOctets	OBJECT-TYPE	
		SYNTAX			Counter64 
		MAX-ACCESS		read-only
		STATUS			current
		DESCRIPTION		"Mo Description"
		::=  {  nptL3LifRxCosTotalEntry  14  }
        
	nptL3LifRxCosTotalPassPkts	OBJECT-TYPE	
		SYNTAX			Counter64 
		MAX-ACCESS		read-only
		STATUS			current
		DESCRIPTION		"Mo Description"
		::=  {  nptL3LifRxCosTotalEntry  15  }
        
	nptL3LifRxCosTotalDiscardOctets	OBJECT-TYPE	
		SYNTAX			Counter64 
		MAX-ACCESS		read-only
		STATUS			current
		DESCRIPTION		"Mo Description"
		::=  {  nptL3LifRxCosTotalEntry  16  }
        
	nptL3LifRxCosTotalDiscardPkts	OBJECT-TYPE	
		SYNTAX			Counter64 
		MAX-ACCESS		read-only
		STATUS			current
		DESCRIPTION		"Mo Description"
		::=  {  nptL3LifRxCosTotalEntry  17  }
        
        
	nptL3LifTxCosCurrentTable	OBJECT-TYPE
		SYNTAX		SEQUENCE  OF  NptL3LifTxCosCurrentEntry
		MAX-ACCESS	not-accessible
		STATUS		current
		DESCRIPTION	"The Lif current table contains various statistics
            being collected for the current 15 minute
            interval."
		::=  { nptL3LifTxCosGroup  1 }

	nptL3LifTxCosCurrentEntry	OBJECT-TYPE
		SYNTAX		NptL3LifTxCosCurrentEntry
		MAX-ACCESS	not-accessible
		STATUS		current
		DESCRIPTION	"An entry in the Lif Total table."
		INDEX		{  nptL3LifTxCosCurrentIndex  }
		::=  { nptL3LifTxCosCurrentTable 1 }

	NptL3LifTxCosCurrentEntry  ::=  SEQUENCE {
		nptL3LifTxCosCurrentIndex  Integer32,
        nptL3LifTxCosCurrentLifIndex  Integer32,
		nptL3LifTxCosCurrentMoDescription  DisplayString,
        nptL3LifTxCosCurrentCosID  Integer32,
        nptL3LifTxCosCurrentPmState  DisplayString,
		nptL3LifTxCosCurrentPassGreenOctets  Counter64,
        nptL3LifTxCosCurrentPassYellowOctets  Counter64, 
		nptL3LifTxCosCurrentDiscardGreenOrYellowOctets  Counter64,
		nptL3LifTxCosCurrentDiscardRedOctets  Counter64,
        nptL3LifTxCosCurrentPassGreenPkts  Counter64,
        nptL3LifTxCosCurrentPassYellowPkts  Counter64,
        nptL3LifTxCosCurrentDiscardGreenOrYellowPkts  Counter64,
        nptL3LifTxCosCurrentDiscardRedPkts  Counter64,
        nptL3LifTxCosCurrentPassOctets  Counter64,
        nptL3LifTxCosCurrentPassPkts  Counter64,
        nptL3LifTxCosCurrentDiscardOctets  Counter64,
        nptL3LifTxCosCurrentDiscardPkts  Counter64
		}

	nptL3LifTxCosCurrentIndex	OBJECT-TYPE	
		SYNTAX			Integer32  ( -2147483648 .. 2147483647  ) 
		MAX-ACCESS		read-only
		STATUS			current
		DESCRIPTION		"The index value which uniquely identifies  the
            Lif interfL3e to which this entry is applicable."
		::=  {  nptL3LifTxCosCurrentEntry  1  }
        
	nptL3LifTxCosCurrentLifIndex	OBJECT-TYPE	
		SYNTAX			Integer32  ( -2147483648 .. 2147483647  ) 
		MAX-ACCESS		read-only
		STATUS			current
		DESCRIPTION		"The index value which uniquely identifies  the
            Lif interfL3e to which this entry is applicable."
		::=  {  nptL3LifTxCosCurrentEntry  2  }
		
	nptL3LifTxCosCurrentMoDescription	OBJECT-TYPE	
		SYNTAX			DisplayString 
		MAX-ACCESS		read-only
		STATUS			current
		DESCRIPTION		"Mo Description"
		::=  {  nptL3LifTxCosCurrentEntry  3  }
        
	nptL3LifTxCosCurrentCosID	OBJECT-TYPE	
		SYNTAX			Integer32
		MAX-ACCESS		read-only
		STATUS			current
		DESCRIPTION		"The index value which uniquely identifies  the
            Lif interfL3e to which this entry is applicable."
		::=  {  nptL3LifTxCosCurrentEntry  4  }
        
	nptL3LifTxCosCurrentPmState	OBJECT-TYPE	
		SYNTAX			DisplayString 
		MAX-ACCESS		read-only
		STATUS			current
		DESCRIPTION		"Mo Description"
		::=  {  nptL3LifTxCosCurrentEntry  5  }
        
	nptL3LifTxCosCurrentPassGreenOctets 	OBJECT-TYPE	
		SYNTAX			Counter64 
		MAX-ACCESS		read-only
		STATUS			current
		DESCRIPTION		"Mo Description"
		::=  {  nptL3LifTxCosCurrentEntry  6  }
        
	nptL3LifTxCosCurrentPassYellowOctets 	OBJECT-TYPE	
		SYNTAX			Counter64 
		MAX-ACCESS		read-only
		STATUS			current
		DESCRIPTION		"Mo Description"
		::=  {  nptL3LifTxCosCurrentEntry  7  }
        
	nptL3LifTxCosCurrentDiscardGreenOrYellowOctets	OBJECT-TYPE	
		SYNTAX		Counter64 
		MAX-ACCESS		read-only
		STATUS			current
		DESCRIPTION		"Mo Description"
		::=  {  nptL3LifTxCosCurrentEntry  8  }
        
	nptL3LifTxCosCurrentDiscardRedOctets	OBJECT-TYPE	
		SYNTAX			Counter64 
		MAX-ACCESS		read-only
		STATUS			current
		DESCRIPTION		"Mo Description"
		::=  {  nptL3LifTxCosCurrentEntry  9  }
        
	nptL3LifTxCosCurrentPassGreenPkts	OBJECT-TYPE	
		SYNTAX			Counter64 
		MAX-ACCESS		read-only
		STATUS			current
		DESCRIPTION		"Mo Description"
		::=  {  nptL3LifTxCosCurrentEntry  10  }
        
	nptL3LifTxCosCurrentPassYellowPkts	OBJECT-TYPE	
		SYNTAX			Counter64 
		MAX-ACCESS		read-only
		STATUS			current
		DESCRIPTION		"Mo Description"
		::=  {  nptL3LifTxCosCurrentEntry  11  }
        
	nptL3LifTxCosCurrentDiscardGreenOrYellowPkts	OBJECT-TYPE	
		SYNTAX			Counter64 
		MAX-ACCESS		read-only
		STATUS			current
		DESCRIPTION		"Mo Description"
		::=  {  nptL3LifTxCosCurrentEntry  12  }
        
	nptL3LifTxCosCurrentDiscardRedPkts	OBJECT-TYPE	
		SYNTAX			Counter64 
		MAX-ACCESS		read-only
		STATUS			current
		DESCRIPTION		"Mo Description"
		::=  {  nptL3LifTxCosCurrentEntry  13  }
        
	nptL3LifTxCosCurrentPassOctets	OBJECT-TYPE	
		SYNTAX			Counter64 
		MAX-ACCESS		read-only
		STATUS			current
		DESCRIPTION		"Mo Description"
		::=  {  nptL3LifTxCosCurrentEntry  14  }
        
	nptL3LifTxCosCurrentPassPkts	OBJECT-TYPE	
		SYNTAX			Counter64 
		MAX-ACCESS		read-only
		STATUS			current
		DESCRIPTION		"Mo Description"
		::=  {  nptL3LifTxCosCurrentEntry  15  }
        
	nptL3LifTxCosCurrentDiscardOctets	OBJECT-TYPE	
		SYNTAX			Counter64 
		MAX-ACCESS		read-only
		STATUS			current
		DESCRIPTION		"Mo Description"
		::=  {  nptL3LifTxCosCurrentEntry  16  }
        
	nptL3LifTxCosCurrentDiscardPkts	OBJECT-TYPE	
		SYNTAX			Counter64 
		MAX-ACCESS		read-only
		STATUS			current
		DESCRIPTION		"Mo Description"
		::=  {  nptL3LifTxCosCurrentEntry  17  }
        

	nptL3LifTxCosTotalTable	OBJECT-TYPE
		SYNTAX		SEQUENCE  OF  NptL3LifTxCosTotalEntry
		MAX-ACCESS	not-accessible
		STATUS		current
		DESCRIPTION	"The Lif total table contains various statistics
            being collected for the history 24 hours
            interval."
		::=  { nptL3LifTxCosGroup  2 }

	nptL3LifTxCosTotalEntry	OBJECT-TYPE
		SYNTAX		NptL3LifTxCosTotalEntry
		MAX-ACCESS	not-accessible
		STATUS		current
		DESCRIPTION	"An entry in the Lif Total table."
		INDEX		{  nptL3LifTxCosTotalIndex  }
		::=  { nptL3LifTxCosTotalTable 1 }

	NptL3LifTxCosTotalEntry  ::=  SEQUENCE {
		nptL3LifTxCosTotalIndex  Integer32,
        nptL3LifTxCosTotalLifIndex  Integer32,
		nptL3LifTxCosTotalMoDescription  DisplayString,
        nptL3LifTxCosTotalCosID  Integer32,
        nptL3LifTxCosTotalPmState  DisplayString,
		nptL3LifTxCosTotalPassGreenOctets  Counter64,
        nptL3LifTxCosTotalPassYellowOctets  Counter64, 
		nptL3LifTxCosTotalDiscardGreenOrYellowOctets  Counter64,
		nptL3LifTxCosTotalDiscardRedOctets  Counter64,
        nptL3LifTxCosTotalPassGreenPkts  Counter64,
        nptL3LifTxCosTotalPassYellowPkts  Counter64,
        nptL3LifTxCosTotalDiscardGreenOrYellowPkts  Counter64,
        nptL3LifTxCosTotalDiscardRedPkts  Counter64,
        nptL3LifTxCosTotalPassOctets  Counter64,
        nptL3LifTxCosTotalPassPkts  Counter64,
        nptL3LifTxCosTotalDiscardOctets  Counter64,
        nptL3LifTxCosTotalDiscardPkts  Counter64
		}

	nptL3LifTxCosTotalIndex	OBJECT-TYPE	
		SYNTAX			Integer32  ( -2147483648 .. 2147483647  ) 
		MAX-ACCESS		read-only
		STATUS			current
		DESCRIPTION		"The index value which uniquely identifies  the
            Lif interfL3e to which this entry is applicable."
		::=  {  nptL3LifTxCosTotalEntry  1  }
        
	nptL3LifTxCosTotalLifIndex	OBJECT-TYPE	
		SYNTAX			Integer32  ( -2147483648 .. 2147483647  ) 
		MAX-ACCESS		read-only
		STATUS			current
		DESCRIPTION		"Mo Description"
		::=  {  nptL3LifTxCosTotalEntry  2  }
		
	nptL3LifTxCosTotalMoDescription	OBJECT-TYPE	
		SYNTAX			DisplayString 
		MAX-ACCESS		read-only
		STATUS			current
		DESCRIPTION		"Mo Description"
		::=  {  nptL3LifTxCosTotalEntry  3  }
        
	nptL3LifTxCosTotalCosID	OBJECT-TYPE	
		SYNTAX			Integer32
		MAX-ACCESS		read-only
		STATUS			current
		DESCRIPTION		"Mo Description"
		::=  {  nptL3LifTxCosTotalEntry  4  }
        
	nptL3LifTxCosTotalPmState	OBJECT-TYPE	
		SYNTAX			DisplayString 
		MAX-ACCESS		read-only
		STATUS			current
		DESCRIPTION		"Mo Description"
		::=  {  nptL3LifTxCosTotalEntry  5  }
        
	nptL3LifTxCosTotalPassGreenOctets 	OBJECT-TYPE	
		SYNTAX			Counter64 
		MAX-ACCESS		read-only
		STATUS			current
		DESCRIPTION		"Mo Description"
		::=  {  nptL3LifTxCosTotalEntry  6  }
        
	nptL3LifTxCosTotalPassYellowOctets 	OBJECT-TYPE	
		SYNTAX			Counter64 
		MAX-ACCESS		read-only
		STATUS			current
		DESCRIPTION		"Mo Description"
		::=  {  nptL3LifTxCosTotalEntry  7  }
        
	nptL3LifTxCosTotalDiscardGreenOrYellowOctets	OBJECT-TYPE	
		SYNTAX		Counter64 
		MAX-ACCESS		read-only
		STATUS			current
		DESCRIPTION		"Mo Description"
		::=  {  nptL3LifTxCosTotalEntry  8  }
        
	nptL3LifTxCosTotalDiscardRedOctets	OBJECT-TYPE	
		SYNTAX			Counter64 
		MAX-ACCESS		read-only
		STATUS			current
		DESCRIPTION		"Mo Description"
		::=  {  nptL3LifTxCosTotalEntry  9  }
        
	nptL3LifTxCosTotalPassGreenPkts	OBJECT-TYPE	
		SYNTAX			Counter64 
		MAX-ACCESS		read-only
		STATUS			current
		DESCRIPTION		"Mo Description"
		::=  {  nptL3LifTxCosTotalEntry  10  }
        
	nptL3LifTxCosTotalPassYellowPkts	OBJECT-TYPE	
		SYNTAX			Counter64 
		MAX-ACCESS		read-only
		STATUS			current
		DESCRIPTION		"Mo Description"
		::=  {  nptL3LifTxCosTotalEntry  11  }
        
	nptL3LifTxCosTotalDiscardGreenOrYellowPkts	OBJECT-TYPE	
		SYNTAX			Counter64 
		MAX-ACCESS		read-only
		STATUS			current
		DESCRIPTION		"Mo Description"
		::=  {  nptL3LifTxCosTotalEntry  12  }
        
	nptL3LifTxCosTotalDiscardRedPkts	OBJECT-TYPE	
		SYNTAX			Counter64 
		MAX-ACCESS		read-only
		STATUS			current
		DESCRIPTION		"Mo Description"
		::=  {  nptL3LifTxCosTotalEntry  13  }
        
	nptL3LifTxCosTotalPassOctets	OBJECT-TYPE	
		SYNTAX			Counter64 
		MAX-ACCESS		read-only
		STATUS			current
		DESCRIPTION		"Mo Description"
		::=  {  nptL3LifTxCosTotalEntry  14  }
        
	nptL3LifTxCosTotalPassPkts	OBJECT-TYPE	
		SYNTAX			Counter64 
		MAX-ACCESS		read-only
		STATUS			current
		DESCRIPTION		"Mo Description"
		::=  {  nptL3LifTxCosTotalEntry  15  }
        
	nptL3LifTxCosTotalDiscardOctets	OBJECT-TYPE	
		SYNTAX			Counter64 
		MAX-ACCESS		read-only
		STATUS			current
		DESCRIPTION		"Mo Description"
		::=  {  nptL3LifTxCosTotalEntry  16  }
        
	nptL3LifTxCosTotalDiscardPkts	OBJECT-TYPE	
		SYNTAX			Counter64 
		MAX-ACCESS		read-only
		STATUS			current
		DESCRIPTION		"Mo Description"
		::=  {  nptL3LifTxCosTotalEntry  17  }
        
        
	nptFlexEChannelCurrentTable	OBJECT-TYPE
		SYNTAX		SEQUENCE  OF  NptFlexEChannelCurrentEntry
		MAX-ACCESS	not-accessible
		STATUS		current
		DESCRIPTION	"The Lif current table contains various statistics
            being collected for the current 15 minute
            interval."
		::=  { nptFlexEChannelGroup  1 }

	nptFlexEChannelCurrentEntry	OBJECT-TYPE
		SYNTAX		NptFlexEChannelCurrentEntry
		MAX-ACCESS	not-accessible
		STATUS		current
		DESCRIPTION	"An entry in the Lif Total table."
		INDEX		{  nptFlexEChannelCurrentIndex  }
		::=  { nptFlexEChannelCurrentTable 1 }

	NptFlexEChannelCurrentEntry  ::=  SEQUENCE {
		nptFlexEChannelCurrentIndex  Integer32,
		nptFlexEChannelCurrentMoDescription  DisplayString,
        nptFlexEChannelCurrentBIPErrorCounter  Counter64,
        nptFlexEChannelCurrentREICounter  Counter64,
		nptFlexEChannelCurrentCRCErrorPackets  Counter64,
        nptFlexEChannelCurrentBASRxPackets  Counter64, 
		nptFlexEChannelCurrentBASTxPackets  Counter64,
		nptFlexEChannelCurrentAPSRxPackets  Counter64,
        nptFlexEChannelCurrentAPSTxPackets  Counter64,
        nptFlexEChannelCurrentCSRxPackets  Counter64,
        nptFlexEChannelCurrentCSTxPackets  Counter64,
        nptFlexEChannelCurrentCVRxPackets  Counter64,
        nptFlexEChannelCurrentCVTxPackets  Counter64,
        nptFlexEChannelCurrent1DMRxPackets  Counter64,
        nptFlexEChannelCurrent1DMTxPackets  Counter64,
        nptFlexEChannelCurrent2DMMRxPackets  Counter64,
        nptFlexEChannelCurrent2DMMTxPackets  Counter64,
        nptFlexEChannelCurrent2DMRRxPackets  Counter64,
        nptFlexEChannelCurrent2DMRTxPackets  Counter64,
        nptFlexEChannelCurrentCURFD  Counter64,
        nptFlexEChannelCurrentAverageFD  Counter64,
        nptFlexEChannelCurrentMinimumFD  Counter64,
        nptFlexEChannelCurrentMaximumFD  Counter64,
        nptFlexEChannelCurrentCURFDV  Counter64,
        nptFlexEChannelCurrentAverageFDV  Counter64,
        nptFlexEChannelCurrentMinimumFDV  Counter64,
        nptFlexEChannelCurrentMaximumFDV  Counter64
		}

	nptFlexEChannelCurrentIndex	OBJECT-TYPE	
		SYNTAX			Integer32  ( -2147483648 .. 2147483647  ) 
		MAX-ACCESS		read-only
		STATUS			current
		DESCRIPTION		"The index value which uniquely identifies  the
            Lif interfL3e to which this entry is applicable."
		::=  {  nptFlexEChannelCurrentEntry  1  }
        
		
	nptFlexEChannelCurrentMoDescription	OBJECT-TYPE	
		SYNTAX			DisplayString 
		MAX-ACCESS		read-only
		STATUS			current
		DESCRIPTION		"Mo Description"
		::=  {  nptFlexEChannelCurrentEntry  2  }
        
	nptFlexEChannelCurrentBIPErrorCounter	OBJECT-TYPE	
		SYNTAX			Counter64
		MAX-ACCESS		read-only
		STATUS			current
		DESCRIPTION		"The index value which uniquely identifies  the
            Lif interfL3e to which this entry is applicable."
		::=  {  nptFlexEChannelCurrentEntry  3  }
        
	nptFlexEChannelCurrentREICounter	OBJECT-TYPE	
		SYNTAX			Counter64 
		MAX-ACCESS		read-only
		STATUS			current
		DESCRIPTION		"Mo Description"
		::=  {  nptFlexEChannelCurrentEntry  4  }
        
	nptFlexEChannelCurrentCRCErrorPackets 	OBJECT-TYPE	
		SYNTAX			Counter64 
		MAX-ACCESS		read-only
		STATUS			current
		DESCRIPTION		"Mo Description"
		::=  {  nptFlexEChannelCurrentEntry  5  }
        
	nptFlexEChannelCurrentBASRxPackets 	OBJECT-TYPE	
		SYNTAX			Counter64 
		MAX-ACCESS		read-only
		STATUS			current
		DESCRIPTION		"Mo Description"
		::=  {  nptFlexEChannelCurrentEntry  6  }
        
	nptFlexEChannelCurrentBASTxPackets	OBJECT-TYPE	
		SYNTAX		Counter64 
		MAX-ACCESS		read-only
		STATUS			current
		DESCRIPTION		"Mo Description"
		::=  {  nptFlexEChannelCurrentEntry  7  }
        
	nptFlexEChannelCurrentAPSRxPackets	OBJECT-TYPE	
		SYNTAX			Counter64 
		MAX-ACCESS		read-only
		STATUS			current
		DESCRIPTION		"Mo Description"
		::=  {  nptFlexEChannelCurrentEntry  8  }
        
	nptFlexEChannelCurrentAPSTxPackets	OBJECT-TYPE	
		SYNTAX			Counter64 
		MAX-ACCESS		read-only
		STATUS			current
		DESCRIPTION		"Mo Description"
		::=  {  nptFlexEChannelCurrentEntry  9  }
        
	nptFlexEChannelCurrentCSRxPackets	OBJECT-TYPE	
		SYNTAX			Counter64 
		MAX-ACCESS		read-only
		STATUS			current
		DESCRIPTION		"Mo Description"
		::=  {  nptFlexEChannelCurrentEntry  10  }
        
	nptFlexEChannelCurrentCSTxPackets	OBJECT-TYPE	
		SYNTAX			Counter64 
		MAX-ACCESS		read-only
		STATUS			current
		DESCRIPTION		"Mo Description"
		::=  {  nptFlexEChannelCurrentEntry  11  }
        
	nptFlexEChannelCurrentCVRxPackets	OBJECT-TYPE	
		SYNTAX			Counter64 
		MAX-ACCESS		read-only
		STATUS			current
		DESCRIPTION		"Mo Description"
		::=  {  nptFlexEChannelCurrentEntry  12  }
        
	nptFlexEChannelCurrentCVTxPackets	OBJECT-TYPE	
		SYNTAX			Counter64 
		MAX-ACCESS		read-only
		STATUS			current
		DESCRIPTION		"Mo Description"
		::=  {  nptFlexEChannelCurrentEntry  13  }
        
	nptFlexEChannelCurrent1DMRxPackets	OBJECT-TYPE	
		SYNTAX			Counter64 
		MAX-ACCESS		read-only
		STATUS			current
		DESCRIPTION		"Mo Description"
		::=  {  nptFlexEChannelCurrentEntry  14  }
        
	nptFlexEChannelCurrent1DMTxPackets	OBJECT-TYPE	
		SYNTAX			Counter64 
		MAX-ACCESS		read-only
		STATUS			current
		DESCRIPTION		"Mo Description"
		::=  {  nptFlexEChannelCurrentEntry  15  }
        
	nptFlexEChannelCurrent2DMMRxPackets	OBJECT-TYPE	
		SYNTAX			Counter64 
		MAX-ACCESS		read-only
		STATUS			current
		DESCRIPTION		"Mo Description"
		::=  {  nptFlexEChannelCurrentEntry  16  }
        
	nptFlexEChannelCurrent2DMMTxPackets	OBJECT-TYPE	
		SYNTAX			Counter64 
		MAX-ACCESS		read-only
		STATUS			current
		DESCRIPTION		"Mo Description"
		::=  {  nptFlexEChannelCurrentEntry  17  }
        
	nptFlexEChannelCurrent2DMRRxPackets	OBJECT-TYPE	
		SYNTAX			Counter64 
		MAX-ACCESS		read-only
		STATUS			current
		DESCRIPTION		"Mo Description"
		::=  {  nptFlexEChannelCurrentEntry  18  }
        
	nptFlexEChannelCurrent2DMRTxPackets	OBJECT-TYPE	
		SYNTAX			Counter64 
		MAX-ACCESS		read-only
		STATUS			current
		DESCRIPTION		"Mo Description"
		::=  {  nptFlexEChannelCurrentEntry  19  }
        
	nptFlexEChannelCurrentCURFD	OBJECT-TYPE	
		SYNTAX			Counter64 
		MAX-ACCESS		read-only
		STATUS			current
		DESCRIPTION		"Mo Description"
		::=  {  nptFlexEChannelCurrentEntry  20  }
        
	nptFlexEChannelCurrentAverageFD	OBJECT-TYPE	
		SYNTAX			Counter64 
		MAX-ACCESS		read-only
		STATUS			current
		DESCRIPTION		"Mo Description"
		::=  {  nptFlexEChannelCurrentEntry  21  }
        
	nptFlexEChannelCurrentMinimumFD	OBJECT-TYPE	
		SYNTAX			Counter64 
		MAX-ACCESS		read-only
		STATUS			current
		DESCRIPTION		"Mo Description"
		::=  {  nptFlexEChannelCurrentEntry  22  }
        
	nptFlexEChannelCurrentMaximumFD	OBJECT-TYPE	
		SYNTAX			Counter64 
		MAX-ACCESS		read-only
		STATUS			current
		DESCRIPTION		"Mo Description"
		::=  {  nptFlexEChannelCurrentEntry  23  }
        
	nptFlexEChannelCurrentCURFDV	OBJECT-TYPE	
		SYNTAX			Counter64 
		MAX-ACCESS		read-only
		STATUS			current
		DESCRIPTION		"Mo Description"
		::=  {  nptFlexEChannelCurrentEntry  24  }
        
	nptFlexEChannelCurrentAverageFDV	OBJECT-TYPE	
		SYNTAX			Counter64 
		MAX-ACCESS		read-only
		STATUS			current
		DESCRIPTION		"Mo Description"
		::=  {  nptFlexEChannelCurrentEntry  25  }
        
	nptFlexEChannelCurrentMinimumFDV	OBJECT-TYPE	
		SYNTAX			Counter64 
		MAX-ACCESS		read-only
		STATUS			current
		DESCRIPTION		"Mo Description"
		::=  {  nptFlexEChannelCurrentEntry  26  }
        
	nptFlexEChannelCurrentMaximumFDV	OBJECT-TYPE	
		SYNTAX			Counter64 
		MAX-ACCESS		read-only
		STATUS			current
		DESCRIPTION		"Mo Description"
		::=  {  nptFlexEChannelCurrentEntry  27  }

	nptFlexEChannelTotalTable	OBJECT-TYPE
		SYNTAX		SEQUENCE  OF  NptFlexEChannelTotalEntry
		MAX-ACCESS	not-accessible
		STATUS		current
		DESCRIPTION	"The Lif total table contains various statistics
            being collected for the history 24 hours
            interval."
		::=  { nptFlexEChannelGroup  2 }

	nptFlexEChannelTotalEntry	OBJECT-TYPE
		SYNTAX		NptFlexEChannelTotalEntry
		MAX-ACCESS	not-accessible
		STATUS		current
		DESCRIPTION	"An entry in the Lif Total table."
		INDEX		{  nptFlexEChannelTotalIndex  }
		::=  { nptFlexEChannelTotalTable 1 }

	NptFlexEChannelTotalEntry  ::=  SEQUENCE {
		nptFlexEChannelTotalIndex  Integer32,
		nptFlexEChannelTotalMoDescription  DisplayString,
        nptFlexEChannelTotalBIPErrorCounter  Counter64,
        nptFlexEChannelTotalREICounter  Counter64,
		nptFlexEChannelTotalCRCErrorPackets  Counter64,
        nptFlexEChannelTotalBASRxPackets  Counter64, 
		nptFlexEChannelTotalBASTxPackets  Counter64,
		nptFlexEChannelTotalAPSRxPackets  Counter64,
        nptFlexEChannelTotalAPSTxPackets  Counter64,
        nptFlexEChannelTotalCSRxPackets  Counter64,
        nptFlexEChannelTotalCSTxPackets  Counter64,
        nptFlexEChannelTotalCVRxPackets  Counter64,
        nptFlexEChannelTotalCVTxPackets  Counter64,
        nptFlexEChannelTotal1DMRxPackets  Counter64,
        nptFlexEChannelTotal1DMTxPackets  Counter64,
        nptFlexEChannelTotal2DMMRxPackets  Counter64,
        nptFlexEChannelTotal2DMMTxPackets  Counter64,
        nptFlexEChannelTotal2DMRRxPackets  Counter64,
        nptFlexEChannelTotal2DMRTxPackets  Counter64,
        nptFlexEChannelTotalCURFD  Counter64,
        nptFlexEChannelTotalAverageFD  Counter64,
        nptFlexEChannelTotalMinimumFD  Counter64,
        nptFlexEChannelTotalMaximumFD  Counter64,
        nptFlexEChannelTotalCURFDV  Counter64,
        nptFlexEChannelTotalAverageFDV  Counter64,
        nptFlexEChannelTotalMinimumFDV  Counter64,
        nptFlexEChannelTotalMaximumFDV  Counter64
		}

	nptFlexEChannelTotalIndex	OBJECT-TYPE	
		SYNTAX			Integer32  ( -2147483648 .. 2147483647  ) 
		MAX-ACCESS		read-only
		STATUS			current
		DESCRIPTION		"The index value which uniquely identifies  the
            Lif interfL3e to which this entry is applicable."
		::=  {  nptFlexEChannelTotalEntry  1  }
        
		
	nptFlexEChannelTotalMoDescription	OBJECT-TYPE	
		SYNTAX			DisplayString 
		MAX-ACCESS		read-only
		STATUS			current
		DESCRIPTION		"Mo Description"
		::=  {  nptFlexEChannelTotalEntry  2  }
        
	nptFlexEChannelTotalBIPErrorCounter	OBJECT-TYPE	
		SYNTAX			Counter64
		MAX-ACCESS		read-only
		STATUS			current
		DESCRIPTION		"The index value which uniquely identifies  the
            Lif interfL3e to which this entry is applicable."
		::=  {  nptFlexEChannelTotalEntry  3  }
        
	nptFlexEChannelTotalREICounter	OBJECT-TYPE	
		SYNTAX			Counter64 
		MAX-ACCESS		read-only
		STATUS			current
		DESCRIPTION		"Mo Description"
		::=  {  nptFlexEChannelTotalEntry  4  }
        
	nptFlexEChannelTotalCRCErrorPackets 	OBJECT-TYPE	
		SYNTAX			Counter64 
		MAX-ACCESS		read-only
		STATUS			current
		DESCRIPTION		"Mo Description"
		::=  {  nptFlexEChannelTotalEntry  5  }
        
	nptFlexEChannelTotalBASRxPackets 	OBJECT-TYPE	
		SYNTAX			Counter64 
		MAX-ACCESS		read-only
		STATUS			current
		DESCRIPTION		"Mo Description"
		::=  {  nptFlexEChannelTotalEntry  6  }
        
	nptFlexEChannelTotalBASTxPackets	OBJECT-TYPE	
		SYNTAX		Counter64 
		MAX-ACCESS		read-only
		STATUS			current
		DESCRIPTION		"Mo Description"
		::=  {  nptFlexEChannelTotalEntry  7  }
        
	nptFlexEChannelTotalAPSRxPackets	OBJECT-TYPE	
		SYNTAX			Counter64 
		MAX-ACCESS		read-only
		STATUS			current
		DESCRIPTION		"Mo Description"
		::=  {  nptFlexEChannelTotalEntry  8  }
        
	nptFlexEChannelTotalAPSTxPackets	OBJECT-TYPE	
		SYNTAX			Counter64 
		MAX-ACCESS		read-only
		STATUS			current
		DESCRIPTION		"Mo Description"
		::=  {  nptFlexEChannelTotalEntry  9  }
        
	nptFlexEChannelTotalCSRxPackets	OBJECT-TYPE	
		SYNTAX			Counter64 
		MAX-ACCESS		read-only
		STATUS			current
		DESCRIPTION		"Mo Description"
		::=  {  nptFlexEChannelTotalEntry  10  }
        
	nptFlexEChannelTotalCSTxPackets	OBJECT-TYPE	
		SYNTAX			Counter64 
		MAX-ACCESS		read-only
		STATUS			current
		DESCRIPTION		"Mo Description"
		::=  {  nptFlexEChannelTotalEntry  11  }
        
	nptFlexEChannelTotalCVRxPackets	OBJECT-TYPE	
		SYNTAX			Counter64 
		MAX-ACCESS		read-only
		STATUS			current
		DESCRIPTION		"Mo Description"
		::=  {  nptFlexEChannelTotalEntry  12  }
        
	nptFlexEChannelTotalCVTxPackets	OBJECT-TYPE	
		SYNTAX			Counter64 
		MAX-ACCESS		read-only
		STATUS			current
		DESCRIPTION		"Mo Description"
		::=  {  nptFlexEChannelTotalEntry  13  }
        
	nptFlexEChannelTotal1DMRxPackets	OBJECT-TYPE	
		SYNTAX			Counter64 
		MAX-ACCESS		read-only
		STATUS			current
		DESCRIPTION		"Mo Description"
		::=  {  nptFlexEChannelTotalEntry  14  }
        
	nptFlexEChannelTotal1DMTxPackets	OBJECT-TYPE	
		SYNTAX			Counter64 
		MAX-ACCESS		read-only
		STATUS			current
		DESCRIPTION		"Mo Description"
		::=  {  nptFlexEChannelTotalEntry  15  }
        
	nptFlexEChannelTotal2DMMRxPackets	OBJECT-TYPE	
		SYNTAX			Counter64 
		MAX-ACCESS		read-only
		STATUS			current
		DESCRIPTION		"Mo Description"
		::=  {  nptFlexEChannelTotalEntry  16  }
        
	nptFlexEChannelTotal2DMMTxPackets	OBJECT-TYPE	
		SYNTAX			Counter64 
		MAX-ACCESS		read-only
		STATUS			current
		DESCRIPTION		"Mo Description"
		::=  {  nptFlexEChannelTotalEntry  17  }
        
	nptFlexEChannelTotal2DMRRxPackets	OBJECT-TYPE	
		SYNTAX			Counter64 
		MAX-ACCESS		read-only
		STATUS			current
		DESCRIPTION		"Mo Description"
		::=  {  nptFlexEChannelTotalEntry  18  }
        
	nptFlexEChannelTotal2DMRTxPackets	OBJECT-TYPE	
		SYNTAX			Counter64 
		MAX-ACCESS		read-only
		STATUS			current
		DESCRIPTION		"Mo Description"
		::=  {  nptFlexEChannelTotalEntry  19  }
        
	nptFlexEChannelTotalCURFD	OBJECT-TYPE	
		SYNTAX			Counter64 
		MAX-ACCESS		read-only
		STATUS			current
		DESCRIPTION		"Mo Description"
		::=  {  nptFlexEChannelTotalEntry  20  }
        
	nptFlexEChannelTotalAverageFD	OBJECT-TYPE	
		SYNTAX			Counter64 
		MAX-ACCESS		read-only
		STATUS			current
		DESCRIPTION		"Mo Description"
		::=  {  nptFlexEChannelTotalEntry  21  }
        
	nptFlexEChannelTotalMinimumFD	OBJECT-TYPE	
		SYNTAX			Counter64 
		MAX-ACCESS		read-only
		STATUS			current
		DESCRIPTION		"Mo Description"
		::=  {  nptFlexEChannelTotalEntry  22  }
        
	nptFlexEChannelTotalMaximumFD	OBJECT-TYPE	
		SYNTAX			Counter64 
		MAX-ACCESS		read-only
		STATUS			current
		DESCRIPTION		"Mo Description"
		::=  {  nptFlexEChannelTotalEntry  23  }
        
	nptFlexEChannelTotalCURFDV	OBJECT-TYPE	
		SYNTAX			Counter64 
		MAX-ACCESS		read-only
		STATUS			current
		DESCRIPTION		"Mo Description"
		::=  {  nptFlexEChannelTotalEntry  24  }
        
	nptFlexEChannelTotalAverageFDV	OBJECT-TYPE	
		SYNTAX			Counter64 
		MAX-ACCESS		read-only
		STATUS			current
		DESCRIPTION		"Mo Description"
		::=  {  nptFlexEChannelTotalEntry  25  }
        
	nptFlexEChannelTotalMinimumFDV	OBJECT-TYPE	
		SYNTAX			Counter64 
		MAX-ACCESS		read-only
		STATUS			current
		DESCRIPTION		"Mo Description"
		::=  {  nptFlexEChannelTotalEntry  26  }
        
	nptFlexEChannelTotalMaximumFDV	OBJECT-TYPE	
		SYNTAX			Counter64 
		MAX-ACCESS		read-only
		STATUS			current
		DESCRIPTION		"Mo Description"
		::=  {  nptFlexEChannelTotalEntry  27  }
        
        
	nptSPPCurrentTable	OBJECT-TYPE
		SYNTAX		SEQUENCE  OF  NptSPPCurrentEntry
		MAX-ACCESS	not-accessible
		STATUS		current
		DESCRIPTION	"The Lif current table contains various statistics
            being collected for the current 15 minute
            interval."
		::=  { nptSPPGroup  1 }

	nptSPPCurrentEntry	OBJECT-TYPE
		SYNTAX		NptSPPCurrentEntry
		MAX-ACCESS	not-accessible
		STATUS		current
		DESCRIPTION	"An entry in the Lif Total table."
		INDEX		{  nptSPPCurrentIndex  }
		::=  { nptSPPCurrentTable 1 }

	NptSPPCurrentEntry  ::=  SEQUENCE {
		nptSPPCurrentIndex  Integer32,
		nptSPPCurrentMoDescription  DisplayString,
        nptSPPCurrentRxGoodOctets  Counter64,
        nptSPPCurrentRxFrames  Counter64,
		nptSPPCurrentRxGoodFrames  Counter64,
        nptSPPCurrentRxBadFrames  Counter64, 
		nptSPPCurrentRxBroadcastFrames  Counter64,
		nptSPPCurrentRxMulticastFrames  Counter64,
        nptSPPCurrentRxUnicastFrames  Counter64,
        nptSPPCurrentRXFCSError  Counter64,
        nptSPPCurrentRxUndersizeFrames  Counter64,
        nptSPPCurrentRxOversizeFrames  Counter64,
        nptSPPCurrentRxPauseFrames  Counter64,
        nptSPPCurrentRx64octets  Counter64,
        nptSPPCurrentRx65to127octets  Counter64,
        nptSPPCurrentRx128to255octets  Counter64,
        nptSPPCurrentRx256to511octets  Counter64,
        nptSPPCurrentRx512to1023octets Counter64,
        nptSPPCurrentRx1024to1518octets  Counter64,
        nptSPPCurrentRx1519toMaxFrameSize  Counter64,
        nptSPPCurrentTxGoodOctets  Counter64,
        nptSPPCurrentTxGoodFrames  Counter64,
        nptSPPCurrentTxBadFrames  Counter64,
        nptSPPCurrentTxUndersizeFrames  Counter64,
        nptSPPCurrentTxOversizeFrames  Counter64,
        nptSPPCurrentTx64ctets  Counter64,
        nptSPPCurrentTx65to127octets  Counter64,
        nptSPPCurrentTx128to255octets  Counter64,
        nptSPPCurrentTx256to511octets  Counter64,
        nptSPPCurrentTx512to1023octets  Counter64,
        nptSPPCurrentTx1024to1518octets  Counter64,
        nptSPPCurrentTx1519toMaxFrameSize  Counter64
		}

	nptSPPCurrentIndex	OBJECT-TYPE	
		SYNTAX			Integer32  ( -2147483648 .. 2147483647  ) 
		MAX-ACCESS		read-only
		STATUS			current
		DESCRIPTION		"The index value which uniquely identifies  the
            Lif interfL3e to which this entry is applicable."
		::=  {  nptSPPCurrentEntry  1  }
        
		
	nptSPPCurrentMoDescription	OBJECT-TYPE	
		SYNTAX			DisplayString 
		MAX-ACCESS		read-only
		STATUS			current
		DESCRIPTION		"Mo Description"
		::=  {  nptSPPCurrentEntry  2  }
        
	nptSPPCurrentRxGoodOctets	OBJECT-TYPE	
		SYNTAX			Counter64
		MAX-ACCESS		read-only
		STATUS			current
		DESCRIPTION		""
		::=  {  nptSPPCurrentEntry  3  }
        
	nptSPPCurrentRxFrames	OBJECT-TYPE	
		SYNTAX			Counter64 
		MAX-ACCESS		read-only
		STATUS			current
		DESCRIPTION		"Mo Description"
		::=  {  nptSPPCurrentEntry  4  }
        
	nptSPPCurrentRxGoodFrames 	OBJECT-TYPE	
		SYNTAX			Counter64 
		MAX-ACCESS		read-only
		STATUS			current
		DESCRIPTION		"Mo Description"
		::=  {  nptSPPCurrentEntry  5  }
        
	nptSPPCurrentRxBadFrames 	OBJECT-TYPE	
		SYNTAX			Counter64 
		MAX-ACCESS		read-only
		STATUS			current
		DESCRIPTION		"Mo Description"
		::=  {  nptSPPCurrentEntry  6  }
        
	nptSPPCurrentRxBroadcastFrames	OBJECT-TYPE	
		SYNTAX		Counter64 
		MAX-ACCESS		read-only
		STATUS			current
		DESCRIPTION		"Mo Description"
		::=  {  nptSPPCurrentEntry  7  }
        
	nptSPPCurrentRxMulticastFrames	OBJECT-TYPE	
		SYNTAX			Counter64 
		MAX-ACCESS		read-only
		STATUS			current
		DESCRIPTION		"Mo Description"
		::=  {  nptSPPCurrentEntry  8  }
        
	nptSPPCurrentRxUnicastFrames	OBJECT-TYPE	
		SYNTAX			Counter64 
		MAX-ACCESS		read-only
		STATUS			current
		DESCRIPTION		"Mo Description"
		::=  {  nptSPPCurrentEntry  9  }
        
	nptSPPCurrentRXFCSError	OBJECT-TYPE	
		SYNTAX			Counter64 
		MAX-ACCESS		read-only
		STATUS			current
		DESCRIPTION		"Mo Description"
		::=  {  nptSPPCurrentEntry  10  }
        
	nptSPPCurrentRxUndersizeFrames	OBJECT-TYPE	
		SYNTAX			Counter64 
		MAX-ACCESS		read-only
		STATUS			current
		DESCRIPTION		"Mo Description"
		::=  {  nptSPPCurrentEntry  11  }
        
	nptSPPCurrentRxOversizeFrames	OBJECT-TYPE	
		SYNTAX			Counter64 
		MAX-ACCESS		read-only
		STATUS			current
		DESCRIPTION		"Mo Description"
		::=  {  nptSPPCurrentEntry  12  }
        
	nptSPPCurrentRxPauseFrames	OBJECT-TYPE	
		SYNTAX			Counter64 
		MAX-ACCESS		read-only
		STATUS			current
		DESCRIPTION		"Mo Description"
		::=  {  nptSPPCurrentEntry  13  }
        
	nptSPPCurrentRx64octets	OBJECT-TYPE	
		SYNTAX			Counter64 
		MAX-ACCESS		read-only
		STATUS			current
		DESCRIPTION		"Mo Description"
		::=  {  nptSPPCurrentEntry  14  }
        
	nptSPPCurrentRx65to127octets	OBJECT-TYPE	
		SYNTAX			Counter64 
		MAX-ACCESS		read-only
		STATUS			current
		DESCRIPTION		"Mo Description"
		::=  {  nptSPPCurrentEntry  15  }
        
	nptSPPCurrentRx128to255octets	OBJECT-TYPE	
		SYNTAX			Counter64 
		MAX-ACCESS		read-only
		STATUS			current
		DESCRIPTION		"Mo Description"
		::=  {  nptSPPCurrentEntry  16  }
        
	nptSPPCurrentRx256to511octets	OBJECT-TYPE	
		SYNTAX			Counter64 
		MAX-ACCESS		read-only
		STATUS			current
		DESCRIPTION		"Mo Description"
		::=  {  nptSPPCurrentEntry  17  }
        
	nptSPPCurrentRx512to1023octets	OBJECT-TYPE	
		SYNTAX			Counter64 
		MAX-ACCESS		read-only
		STATUS			current
		DESCRIPTION		"Mo Description"
		::=  {  nptSPPCurrentEntry  18  }
        
	nptSPPCurrentRx1024to1518octets	OBJECT-TYPE	
		SYNTAX			Counter64 
		MAX-ACCESS		read-only
		STATUS			current
		DESCRIPTION		"Mo Description"
		::=  {  nptSPPCurrentEntry  19  }
        
	nptSPPCurrentRx1519toMaxFrameSize 	OBJECT-TYPE	
		SYNTAX			Counter64 
		MAX-ACCESS		read-only
		STATUS			current
		DESCRIPTION		"Mo Description"
		::=  {  nptSPPCurrentEntry  20  }
        
	nptSPPCurrentTxGoodOctets	OBJECT-TYPE	
		SYNTAX			Counter64 
		MAX-ACCESS		read-only
		STATUS			current
		DESCRIPTION		"Mo Description"
		::=  {  nptSPPCurrentEntry  21  }
        
	nptSPPCurrentTxGoodFrames	OBJECT-TYPE	
		SYNTAX			Counter64 
		MAX-ACCESS		read-only
		STATUS			current
		DESCRIPTION		"Mo Description"
		::=  {  nptSPPCurrentEntry  22  }
        
	nptSPPCurrentTxBadFrames	OBJECT-TYPE	
		SYNTAX			Counter64 
		MAX-ACCESS		read-only
		STATUS			current
		DESCRIPTION		"Mo Description"
		::=  {  nptSPPCurrentEntry  23  }
        
	nptSPPCurrentTxUndersizeFrames	OBJECT-TYPE	
		SYNTAX			Counter64 
		MAX-ACCESS		read-only
		STATUS			current
		DESCRIPTION		"Mo Description"
		::=  {  nptSPPCurrentEntry  24  }
        
	nptSPPCurrentTxOversizeFrames	OBJECT-TYPE	
		SYNTAX			Counter64 
		MAX-ACCESS		read-only
		STATUS			current
		DESCRIPTION		"Mo Description"
		::=  {  nptSPPCurrentEntry  25  }
        
	nptSPPCurrentTx64ctets	OBJECT-TYPE	
		SYNTAX			Counter64 
		MAX-ACCESS		read-only
		STATUS			current
		DESCRIPTION		"Mo Description"
		::=  {  nptSPPCurrentEntry  26  }
        
	nptSPPCurrentTx65to127octets	OBJECT-TYPE	
		SYNTAX			Counter64 
		MAX-ACCESS		read-only
		STATUS			current
		DESCRIPTION		"Mo Description"
		::=  {  nptSPPCurrentEntry  27  }
        
	nptSPPCurrentTx128to255octets	OBJECT-TYPE	
		SYNTAX			Counter64 
		MAX-ACCESS		read-only
		STATUS			current
		DESCRIPTION		"Mo Description"
		::=  {  nptSPPCurrentEntry  28  }
        
	nptSPPCurrentTx256to511octets	OBJECT-TYPE	
		SYNTAX			Counter64 
		MAX-ACCESS		read-only
		STATUS			current
		DESCRIPTION		"Mo Description"
		::=  {  nptSPPCurrentEntry  29  }
        
	nptSPPCurrentTx512to1023octets	OBJECT-TYPE	
		SYNTAX			Counter64 
		MAX-ACCESS		read-only
		STATUS			current
		DESCRIPTION		"Mo Description"
		::=  {  nptSPPCurrentEntry  30  }
        
	nptSPPCurrentTx1024to1518octets	OBJECT-TYPE	
		SYNTAX			Counter64 
		MAX-ACCESS		read-only
		STATUS			current
		DESCRIPTION		"Mo Description"
		::=  {  nptSPPCurrentEntry  31  }
        
	nptSPPCurrentTx1519toMaxFrameSize	OBJECT-TYPE	
		SYNTAX			Counter64 
		MAX-ACCESS		read-only
		STATUS			current
		DESCRIPTION		"Mo Description"
		::=  {  nptSPPCurrentEntry  32  }

	nptSPPTotalTable	OBJECT-TYPE
		SYNTAX		SEQUENCE  OF  NptSPPTotalEntry
		MAX-ACCESS	not-accessible
		STATUS		current
		DESCRIPTION	"The Lif total table contains various statistics
            being collected for the history 24 hours
            interval."
		::=  { nptSPPGroup  2 }

	nptSPPTotalEntry	OBJECT-TYPE
		SYNTAX		NptSPPTotalEntry
		MAX-ACCESS	not-accessible
		STATUS		current
		DESCRIPTION	"An entry in the Lif Total table."
		INDEX		{  nptSPPTotalIndex  }
		::=  { nptSPPTotalTable 1 }

	NptSPPTotalEntry  ::=  SEQUENCE {
		nptSPPTotalIndex  Integer32,
		nptSPPTotalMoDescription  DisplayString,
        nptSPPTotalRxGoodOctets  Counter64,
        nptSPPTotalRxFrames  Counter64,
		nptSPPTotalRxGoodFrames  Counter64,
        nptSPPTotalRxBadFrames  Counter64, 
		nptSPPTotalRxBroadcastFrames  Counter64,
		nptSPPTotalRxMulticastFrames  Counter64,
        nptSPPTotalRxUnicastFrames  Counter64,
        nptSPPTotalRXFCSError  Counter64,
        nptSPPTotalRxUndersizeFrames  Counter64,
        nptSPPTotalRxOversizeFrames  Counter64,
        nptSPPTotalRxPauseFrames  Counter64,
        nptSPPTotalRx64octets  Counter64,
        nptSPPTotalRx65to127octets  Counter64,
        nptSPPTotalRx128to255octets  Counter64,
        nptSPPTotalRx256to511octets  Counter64,
        nptSPPTotalRx512to1023octets Counter64,
        nptSPPTotalRx1024to1518octets  Counter64,
        nptSPPTotalRx1519toMaxFrameSize  Counter64,
        nptSPPTotalTxGoodOctets  Counter64,
        nptSPPTotalTxGoodFrames  Counter64,
        nptSPPTotalTxBadFrames  Counter64,
        nptSPPTotalTxUndersizeFrames  Counter64,
        nptSPPTotalTxOversizeFrames  Counter64,
        nptSPPTotalTx64ctets  Counter64,
        nptSPPTotalTx65to127octets  Counter64,
        nptSPPTotalTx128to255octets  Counter64,
        nptSPPTotalTx256to511octets  Counter64,
        nptSPPTotalTx512to1023octets  Counter64,
        nptSPPTotalTx1024to1518octets  Counter64,
        nptSPPTotalTx1519toMaxFrameSize  Counter64
		}

	nptSPPTotalIndex	OBJECT-TYPE	
		SYNTAX			Integer32  ( -2147483648 .. 2147483647  ) 
		MAX-ACCESS		read-only
		STATUS			current
		DESCRIPTION		"The index value which uniquely identifies  the
            Lif interfL3e to which this entry is applicable."
		::=  {  nptSPPTotalEntry  1  }
        
		
	nptSPPTotalMoDescription	OBJECT-TYPE	
		SYNTAX			DisplayString 
		MAX-ACCESS		read-only
		STATUS			current
		DESCRIPTION		"Mo Description"
		::=  {  nptSPPTotalEntry  2  }
        
	nptSPPTotalRxGoodOctets	OBJECT-TYPE	
		SYNTAX			Counter64
		MAX-ACCESS		read-only
		STATUS			current
		DESCRIPTION		""
		::=  {  nptSPPTotalEntry  3  }
        
	nptSPPTotalRxFrames	OBJECT-TYPE	
		SYNTAX			Counter64 
		MAX-ACCESS		read-only
		STATUS			current
		DESCRIPTION		"Mo Description"
		::=  {  nptSPPTotalEntry  4  }
        
	nptSPPTotalRxGoodFrames 	OBJECT-TYPE	
		SYNTAX			Counter64 
		MAX-ACCESS		read-only
		STATUS			current
		DESCRIPTION		"Mo Description"
		::=  {  nptSPPTotalEntry  5  }
        
	nptSPPTotalRxBadFrames 	OBJECT-TYPE	
		SYNTAX			Counter64 
		MAX-ACCESS		read-only
		STATUS			current
		DESCRIPTION		"Mo Description"
		::=  {  nptSPPTotalEntry  6  }
        
	nptSPPTotalRxBroadcastFrames	OBJECT-TYPE	
		SYNTAX		Counter64 
		MAX-ACCESS		read-only
		STATUS			current
		DESCRIPTION		"Mo Description"
		::=  {  nptSPPTotalEntry  7  }
        
	nptSPPTotalRxMulticastFrames	OBJECT-TYPE	
		SYNTAX			Counter64 
		MAX-ACCESS		read-only
		STATUS			current
		DESCRIPTION		"Mo Description"
		::=  {  nptSPPTotalEntry  8  }
        
	nptSPPTotalRxUnicastFrames	OBJECT-TYPE	
		SYNTAX			Counter64 
		MAX-ACCESS		read-only
		STATUS			current
		DESCRIPTION		"Mo Description"
		::=  {  nptSPPTotalEntry  9  }
        
	nptSPPTotalRXFCSError	OBJECT-TYPE	
		SYNTAX			Counter64 
		MAX-ACCESS		read-only
		STATUS			current
		DESCRIPTION		"Mo Description"
		::=  {  nptSPPTotalEntry  10  }
        
	nptSPPTotalRxUndersizeFrames	OBJECT-TYPE	
		SYNTAX			Counter64 
		MAX-ACCESS		read-only
		STATUS			current
		DESCRIPTION		"Mo Description"
		::=  {  nptSPPTotalEntry  11  }
        
	nptSPPTotalRxOversizeFrames	OBJECT-TYPE	
		SYNTAX			Counter64 
		MAX-ACCESS		read-only
		STATUS			current
		DESCRIPTION		"Mo Description"
		::=  {  nptSPPTotalEntry  12  }
        
	nptSPPTotalRxPauseFrames	OBJECT-TYPE	
		SYNTAX			Counter64 
		MAX-ACCESS		read-only
		STATUS			current
		DESCRIPTION		"Mo Description"
		::=  {  nptSPPTotalEntry  13  }
        
	nptSPPTotalRx64octets	OBJECT-TYPE	
		SYNTAX			Counter64 
		MAX-ACCESS		read-only
		STATUS			current
		DESCRIPTION		"Mo Description"
		::=  {  nptSPPTotalEntry  14  }
        
	nptSPPTotalRx65to127octets	OBJECT-TYPE	
		SYNTAX			Counter64 
		MAX-ACCESS		read-only
		STATUS			current
		DESCRIPTION		"Mo Description"
		::=  {  nptSPPTotalEntry  15  }
        
	nptSPPTotalRx128to255octets	OBJECT-TYPE	
		SYNTAX			Counter64 
		MAX-ACCESS		read-only
		STATUS			current
		DESCRIPTION		"Mo Description"
		::=  {  nptSPPTotalEntry  16  }
        
	nptSPPTotalRx256to511octets	OBJECT-TYPE	
		SYNTAX			Counter64 
		MAX-ACCESS		read-only
		STATUS			current
		DESCRIPTION		"Mo Description"
		::=  {  nptSPPTotalEntry  17  }
        
	nptSPPTotalRx512to1023octets	OBJECT-TYPE	
		SYNTAX			Counter64 
		MAX-ACCESS		read-only
		STATUS			current
		DESCRIPTION		"Mo Description"
		::=  {  nptSPPTotalEntry  18  }
        
	nptSPPTotalRx1024to1518octets	OBJECT-TYPE	
		SYNTAX			Counter64 
		MAX-ACCESS		read-only
		STATUS			current
		DESCRIPTION		"Mo Description"
		::=  {  nptSPPTotalEntry  19  }
        
	nptSPPTotalRx1519toMaxFrameSize 	OBJECT-TYPE	
		SYNTAX			Counter64 
		MAX-ACCESS		read-only
		STATUS			current
		DESCRIPTION		"Mo Description"
		::=  {  nptSPPTotalEntry  20  }
        
	nptSPPTotalTxGoodOctets	OBJECT-TYPE	
		SYNTAX			Counter64 
		MAX-ACCESS		read-only
		STATUS			current
		DESCRIPTION		"Mo Description"
		::=  {  nptSPPTotalEntry  21  }
        
	nptSPPTotalTxGoodFrames	OBJECT-TYPE	
		SYNTAX			Counter64 
		MAX-ACCESS		read-only
		STATUS			current
		DESCRIPTION		"Mo Description"
		::=  {  nptSPPTotalEntry  22  }
        
	nptSPPTotalTxBadFrames	OBJECT-TYPE	
		SYNTAX			Counter64 
		MAX-ACCESS		read-only
		STATUS			current
		DESCRIPTION		"Mo Description"
		::=  {  nptSPPTotalEntry  23  }
        
	nptSPPTotalTxUndersizeFrames	OBJECT-TYPE	
		SYNTAX			Counter64 
		MAX-ACCESS		read-only
		STATUS			current
		DESCRIPTION		"Mo Description"
		::=  {  nptSPPTotalEntry  24  }
        
	nptSPPTotalTxOversizeFrames	OBJECT-TYPE	
		SYNTAX			Counter64 
		MAX-ACCESS		read-only
		STATUS			current
		DESCRIPTION		"Mo Description"
		::=  {  nptSPPTotalEntry  25  }
        
	nptSPPTotalTx64ctets	OBJECT-TYPE	
		SYNTAX			Counter64 
		MAX-ACCESS		read-only
		STATUS			current
		DESCRIPTION		"Mo Description"
		::=  {  nptSPPTotalEntry  26  }
        
	nptSPPTotalTx65to127octets	OBJECT-TYPE	
		SYNTAX			Counter64 
		MAX-ACCESS		read-only
		STATUS			current
		DESCRIPTION		"Mo Description"
		::=  {  nptSPPTotalEntry  27  }
        
	nptSPPTotalTx128to255octets	OBJECT-TYPE	
		SYNTAX			Counter64 
		MAX-ACCESS		read-only
		STATUS			current
		DESCRIPTION		"Mo Description"
		::=  {  nptSPPTotalEntry  28  }
        
	nptSPPTotalTx256to511octets	OBJECT-TYPE	
		SYNTAX			Counter64 
		MAX-ACCESS		read-only
		STATUS			current
		DESCRIPTION		"Mo Description"
		::=  {  nptSPPTotalEntry  29  }
        
	nptSPPTotalTx512to1023octets	OBJECT-TYPE	
		SYNTAX			Counter64 
		MAX-ACCESS		read-only
		STATUS			current
		DESCRIPTION		"Mo Description"
		::=  {  nptSPPTotalEntry  30  }
        
	nptSPPTotalTx1024to1518octets	OBJECT-TYPE	
		SYNTAX			Counter64 
		MAX-ACCESS		read-only
		STATUS			current
		DESCRIPTION		"Mo Description"
		::=  {  nptSPPTotalEntry  31  }
        
	nptSPPTotalTx1519toMaxFrameSize	OBJECT-TYPE	
		SYNTAX			Counter64 
		MAX-ACCESS		read-only
		STATUS			current
		DESCRIPTION		"Mo Description"
		::=  {  nptSPPTotalEntry  32  }
        
        
	nptFlexEPortCurrentTable	OBJECT-TYPE
		SYNTAX		SEQUENCE  OF  NptFlexEPortCurrentEntry
		MAX-ACCESS	not-accessible
		STATUS		current
		DESCRIPTION	"The Lif current table contains various statistics
            being collected for the current 15 minute
            interval."
		::=  { nptFlexEPortGroup  1 }

	nptFlexEPortCurrentEntry	OBJECT-TYPE
		SYNTAX		NptFlexEPortCurrentEntry
		MAX-ACCESS	not-accessible
		STATUS		current
		DESCRIPTION	"An entry in the Lif Total table."
		INDEX		{  nptFlexEPortCurrentIndex  }
		::=  { nptFlexEPortCurrentTable 1 }

	NptFlexEPortCurrentEntry  ::=  SEQUENCE {
		nptFlexEPortCurrentIndex  Integer32,
		nptFlexEPortCurrentMoDescription  DisplayString,
        nptFlexEPortCurrentMaxRxPower  DisplayString,
        nptFlexEPortCurrentMinRxPower  DisplayString,
		nptFlexEPortCurrentTxPower  DisplayString,
        nptFlexEPortCurrentOSNRMax  DisplayString, 
		nptFlexEPortCurrentOSNRMin  DisplayString
		}

	nptFlexEPortCurrentIndex	OBJECT-TYPE	
		SYNTAX			Integer32  ( -2147483648 .. 2147483647  ) 
		MAX-ACCESS		read-only
		STATUS			current
		DESCRIPTION		"The index value which uniquely identifies  the
            Lif interfL3e to which this entry is applicable."
		::=  {  nptFlexEPortCurrentEntry  1  }
        
		
	nptFlexEPortCurrentMoDescription	OBJECT-TYPE	
		SYNTAX			DisplayString 
		MAX-ACCESS		read-only
		STATUS			current
		DESCRIPTION		"Mo Description"
		::=  {  nptFlexEPortCurrentEntry  2  }
        
	nptFlexEPortCurrentMaxRxPower	OBJECT-TYPE	
		SYNTAX			DisplayString
		MAX-ACCESS		read-only
		STATUS			current
		DESCRIPTION		""
		::=  {  nptFlexEPortCurrentEntry  3  }
        
	nptFlexEPortCurrentMinRxPower	OBJECT-TYPE	
		SYNTAX			DisplayString 
		MAX-ACCESS		read-only
		STATUS			current
		DESCRIPTION		"Mo Description"
		::=  {  nptFlexEPortCurrentEntry  4  }
        
	nptFlexEPortCurrentTxPower 	OBJECT-TYPE	
		SYNTAX			DisplayString 
		MAX-ACCESS		read-only
		STATUS			current
		DESCRIPTION		"Mo Description"
		::=  {  nptFlexEPortCurrentEntry  5  }
        
	nptFlexEPortCurrentOSNRMax 	OBJECT-TYPE	
		SYNTAX			DisplayString 
		MAX-ACCESS		read-only
		STATUS			current
		DESCRIPTION		"Mo Description"
		::=  {  nptFlexEPortCurrentEntry  6  }
        
	nptFlexEPortCurrentOSNRMin	OBJECT-TYPE	
		SYNTAX		DisplayString 
		MAX-ACCESS		read-only
		STATUS			current
		DESCRIPTION		"Mo Description"
		::=  {  nptFlexEPortCurrentEntry  7  }

	nptFlexEPortTotalTable	OBJECT-TYPE
		SYNTAX		SEQUENCE  OF  NptFlexEPortTotalEntry
		MAX-ACCESS	not-accessible
		STATUS		current
		DESCRIPTION	"The Lif total table contains various statistics
            being collected for the history 24 hours
            interval."
		::=  { nptFlexEPortGroup  2 }

	nptFlexEPortTotalEntry	OBJECT-TYPE
		SYNTAX		NptFlexEPortTotalEntry
		MAX-ACCESS	not-accessible
		STATUS		current
		DESCRIPTION	"An entry in the Lif Total table."
		INDEX		{  nptFlexEPortTotalIndex  }
		::=  { nptFlexEPortTotalTable 1 }

	NptFlexEPortTotalEntry  ::=  SEQUENCE {
		nptFlexEPortTotalIndex  Integer32,
		nptFlexEPortTotalMoDescription  DisplayString,
        nptFlexEPortTotalMaxRxPower  DisplayString,
        nptFlexEPortTotalMinRxPower  DisplayString,
		nptFlexEPortTotalTxPower  DisplayString,
        nptFlexEPortTotalOSNRMax  DisplayString, 
		nptFlexEPortTotalOSNRMin  DisplayString
		}

	nptFlexEPortTotalIndex	OBJECT-TYPE	
		SYNTAX			Integer32  ( -2147483648 .. 2147483647  ) 
		MAX-ACCESS		read-only
		STATUS			current
		DESCRIPTION		"The index value which uniquely identifies  the
            Lif interfL3e to which this entry is applicable."
		::=  {  nptFlexEPortTotalEntry  1  }
        
		
	nptFlexEPortTotalMoDescription	OBJECT-TYPE	
		SYNTAX			DisplayString 
		MAX-ACCESS		read-only
		STATUS			current
		DESCRIPTION		"Mo Description"
		::=  {  nptFlexEPortTotalEntry  2  }
        
	nptFlexEPortTotalMaxRxPower	OBJECT-TYPE	
		SYNTAX			DisplayString
		MAX-ACCESS		read-only
		STATUS			current
		DESCRIPTION		""
		::=  {  nptFlexEPortTotalEntry  3  }
        
	nptFlexEPortTotalMinRxPower	OBJECT-TYPE	
		SYNTAX			DisplayString 
		MAX-ACCESS		read-only
		STATUS			current
		DESCRIPTION		"Mo Description"
		::=  {  nptFlexEPortTotalEntry  4  }
        
	nptFlexEPortTotalTxPower 	OBJECT-TYPE	
		SYNTAX			DisplayString 
		MAX-ACCESS		read-only
		STATUS			current
		DESCRIPTION		"Mo Description"
		::=  {  nptFlexEPortTotalEntry  5  }
        
	nptFlexEPortTotalOSNRMax 	OBJECT-TYPE	
		SYNTAX			DisplayString 
		MAX-ACCESS		read-only
		STATUS			current
		DESCRIPTION		"Mo Description"
		::=  {  nptFlexEPortTotalEntry  6  }
        
	nptFlexEPortTotalOSNRMin	OBJECT-TYPE	
		SYNTAX		DisplayString 
		MAX-ACCESS		read-only
		STATUS			current
		DESCRIPTION		"Mo Description"
		::=  {  nptFlexEPortTotalEntry  7  }
        
        
	nptTMUCurrentTable	OBJECT-TYPE
		SYNTAX		SEQUENCE  OF  NptTMUCurrentEntry
		MAX-ACCESS	not-accessible
		STATUS		current
		DESCRIPTION	"The Lif current table contains various statistics
            being collected for the current 15 minute
            interval."
		::=  { nptTMU  1 }

	nptTMUCurrentEntry	OBJECT-TYPE
		SYNTAX		NptTMUCurrentEntry
		MAX-ACCESS	not-accessible
		STATUS		current
		DESCRIPTION	"An entry in the Lif Total table."
		INDEX		{  nptTMUCurrentIndex  }
		::=  { nptTMUCurrentTable 1 }

	NptTMUCurrentEntry  ::=  SEQUENCE {
		nptTMUCurrentIndex  Integer32,
		nptTMUCurrentMoDescription  DisplayString,
        nptTMUCurrentT0FrequencyOffsetMax  DisplayString,
        nptTMUCurrentT0FrequencyOffsetMin  DisplayString,
		nptTMUCurrentT0FrequencyOffsetCur  DisplayString
		}

	nptTMUCurrentIndex	OBJECT-TYPE	
		SYNTAX			Integer32  ( -2147483648 .. 2147483647  ) 
		MAX-ACCESS		read-only
		STATUS			current
		DESCRIPTION		"The index value which uniquely identifies  the
            Lif interfL3e to which this entry is applicable."
		::=  {  nptTMUCurrentEntry  1  }
        
		
	nptTMUCurrentMoDescription	OBJECT-TYPE	
		SYNTAX			DisplayString 
		MAX-ACCESS		read-only
		STATUS			current
		DESCRIPTION		"Mo Description"
		::=  {  nptTMUCurrentEntry  2  }
        
	nptTMUCurrentT0FrequencyOffsetMax	OBJECT-TYPE	
		SYNTAX			DisplayString
		MAX-ACCESS		read-only
		STATUS			current
		DESCRIPTION		""
		::=  {  nptTMUCurrentEntry  3  }
        
	nptTMUCurrentT0FrequencyOffsetMin	OBJECT-TYPE	
		SYNTAX			DisplayString 
		MAX-ACCESS		read-only
		STATUS			current
		DESCRIPTION		"Mo Description"
		::=  {  nptTMUCurrentEntry  4  }
        
	nptTMUCurrentT0FrequencyOffsetCur 	OBJECT-TYPE	
		SYNTAX			DisplayString 
		MAX-ACCESS		read-only
		STATUS			current
		DESCRIPTION		"Mo Description"
		::=  {  nptTMUCurrentEntry  5  }
        
	nptCardCurrentTable	OBJECT-TYPE
		SYNTAX		SEQUENCE  OF  NptCardCurrentEntry
		MAX-ACCESS	not-accessible
		STATUS		current
		DESCRIPTION	"The Lif current table contains various statistics
            being collected for the current 15 minute
            interval."
		::=  { nptCard  1 }

	nptCardCurrentEntry	OBJECT-TYPE
		SYNTAX		NptCardCurrentEntry
		MAX-ACCESS	not-accessible
		STATUS		current
		DESCRIPTION	"An entry in the Lif Total table."
		INDEX		{  nptCardCurrentIndex  }
		::=  { nptCardCurrentTable 1 }

	NptCardCurrentEntry  ::=  SEQUENCE {
		nptCardCurrentIndex  Integer32,
		nptCardCurrentMoDescription  DisplayString,
        nptCardCurrentMaxMememoryUtilization  Counter64,
        nptCardCurrentMinMememoryUtilization  Counter64,
		nptCardCurrentAverageMemoryUtilization  Counter64,
        nptCardCurrentCurrentMemoryUtilization  Counter64, 
		nptCardCurrentMaxCpuUtilization  Counter64,
        nptCardCurrentMinCpuUtilization  Counter64,
        nptCardCurrentAverageCpuUtilization  Counter64,
        nptCardCurrentCurrentCpuUtilization  Counter64
		}

	nptCardCurrentIndex	OBJECT-TYPE	
		SYNTAX			Integer32  ( -2147483648 .. 2147483647  ) 
		MAX-ACCESS		read-only
		STATUS			current
		DESCRIPTION		"The index value which uniquely identifies  the
            Lif interfL3e to which this entry is applicable."
		::=  {  nptCardCurrentEntry  1  }
        
		
	nptCardCurrentMoDescription	OBJECT-TYPE	
		SYNTAX			DisplayString 
		MAX-ACCESS		read-only
		STATUS			current
		DESCRIPTION		"Mo Description"
		::=  {  nptCardCurrentEntry  2  }
        
	nptCardCurrentMaxMememoryUtilization	OBJECT-TYPE	
		SYNTAX			Counter64
		MAX-ACCESS		read-only
		STATUS			current
		DESCRIPTION		""
		::=  {  nptCardCurrentEntry  3  }
        
	nptCardCurrentMinMememoryUtilization	OBJECT-TYPE	
		SYNTAX			Counter64 
		MAX-ACCESS		read-only
		STATUS			current
		DESCRIPTION		"Mo Description"
		::=  {  nptCardCurrentEntry  4  }
        
	nptCardCurrentAverageMemoryUtilization 	OBJECT-TYPE	
		SYNTAX			Counter64 
		MAX-ACCESS		read-only
		STATUS			current
		DESCRIPTION		"Mo Description"
		::=  {  nptCardCurrentEntry  5  }
        
	nptCardCurrentCurrentMemoryUtilization 	OBJECT-TYPE	
		SYNTAX			Counter64 
		MAX-ACCESS		read-only
		STATUS			current
		DESCRIPTION		"Mo Description"
		::=  {  nptCardCurrentEntry  6  }
        
	nptCardCurrentMaxCpuUtilization	OBJECT-TYPE	
		SYNTAX		Counter64 
		MAX-ACCESS		read-only
		STATUS			current
		DESCRIPTION		"Mo Description"
		::=  {  nptCardCurrentEntry  7  }

	nptCardCurrentMinCpuUtilization	OBJECT-TYPE	
		SYNTAX		Counter64 
		MAX-ACCESS		read-only
		STATUS			current
		DESCRIPTION		"Mo Description"
		::=  {  nptCardCurrentEntry  8  }

	nptCardCurrentAverageCpuUtilization	OBJECT-TYPE	
		SYNTAX		Counter64 
		MAX-ACCESS		read-only
		STATUS			current
		DESCRIPTION		"Mo Description"
		::=  {  nptCardCurrentEntry  9  }

	nptCardCurrentCurrentCpuUtilization	OBJECT-TYPE	
		SYNTAX		Counter64 
		MAX-ACCESS		read-only
		STATUS			current
		DESCRIPTION		"Mo Description"
		::=  {  nptCardCurrentEntry  10  }

	nptCardTotalTable	OBJECT-TYPE
		SYNTAX		SEQUENCE  OF  NptCardTotalEntry
		MAX-ACCESS	not-accessible
		STATUS		current
		DESCRIPTION	"The Lif total table contains various statistics
            being collected for the history 24 hours
            interval."
		::=  { nptCard  2 }

	nptCardTotalEntry	OBJECT-TYPE
		SYNTAX		NptCardTotalEntry
		MAX-ACCESS	not-accessible
		STATUS		current
		DESCRIPTION	"An entry in the Lif Total table."
		INDEX		{  nptCardTotalIndex  }
		::=  { nptCardTotalTable 1 }

	NptCardTotalEntry  ::=  SEQUENCE {
		nptCardTotalIndex  Integer32,
		nptCardTotalMoDescription  DisplayString,
        nptCardTotalMaxMememoryUtilization  Counter64,
        nptCardTotalMinMememoryUtilization  Counter64,
		nptCardTotalAverageMemoryUtilization  Counter64,
        nptCardTotalCurrentMemoryUtilization  Counter64, 
		nptCardTotalMaxCpuUtilization  Counter64,
        nptCardTotalMinCpuUtilization  Counter64,
        nptCardTotalAverageCpuUtilization  Counter64,
        nptCardTotalCurrentCpuUtilization  Counter64
		}

	nptCardTotalIndex	OBJECT-TYPE	
		SYNTAX			Integer32  ( -2147483648 .. 2147483647  ) 
		MAX-ACCESS		read-only
		STATUS			current
		DESCRIPTION		"The index value which uniquely identifies  the
            Lif interfL3e to which this entry is applicable."
		::=  {  nptCardTotalEntry  1  }
        
		
	nptCardTotalMoDescription	OBJECT-TYPE	
		SYNTAX			DisplayString 
		MAX-ACCESS		read-only
		STATUS			current
		DESCRIPTION		"Mo Description"
		::=  {  nptCardTotalEntry  2  }
        
	nptCardTotalMaxMememoryUtilization	OBJECT-TYPE	
		SYNTAX			Counter64
		MAX-ACCESS		read-only
		STATUS			current
		DESCRIPTION		""
		::=  {  nptCardTotalEntry  3  }
        
	nptCardTotalMinMememoryUtilization	OBJECT-TYPE	
		SYNTAX			Counter64 
		MAX-ACCESS		read-only
		STATUS			current
		DESCRIPTION		"Mo Description"
		::=  {  nptCardTotalEntry  4  }
        
	nptCardTotalAverageMemoryUtilization 	OBJECT-TYPE	
		SYNTAX			Counter64 
		MAX-ACCESS		read-only
		STATUS			current
		DESCRIPTION		"Mo Description"
		::=  {  nptCardTotalEntry  5  }
        
	nptCardTotalCurrentMemoryUtilization 	OBJECT-TYPE	
		SYNTAX			Counter64 
		MAX-ACCESS		read-only
		STATUS			current
		DESCRIPTION		"Mo Description"
		::=  {  nptCardTotalEntry  6  }
        
	nptCardTotalMaxCpuUtilization	OBJECT-TYPE	
		SYNTAX		Counter64 
		MAX-ACCESS		read-only
		STATUS			current
		DESCRIPTION		"Mo Description"
		::=  {  nptCardTotalEntry  7  }

	nptCardTotalMinCpuUtilization 	OBJECT-TYPE	
		SYNTAX			Counter64 
		MAX-ACCESS		read-only
		STATUS			current
		DESCRIPTION		"Mo Description"
		::=  {  nptCardTotalEntry  8  }
        
	nptCardTotalAverageCpuUtilization 	OBJECT-TYPE	
		SYNTAX			Counter64 
		MAX-ACCESS		read-only
		STATUS			current
		DESCRIPTION		"Mo Description"
		::=  {  nptCardTotalEntry  9  }
        
	nptCardTotalCurrentCpuUtilization	OBJECT-TYPE	
		SYNTAX		Counter64 
		MAX-ACCESS		read-only
		STATUS			current
		DESCRIPTION		"Mo Description"
		::=  {  nptCardTotalEntry  10  }

	nptOZRCurrentTable	OBJECT-TYPE
		SYNTAX		SEQUENCE  OF  NptOZRCurrentEntry
		MAX-ACCESS	not-accessible
		STATUS		current
		DESCRIPTION	"The OZR current table contains various statistics
            being collected for the current 15 minute
            interval."
		::=  { nptOZR  1 }

	nptOZRCurrentEntry	OBJECT-TYPE
		SYNTAX		NptOZRCurrentEntry
		MAX-ACCESS	not-accessible
		STATUS		current
		DESCRIPTION	"An entry in the OZR Current table."
		INDEX		{  nptOZRCurrentIndex  }
		::=  { nptOZRCurrentTable 1 }

	NptOZRCurrentEntry  ::=  SEQUENCE {
		nptOZRCurrentIndex  Integer32,
		nptOZRCurrentMoDescription  DisplayString,
		nptOZRCurrentFECCE  Counter64,
		nptOZRCurrentFECUCE  Counter64,
		nptOZRCurrentPREFECBER  DisplayString,
		nptOZRCurrentDGDMAX  DisplayString,
		nptOZRCurrentDGDMIN  DisplayString,
		nptOZRCurrentCDMAX  DisplayString,
		nptOZRCurrentCDMIN  DisplayString
		}


	nptOZRCurrentIndex	OBJECT-TYPE	
		SYNTAX			Integer32  ( -2147483648 .. 2147483647  ) 
		MAX-ACCESS		read-only
		STATUS			current
		DESCRIPTION		"The index value which uniquely identifies  the
            OZR interface to which this entry is applicable."
		::=  {  nptOZRCurrentEntry  1  }
		
	nptOZRCurrentMoDescription	OBJECT-TYPE	
		SYNTAX			DisplayString 
		MAX-ACCESS		read-only
		STATUS			current
		DESCRIPTION		"Mo Description"
		::=  {  nptOZRCurrentEntry  2  }


	nptOZRCurrentFECCE	OBJECT-TYPE	
		SYNTAX			Counter64
		MAX-ACCESS		read-only
		STATUS			current
		DESCRIPTION		"Description"
		::=  {  nptOZRCurrentEntry  3  }


	nptOZRCurrentFECUCE	OBJECT-TYPE	
		SYNTAX			Counter64
		MAX-ACCESS		read-only
		STATUS			current
		DESCRIPTION		"Description"
		::=  {  nptOZRCurrentEntry  4  }


	nptOZRCurrentPREFECBER	OBJECT-TYPE	
		SYNTAX			DisplayString
		MAX-ACCESS		read-only
		STATUS			current
		DESCRIPTION		"Description"
		::=  {  nptOZRCurrentEntry  5  }


	nptOZRCurrentDGDMAX	OBJECT-TYPE	
		SYNTAX			DisplayString
		MAX-ACCESS		read-only
		STATUS			current
		DESCRIPTION		"Description"
		::=  {  nptOZRCurrentEntry  6  }


	nptOZRCurrentDGDMIN	OBJECT-TYPE	
		SYNTAX			DisplayString
		MAX-ACCESS		read-only
		STATUS			current
		DESCRIPTION		"Description"
		::=  {  nptOZRCurrentEntry  7  }


	nptOZRCurrentCDMAX	OBJECT-TYPE	
		SYNTAX			DisplayString
		MAX-ACCESS		read-only
		STATUS			current
		DESCRIPTION		"Description"
		::=  {  nptOZRCurrentEntry  8  }


	nptOZRCurrentCDMIN	OBJECT-TYPE	
		SYNTAX			DisplayString
		MAX-ACCESS		read-only
		STATUS			current
		DESCRIPTION		"Description"
		::=  {  nptOZRCurrentEntry  9  }


		
	nptOZRTotalTable	OBJECT-TYPE
		SYNTAX		SEQUENCE  OF  NptOZRTotalEntry
		MAX-ACCESS	not-accessible
		STATUS		current
		DESCRIPTION	"The OZR current table contains various statistics
            being collected for the current 15 minute
            interval."
		::=  { nptOZR  2 }

	nptOZRTotalEntry	OBJECT-TYPE
		SYNTAX		NptOZRTotalEntry
		MAX-ACCESS	not-accessible
		STATUS		current
		DESCRIPTION	"An entry in the OZR Total table."
		INDEX		{  nptOZRTotalIndex  }
		::=  { nptOZRTotalTable 1 }

	NptOZRTotalEntry  ::=  SEQUENCE {
		nptOZRTotalIndex  Integer32,
		nptOZRTotalMoDescription  DisplayString,
		nptOZRTotalFECCE  Counter64,
		nptOZRTotalFECUCE  Counter64,
		nptOZRTotalPREFECBER  DisplayString,
		nptOZRTotalDGDMAX  DisplayString,
		nptOZRTotalDGDMIN  DisplayString,
		nptOZRTotalCDMAX  DisplayString,
		nptOZRTotalCDMIN  DisplayString
		}


	nptOZRTotalIndex	OBJECT-TYPE	
		SYNTAX			Integer32  ( -2147483648 .. 2147483647  ) 
		MAX-ACCESS		read-only
		STATUS			current
		DESCRIPTION		"The index value which uniquely identifies  the
            OZR interface to which this entry is applicable."
		::=  {  nptOZRTotalEntry  1  }
		
	nptOZRTotalMoDescription	OBJECT-TYPE	
		SYNTAX			DisplayString 
		MAX-ACCESS		read-only
		STATUS			current
		DESCRIPTION		"Mo Description"
		::=  {  nptOZRTotalEntry  2  }


	nptOZRTotalFECCE	OBJECT-TYPE	
		SYNTAX			Counter64
		MAX-ACCESS		read-only
		STATUS			current
		DESCRIPTION		"Description"
		::=  {  nptOZRTotalEntry  3  }


	nptOZRTotalFECUCE	OBJECT-TYPE	
		SYNTAX			Counter64
		MAX-ACCESS		read-only
		STATUS			current
		DESCRIPTION		"Description"
		::=  {  nptOZRTotalEntry  4  }


	nptOZRTotalPREFECBER	OBJECT-TYPE	
		SYNTAX			DisplayString
		MAX-ACCESS		read-only
		STATUS			current
		DESCRIPTION		"Description"
		::=  {  nptOZRTotalEntry  5  }


	nptOZRTotalDGDMAX	OBJECT-TYPE	
		SYNTAX			DisplayString
		MAX-ACCESS		read-only
		STATUS			current
		DESCRIPTION		"Description"
		::=  {  nptOZRTotalEntry  6  }


	nptOZRTotalDGDMIN	OBJECT-TYPE	
		SYNTAX			DisplayString
		MAX-ACCESS		read-only
		STATUS			current
		DESCRIPTION		"Description"
		::=  {  nptOZRTotalEntry  7  }


	nptOZRTotalCDMAX	OBJECT-TYPE	
		SYNTAX			DisplayString
		MAX-ACCESS		read-only
		STATUS			current
		DESCRIPTION		"Description"
		::=  {  nptOZRTotalEntry  8  }


	nptOZRTotalCDMIN	OBJECT-TYPE	
		SYNTAX			DisplayString
		MAX-ACCESS		read-only
		STATUS			current
		DESCRIPTION		"Description"
		::=  {  nptOZRTotalEntry  9  }

END
