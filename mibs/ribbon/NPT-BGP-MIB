-- File Name : NPT-BGP-MIB
-- Date      : Tue Dec 01 10:00:00 CST 2020
-- Author    : Haoyang Xu



NPT-BGP-MIB	DEFINITIONS ::= BEGIN
	IMPORTS
		nptBGP
			FROM NPT-ROOT-MIB
		RowStatus, DisplayString, TruthValue, TimeStamp
			FROM SNMPv2-TC
		DisplayString
			FROM RFC1213-MIB
		MODULE-IDENTITY, enterprises, OBJECT-TYPE, Integer32, OBJECT-IDENTITY, Unsigned32
			FROM SNMPv2-SMI
        InetAddressType, InetAddress, InetPortNumber, InetAutonomousSystemNumber, InetAddressPrefixLength
            FROM INET-ADDRESS-MIB
        Bgp4V2IdentifierTC
            FROM BGP4V2-TC-MIB
        SnmpAdminString
            FROM SNMP-FRAMEWORK-MIB;

     Bgp4V2AddressFamilyIdentifierTC ::= TEXTUAL-CONVENTION
         STATUS       current
         DESCRIPTION
             "The representation of a BGP AFI.  The value of this object
              should be restricted to be between the values of 0 and
              65535."
         REFERENCE
             "RFC 4760, Section 3"
         SYNTAX INTEGER {
                 ipv4(1),
                 ipv6(2),
                 nsap(3),
                 hdlc(4),
                 bbn1822(5),
                 ieee802(6),
                 e163(7),
                 e164(8),
                 f69(9),
                 x121(10),
                 ipx(11),
                 appletalk(12),
                 decnet-iv(13),
                 vines(14),
                 e164-nsap(15),
                 dns(16),
                 distinguished-name(17),
                 as-num(18),
                 xtp-v4(19),
                 xtp-v6(20),
                 xtp-native(21),
                 fc-port(22),
                 fc-node(23),
                 gwid(24),
                 l2vpn(25),
                 mpls-tp-section-eid(26),
                 mpls-tp-lsp-eid(27),
                 mpls-tp-pwe-eid(28),
                 mt-v4(29),
                 mt-v6(30),
                 eigrp-common-sf(16384),
                 eigrp-v4-sf(16385),
                 eigrp-v6-sf(16386),
                 lcaf(16387),
                 bgp-ls(16388),
                 mac-48(16389),
                 mac-64(16390),
                 trill-oui(16391),
                 trill-mac-24(16392),
                 trill-mac-40(16393),
                 ipv6-64(16394),
                 trill-rbridge-port-id(16395),
                 trill-nickname(16396)
             }

     Bgp4V2SubsequentAddressFamilyIdentifierTC ::= TEXTUAL-CONVENTION
         STATUS       current
         DESCRIPTION
             "The representation of a BGP SAFI"
         REFERENCE
             "RFC 4760, Section 3.  The value of this object should be
              restricted to be between the values of 0 and 255."
         SYNTAX INTEGER {
                 unicast(1),
                 multicast(2),
                 labeled-unicast(4),
                 multicast-vpn(5),
                 pseudowire(6),
                 tunnel-encap(7),
                 mcast-vpls(8),
                 tunnel(64),
                 vpls(65),
                 mdt(66),
                 v4-over-v6(67),
                 v6-over-v4(68),
                 l1-vpn-auto-discovery(69),
                 evpn(70),
                 bgp-ls(71),
                 bgp-ls-vpn(72),
                 sr-te(73),
                 labeled-vpn(128),
                 multicast-mpls-vpn(129),
                 route-target(132),
                 ipv4-flow-spec(133),
                 vpnv4-flow-spec(134),
                 vpn-auto-discovery(140)
             }

    nptBgp4V2 MODULE-IDENTITY
        LAST-UPDATED "202012010000Z"
        ORGANIZATION "Ribbon Communications Inc."
        CONTACT-INFO "on.support@rbbn.com 
                         Ribbon Communications Inc.,China
                         Dongxin Tower, No.398 Wensan Road, 
                         Hangzhou, 310012 P.R.China"
        DESCRIPTION  "Description"
		REVISION	 "01Z"
		DESCRIPTION	 ""
		::=  {  nptBGP  1  }

    -- Objects
    nptBgp4V2Objects OBJECT IDENTIFIER ::= { nptBgp4V2 1 }

    nptBgp4V2PeerTable OBJECT-TYPE
        SYNTAX     SEQUENCE OF NptBgp4V2PeerEntry
        MAX-ACCESS not-accessible
        STATUS     current
        DESCRIPTION
            "BGP peer table.  This table contains, one entry per BGP
             peer, information about the connections with BGP peers."
        ::= { nptBgp4V2Objects 2 }

    nptBgp4V2PeerEntry OBJECT-TYPE
        SYNTAX     NptBgp4V2PeerEntry
        MAX-ACCESS not-accessible
        STATUS     current
        DESCRIPTION
            "Entry containing information about the connection with
             a remote BGP peer."
        INDEX {
            nptBgp4V2PeerInstance,
            nptBgp4V2PeerRemoteAddrType,
            nptBgp4V2PeerRemoteAddr
        }
        ::= { nptBgp4V2PeerTable 1 }

    NptBgp4V2PeerEntry ::= SEQUENCE {
        -- INDEX information
        nptBgp4V2PeerInstance
            Unsigned32,
        nptBgp4V2PeerLocalAddrType
            InetAddressType,
        nptBgp4V2PeerLocalAddr
            InetAddress,
        nptBgp4V2PeerRemoteAddrType
            InetAddressType,
        nptBgp4V2PeerRemoteAddr
            InetAddress,

        -- Local
        nptBgp4V2PeerLocalPort
            InetPortNumber,
        nptBgp4V2PeerLocalAs
            InetAutonomousSystemNumber,
        nptBgp4V2PeerLocalIdentifier
            Bgp4V2IdentifierTC,

        -- Remote
        nptBgp4V2PeerRemotePort
            InetPortNumber,
        nptBgp4V2PeerRemoteAs
            InetAutonomousSystemNumber,
        nptBgp4V2PeerRemoteIdentifier
            Bgp4V2IdentifierTC,

        -- Session status
        nptBgp4V2PeerAdminStatus
            INTEGER,
        nptBgp4V2PeerState
            INTEGER,
        nptBgp4V2PeerDescription
            SnmpAdminString
    }

    nptBgp4V2PeerInstance OBJECT-TYPE
        SYNTAX     Unsigned32 (1..4294967295)
        MAX-ACCESS read-only
        STATUS     current
        DESCRIPTION
            "The routing instance index.

             Some BGP implementations permit the creation of
             multiple instances of a BGP routing process. An
             example includes routers running BGP/MPLS IP Virtual
             Private Networks.

             Implementations that do not support multiple
             routing instances should return 1 for this object."
        ::= { nptBgp4V2PeerEntry 1 }

    nptBgp4V2PeerLocalAddrType OBJECT-TYPE
        SYNTAX     InetAddressType
        MAX-ACCESS read-only
        STATUS     current
        DESCRIPTION
            "The address family of the local end of the peering
             session."
        ::= { nptBgp4V2PeerEntry 2 }

    nptBgp4V2PeerLocalAddr OBJECT-TYPE
        SYNTAX     InetAddress
        MAX-ACCESS read-only
        STATUS     current
        DESCRIPTION
            "The local IP address of this entry's BGP connection.

             An implementation is required to support IPv4 peering
             sessions in which case the length of this object is 4.
             An implementation MAY support IPv6 peering
             sessions in which case the length of this object is 16.
             IPv6 link-local peering sessions MAY be supported by
             this MIB.  In this case the length of this object is 20."
        ::= { nptBgp4V2PeerEntry 3 }

    nptBgp4V2PeerRemoteAddrType OBJECT-TYPE
        SYNTAX     InetAddressType
        MAX-ACCESS read-only
        STATUS     current
        DESCRIPTION
            "The address family of the remote end of the peering
             session.

             An implementation is required to support IPv4 peering
             sessions in which case the length of this object is 4.
             An implementation MAY support IPv6 peering
             sessions in which case the length of this object is 16.
             IPv6 link-local peering sessions MAY be supported by
             this MIB.  In this case the length of this object is 20."
        ::= { nptBgp4V2PeerEntry 4 }

    nptBgp4V2PeerRemoteAddr OBJECT-TYPE
        SYNTAX     InetAddress
        MAX-ACCESS read-only
        STATUS     current
        DESCRIPTION
            "The remote IP address of this entry's BGP peer."
        ::= { nptBgp4V2PeerEntry 5 }

    nptBgp4V2PeerLocalPort OBJECT-TYPE
        SYNTAX     InetPortNumber
        MAX-ACCESS read-only
        STATUS     current
        DESCRIPTION
            "The local port for the TCP connection between the BGP
             peers."
        ::= { nptBgp4V2PeerEntry 6 }

    nptBgp4V2PeerLocalAs OBJECT-TYPE
        SYNTAX     InetAutonomousSystemNumber
        MAX-ACCESS read-only
        STATUS     current
        DESCRIPTION
            "Some implementations of BGP can represent themselves
             as multiple ASes. This is the AS that this peering
             session is representing itself as to the remote peer."
        ::= { nptBgp4V2PeerEntry 7 }

    nptBgp4V2PeerLocalIdentifier OBJECT-TYPE
        SYNTAX     Bgp4V2IdentifierTC
        MAX-ACCESS read-only
        STATUS     current
        DESCRIPTION
            "The BGP Identifier of the local system for this peering
             session.  It is REQUIRED that all bgp4V2PeerLocalIdentifier
             values for the same bgp4V2PeerInstance be identical."
        REFERENCE
            "RFC 4271, Section 4.2, 'BGP Identifier'."
        ::= { nptBgp4V2PeerEntry 8 }

    nptBgp4V2PeerRemotePort OBJECT-TYPE
        SYNTAX     InetPortNumber
        MAX-ACCESS read-only
        STATUS     current
        DESCRIPTION
            "The remote port for the TCP connection between the BGP
             peers.

             Note that the objects bgp4V2PeerLocalAddr,
             bgp4V2PeerLocalPort, bgp4V2PeerRemoteAddr and
             bgp4V2PeerRemotePort provide the appropriate reference to
             the standard MIB TCP connection table, or even the ipv6
             TCP MIB as in RFC 4022."
        REFERENCE
            "RFC 2012 - SNMPv2 Management Information Base for the
             Transmission Control Protocol using SMIv2.
             RFC 4022 - IP Version 6 Management Information Base
             for the Transmission Control Protocol."
        ::= { nptBgp4V2PeerEntry 9 }

    nptBgp4V2PeerRemoteAs OBJECT-TYPE
        SYNTAX     InetAutonomousSystemNumber
        MAX-ACCESS read-only
        STATUS     current
        DESCRIPTION
            "The remote autonomous system number received in the BGP
             OPEN message."
        REFERENCE
            "RFC 4271, Section 4.2."
        ::= { nptBgp4V2PeerEntry 10 }

    nptBgp4V2PeerRemoteIdentifier OBJECT-TYPE
        SYNTAX     Bgp4V2IdentifierTC
        MAX-ACCESS read-only
        STATUS     current
        DESCRIPTION
            "The BGP Identifier of this entry's remote BGP peer.

             This entry should be 0.0.0.0 unless the
             bgp4V2PeerState is in the openconfirm or the
             established state."
        REFERENCE
            "RFC 4271, Section 4.2, 'BGP Identifier'."
        ::= { nptBgp4V2PeerEntry 11 }

    nptBgp4V2PeerAdminStatus OBJECT-TYPE
        SYNTAX     INTEGER {
            halted(1),
            running(2)
        }
        MAX-ACCESS read-only
        STATUS     current
        DESCRIPTION
            "Whether or not the BGP FSM for this remote peer is
             halted or running. The BGP FSM for a remote peer is
             halted after processing a Stop event. Likewise, it is
             in the running state after a Start event.

             The bgp4V2PeerState will generally be in the idle state
             when the FSM is halted, although some extensions such
             as Graceful Restart will leave the peer in the Idle
             state but with the FSM running."
        REFERENCE
            "RFC 4271, Section 8.1.2."
        ::= { nptBgp4V2PeerEntry 12 }

    nptBgp4V2PeerState OBJECT-TYPE
        SYNTAX     INTEGER {
            idle(1),
            connect(2),
            active(3),
            opensent(4),
            openconfirm(5),
            established(6)
        }
        MAX-ACCESS read-only
        STATUS     current
        DESCRIPTION
            "The BGP peer connection state."
        REFERENCE
            "RFC 4271, Section 8.2.2."
        ::= { nptBgp4V2PeerEntry 13 }


    nptBgp4V2PeerDescription OBJECT-TYPE
        SYNTAX     SnmpAdminString
        MAX-ACCESS read-only
        STATUS     current
        DESCRIPTION
            "A user configured description identifying this peer.  When
             this object is not the empty string, this object SHOULD
             contain a description that is unique within a given BGP
             instance for this peer."
        ::= { nptBgp4V2PeerEntry 14 }


    --
    -- Per-peer error management information.
    --

    nptBgp4V2PeerErrorsTable OBJECT-TYPE
        SYNTAX     SEQUENCE OF NptBgp4V2PeerErrorsEntry
        MAX-ACCESS not-accessible
        STATUS     current
        DESCRIPTION
            "On a per-peer basis, this table reflects the last
             protocol-defined error encountered and reported on
             the peer session."
        ::= { nptBgp4V2Objects 3 }

    nptBgp4V2PeerErrorsEntry OBJECT-TYPE
        SYNTAX     NptBgp4V2PeerErrorsEntry
        MAX-ACCESS not-accessible
        STATUS     current
        DESCRIPTION
            "Each entry contains information about errors sent
             and received for a particular BGP peer."
        AUGMENTS {
            nptBgp4V2PeerEntry
        }
        ::= { nptBgp4V2PeerErrorsTable 1 }

    NptBgp4V2PeerErrorsEntry ::= SEQUENCE {
        nptBgp4V2PeerLastErrorCodeReceived
            Unsigned32,
        nptBgp4V2PeerLastErrorSubCodeReceived
            Unsigned32,
        nptBgp4V2PeerLastErrorReceivedTime
            TimeStamp,
        nptBgp4V2PeerLastErrorReceivedText
            SnmpAdminString,
        nptBgp4V2PeerLastErrorReceivedData
            OCTET STRING,
        nptBgp4V2PeerLastErrorCodeSent
            Unsigned32,
        nptBgp4V2PeerLastErrorSubCodeSent
            Unsigned32,
        nptBgp4V2PeerLastErrorSentTime
            TimeStamp,
        nptBgp4V2PeerLastErrorSentText
            SnmpAdminString,
        nptBgp4V2PeerLastErrorSentData
            OCTET STRING
    }

    nptBgp4V2PeerLastErrorCodeReceived OBJECT-TYPE
        SYNTAX     Unsigned32 (0..255)
        MAX-ACCESS read-only
        STATUS     current
        DESCRIPTION
            "The last error code received from this peer via
             NOTIFICATION message on this connection.  If no error has
             occurred, this field is zero."
        REFERENCE
            "RFC 4271, Section 4.5.
             RFC 4486 optionally supported.
             RFC 3362, Section 5 optionally supported."
        ::= { nptBgp4V2PeerErrorsEntry 1 }

    nptBgp4V2PeerLastErrorSubCodeReceived OBJECT-TYPE
        SYNTAX     Unsigned32 (0..255)
        MAX-ACCESS read-only
        STATUS     current
        DESCRIPTION
            "The last subcode received from this peer via NOTIFICATION
             message on this connection.  If no error has occurred, this
             field is zero."
        REFERENCE
            "RFC 4271, Section 4.5.
             RFC 4486 optionally supported.
             RFC 3362, Section 5 optionally supported."
        ::= { nptBgp4V2PeerErrorsEntry 2 }

    nptBgp4V2PeerLastErrorReceivedTime OBJECT-TYPE
        SYNTAX     TimeStamp
        MAX-ACCESS read-only
        STATUS     current
        DESCRIPTION
            "The timestamp that the last NOTIFICATION was received from
             this peer."
        REFERENCE
            "RFC 4271, Section 4.5."
        ::= { nptBgp4V2PeerErrorsEntry 3 }

    nptBgp4V2PeerLastErrorReceivedText OBJECT-TYPE
        SYNTAX     SnmpAdminString
        MAX-ACCESS read-only
        STATUS     current
        DESCRIPTION
            "This object contains an implementation specific
             explanation of the error that was reported."
        ::= { nptBgp4V2PeerErrorsEntry 4 }

    nptBgp4V2PeerLastErrorReceivedData OBJECT-TYPE
        SYNTAX     OCTET STRING (SIZE(0..4075))
        MAX-ACCESS read-only
        STATUS     current
        DESCRIPTION
            "The last error code's data seen by this peer.

             Per RFC 2578, some implementations may have limitations
             dealing with OCTET STRINGS larger than 255.  Thus, this
             data may be truncated."
        REFERENCE
            "RFC 4271, Section 4.5,
             RFC 2578, Section 7.1.2,
             RFC 4486 optionally supported.
             RFC 3362, Section 5 optionally supported."
        ::= { nptBgp4V2PeerErrorsEntry 5 }

    nptBgp4V2PeerLastErrorCodeSent OBJECT-TYPE
        SYNTAX     Unsigned32 (0..255)
        MAX-ACCESS read-only
        STATUS     current
        DESCRIPTION
            "The last error code sent to this peer via NOTIFICATION
             message on this connection.  If no error has occurred, this
             field is zero."
        REFERENCE
            "RFC 4271, Section 4.5.
             RFC 4486 optionally supported.
             RFC 3362, Section 5 optionally supported."
        ::= { nptBgp4V2PeerErrorsEntry 6 }

    nptBgp4V2PeerLastErrorSubCodeSent OBJECT-TYPE
        SYNTAX     Unsigned32 (0..255)
        MAX-ACCESS read-only
        STATUS     current
        DESCRIPTION
            "The last subcode sent to this peer via NOTIFICATION
             message on this connection.  If no error has occurred, this
             field is zero."
        REFERENCE
            "RFC 4271, Section 4.5.
             RFC 4486 optionally supported.
             RFC 3362, Section 5 optionally supported."
        ::= { nptBgp4V2PeerErrorsEntry 7 }

    nptBgp4V2PeerLastErrorSentTime OBJECT-TYPE
        SYNTAX     TimeStamp
        MAX-ACCESS read-only
        STATUS     current
        DESCRIPTION
            "The timestamp that the last NOTIFICATION was sent to
             this peer."
        REFERENCE
            "RFC 4271, Section 4.5."
        ::= { nptBgp4V2PeerErrorsEntry 8 }

    nptBgp4V2PeerLastErrorSentText OBJECT-TYPE
        SYNTAX     SnmpAdminString
        MAX-ACCESS read-only
        STATUS     current
        DESCRIPTION
            "This object contains an implementation specific
             explanation of the error that is being reported."
        ::= { nptBgp4V2PeerErrorsEntry 9 }

    nptBgp4V2PeerLastErrorSentData OBJECT-TYPE
        SYNTAX     OCTET STRING (SIZE(0..4075))
        MAX-ACCESS read-only
        STATUS     current
        DESCRIPTION
            "The last error code's data sent to this peer.

             Per RFC 2578, some implementations may have limitations
             dealing with OCTET STRINGS larger than 255.  Thus, this
             data may be truncated."
        REFERENCE
            "RFC 4271, Section 4.5,
             RFC 2578, Section 7.1.2
             RFC 4486 optionally supported.
             RFC 3362, Section 5 optionally supported."
        ::= { nptBgp4V2PeerErrorsEntry 10 }
        
        

    --
    -- Per-peer Event Times
    --

    nptBgp4V2PeerEventTimesTable OBJECT-TYPE
        SYNTAX     SEQUENCE OF NptBgp4V2PeerEventTimesEntry
        MAX-ACCESS not-accessible
        STATUS     current
        DESCRIPTION
            "A table reporting the per-peering session amount
             of time elapsed and update events since the peering
             session advanced into the established state."
        ::= { nptBgp4V2Objects 4 }

    nptBgp4V2PeerEventTimesEntry OBJECT-TYPE
        SYNTAX     NptBgp4V2PeerEventTimesEntry
        MAX-ACCESS not-accessible
        STATUS     current
        DESCRIPTION
            "Each row contains a set of statistics about time
             spent and events encountered in the peer session
             established state."
        AUGMENTS {
            nptBgp4V2PeerEntry
        }
        ::= { nptBgp4V2PeerEventTimesTable 1 }

    NptBgp4V2PeerEventTimesEntry ::= SEQUENCE {
        nptBgp4V2PeerFsmEstablishedTime
            Gauge32,
        nptBgp4V2PeerInUpdatesElapsedTime
            Gauge32
    }

    nptBgp4V2PeerFsmEstablishedTime OBJECT-TYPE
        SYNTAX     Gauge32
        UNITS      "seconds"
        MAX-ACCESS read-only
        STATUS     current
        DESCRIPTION
            "This timer indicates how long (in seconds) this peer
             has been in the established state or how long since this
             peer was last in the established state.  It is set to
             zero when a new peer is configured or when the router is
             booted.  If the peer has never reached the established
             state, the value remains zero."
        REFERENCE
            "RFC 4271, Section 8."
        ::= { nptBgp4V2PeerEventTimesEntry 1 }

    nptBgp4V2PeerInUpdatesElapsedTime OBJECT-TYPE
        SYNTAX     Gauge32
        UNITS      "seconds"
        MAX-ACCESS read-only
        STATUS     current
        DESCRIPTION
            "Elapsed time (in seconds) since the last BGP UPDATE
             message was received from the peer.  Each time
             bgpPeerInUpdates is incremented, the value of this
             object is set to zero (0)."
        REFERENCE
            "RFC 4271, Section 4.3.
             RFC 4271, Section 8.2.2, Established state."

        ::= { nptBgp4V2PeerEventTimesEntry 2 }
        
        

    -- Per-Peer Negotiated Timers
    --

    nptBgp4V2PeerNegotiatedTimersTable OBJECT-TYPE
        SYNTAX     SEQUENCE OF NptBgp4V2PeerNegotiatedTimersEntry
        MAX-ACCESS not-accessible
        STATUS     current
        DESCRIPTION
            "Configured values of per-peer timers are seen
             in the bgp4V2PeerConfiguredTimersTable.

             Values in this table reflect the current
             operational values, after negotiation from values
             derived from initial configuration."
        ::= { nptBgp4V2Objects 6 }

    nptBgp4V2PeerNegotiatedTimersEntry OBJECT-TYPE
        SYNTAX     NptBgp4V2PeerNegotiatedTimersEntry
        MAX-ACCESS not-accessible
        STATUS     current
        DESCRIPTION
            "Each entry reflects a value of the currently
             operational, negotiated timer as reflected in the
             nptBgp4V2PeerNegotiatedTimersEntry."
        AUGMENTS {
            nptBgp4V2PeerEntry
        }
        ::= { nptBgp4V2PeerNegotiatedTimersTable 1 }

    NptBgp4V2PeerNegotiatedTimersEntry ::= SEQUENCE {
        nptBgp4V2PeerHoldTime
            Unsigned32,
        nptBgp4V2PeerKeepAlive
            Unsigned32
    }

    nptBgp4V2PeerHoldTime OBJECT-TYPE
        SYNTAX     Unsigned32 ( 0 | 3..65535 )
        UNITS      "seconds"
        MAX-ACCESS read-only
        STATUS     current
        DESCRIPTION
            "The value of this object is calculated by this BGP
             Speaker as being;

             zero (0) - if this was the value sent by the peer and
             this value is permitted by this BGP Speaker. In this
             case, no keepalive messages are sent and the Hold Timer
             is not set.

             At least three (3). This value is the smaller of
             the value sent by this peer in the OPEN message and
             bgp4V2PeerHoldTimeConfigured for this peer.

             If the peer is not in the established state, the value
             of this object is zero (0)."
        REFERENCE
            "RFC 4271, Section 4.2."
        ::= { nptBgp4V2PeerNegotiatedTimersEntry 1 }

    nptBgp4V2PeerKeepAlive OBJECT-TYPE
        SYNTAX     Unsigned32 ( 0 | 1..21845 )
        UNITS      "seconds"
        MAX-ACCESS read-only
        STATUS     current
        DESCRIPTION
            "Time interval in seconds for the KeepAlive timer
             established with the peer. The value of this object
             is calculated by this BGP speaker such that, when
             compared with bgp4V2PeerHoldTime, it has the same
             proportion as what bgp4V2PeerKeepAliveConfigured has
             when compared with bgp4V2PeerHoldTimeConfigured. If
             the value of this object is zero (0), it indicates
             that the KeepAlive timer has not been established
             with the peer, or, the value of
             bgp4V2PeerKeepAliveConfigured is zero (0).

             If the peer is not in the established state, the value
             of this object is zero (0)."
        REFERENCE
            "RFC 4271, Section 4.4."
        ::= { nptBgp4V2PeerNegotiatedTimersEntry 2 }

    --
    -- Per-peer counters
    --

    nptBgp4V2PeerCountersTable OBJECT-TYPE
        SYNTAX     SEQUENCE OF NptBgp4V2PeerCountersEntry
        MAX-ACCESS not-accessible
        STATUS     current
        DESCRIPTION
            "The counters associated with a BGP Peer."
        ::= { nptBgp4V2Objects 7 }

    nptBgp4V2PeerCountersEntry OBJECT-TYPE
        SYNTAX     NptBgp4V2PeerCountersEntry
        MAX-ACCESS not-accessible
        STATUS     current
        DESCRIPTION
            "Each entry contains counters of message transmissions
             and FSM transitions for a given BGP Peering session."
        AUGMENTS {
            nptBgp4V2PeerEntry
        }
        ::= { nptBgp4V2PeerCountersTable 1 }

    NptBgp4V2PeerCountersEntry ::= SEQUENCE {
        nptBgp4V2PeerInUpdates
            Counter32,
        nptBgp4V2PeerOutUpdates
            Counter32,
        nptBgp4V2PeerInTotalMessages
            Counter32,
        nptBgp4V2PeerOutTotalMessages
            Counter32,
        nptBgp4V2PeerFsmEstablishedTransitions
            Counter32
    }

    nptBgp4V2PeerInUpdates OBJECT-TYPE
        SYNTAX     Counter32
        MAX-ACCESS read-only
        STATUS     current
        DESCRIPTION
            "The number of BGP UPDATE messages received on this
             connection."
        ::= { nptBgp4V2PeerCountersEntry 1 }

    nptBgp4V2PeerOutUpdates OBJECT-TYPE
        SYNTAX     Counter32
        MAX-ACCESS read-only
        STATUS     current
        DESCRIPTION
            "The number of BGP UPDATE messages transmitted on this
             connection."
        ::= { nptBgp4V2PeerCountersEntry 2 }

    nptBgp4V2PeerInTotalMessages OBJECT-TYPE
        SYNTAX     Counter32
        MAX-ACCESS read-only
        STATUS     current
        DESCRIPTION
            "The total number of messages received from the remote
             peer on this connection."
        ::= { nptBgp4V2PeerCountersEntry 3 }

    nptBgp4V2PeerOutTotalMessages OBJECT-TYPE
        SYNTAX     Counter32
        MAX-ACCESS read-only
        STATUS     current
        DESCRIPTION
            "The total number of messages transmitted to the remote
             peer on this connection."
        ::= { nptBgp4V2PeerCountersEntry 4 }

    nptBgp4V2PeerFsmEstablishedTransitions OBJECT-TYPE
        SYNTAX     Counter32
        MAX-ACCESS read-only
        STATUS     current
        DESCRIPTION
            "The total number of times the BGP FSM transitioned into
             the established state for this peer."
        ::= { nptBgp4V2PeerCountersEntry 5 }

    --
    -- Per-Peer Prefix Gauges
    --

    nptBgp4V2PrefixGaugesTable OBJECT-TYPE
        SYNTAX     SEQUENCE OF NptBgp4V2PrefixGaugesEntry
        MAX-ACCESS not-accessible
        STATUS     current
        DESCRIPTION
            "Additional per-peer, per AFI-SAFI counters for
             prefixes"
        ::= { nptBgp4V2Objects 8 }

    nptBgp4V2PrefixGaugesEntry OBJECT-TYPE
        SYNTAX     NptBgp4V2PrefixGaugesEntry
        MAX-ACCESS not-accessible
        STATUS     current
        DESCRIPTION
            "Entry containing information about a bgp-peers prefix
             counters."
        INDEX {
            nptBgp4V2PeerInstance,
            nptBgp4V2PeerRemoteAddrType,
            nptBgp4V2PeerRemoteAddr,
            nptBgp4V2PrefixGaugesAfi,
            nptBgp4V2PrefixGaugesSafi
        }
        ::= { nptBgp4V2PrefixGaugesTable 1 }

    NptBgp4V2PrefixGaugesEntry ::= SEQUENCE {
        nptBgp4V2PrefixGaugesAfi
            Bgp4V2AddressFamilyIdentifierTC,
        nptBgp4V2PrefixGaugesSafi
            Bgp4V2SubsequentAddressFamilyIdentifierTC,
        nptBgp4V2PrefixInPrefixes
            Gauge32,
        nptBgp4V2PrefixInPrefixesAccepted
            Gauge32,
        nptBgp4V2PrefixOutPrefixes
            Gauge32
    }

    nptBgp4V2PrefixGaugesAfi OBJECT-TYPE
        SYNTAX     Bgp4V2AddressFamilyIdentifierTC
        MAX-ACCESS read-only
        STATUS     current
        DESCRIPTION
            "The AFI index of the per-peer, per prefix counters"
        ::= { nptBgp4V2PrefixGaugesEntry 1 }

    nptBgp4V2PrefixGaugesSafi OBJECT-TYPE
        SYNTAX     Bgp4V2SubsequentAddressFamilyIdentifierTC
        MAX-ACCESS read-only
        STATUS     current
        DESCRIPTION
            "The SAFI index of the per-peer, per prefix counters"
        ::= { nptBgp4V2PrefixGaugesEntry 2 }

    nptBgp4V2PrefixInPrefixes OBJECT-TYPE
        SYNTAX     Gauge32
        MAX-ACCESS read-only
        STATUS     current
        DESCRIPTION
            "The number of prefixes received from a peer and are
             stored in the Adj-Ribs-In for that peer.

             Note that this number does not reflect prefixes that
             have been discarded due to policy."
        REFERENCE
            "RFC 4271, Sections 3.2 and 9."
        ::= { nptBgp4V2PrefixGaugesEntry 3 }

    nptBgp4V2PrefixInPrefixesAccepted OBJECT-TYPE
        SYNTAX     Gauge32
        MAX-ACCESS read-only
        STATUS     current
        DESCRIPTION
            "The number of prefixes for a peer that are installed
             in the Adj-Ribs-In and are eligible to become active
             in the Loc-Rib."
        REFERENCE
            "RFC 4271, Sections 3.2 and 9."
        ::= { nptBgp4V2PrefixGaugesEntry 4 }

    nptBgp4V2PrefixOutPrefixes OBJECT-TYPE
        SYNTAX     Gauge32
        MAX-ACCESS read-only
        STATUS     current
        DESCRIPTION
            "The number of prefixes for a peer that are installed
             in that peer's Adj-Ribs-Out."
        REFERENCE
            "RFC 4271, Sections 3.2 and 9."
        ::= { nptBgp4V2PrefixGaugesEntry 5 }
        
END
